module openconfig-platform-integrated-circuit {
  yang-version "1";
  
  namespace "http://openconfig.net/yang/platform/integrated-circuit";

  prefix "oc-ic";

  import openconfig-platform { prefix oc-platform; }
  import openconfig-extensions { prefix oc-ext; }
  import openconfig-types { prefix oc-types; }

  organization "OpenConfig working group";
  contact
    "OpenConfig working group
    www.openconfig.net";

  description
    "This module defines extensions to the OpenConfig platform model
    that apply to integrated circuit (INTEGRATED_CIRCUIT) components.
    These components are generically forwarding NPUs or ASICs within
    the system for which configuration or state is applicable.";

  oc-ext:openconfig-version "0.1.0";

  revision "2021-05-16" {
    description
      "Initial revision with platform capacity.";
    reference "0.1.0";
  }

  oc-ext:catalog-organization "openconfig";
  oc-ext:origin "openconfig";

  grouping backplane-facing-capacity-structural {
    description
      "Structural grouping for reporting on backplane-facing capacity of an integrated
      circuit.";

    container backplane-facing-capacity {
      description
        "This container allows a particular INTEGRATED_CIRCUIT to report its
        available backplane-facing bandwidth. Wheere an integrated circuit is connected
        by one or more links to the system's backplane, the capacity is the total cross-
        sectional bandwidfth available from the input ports of the integrated circuit
        across the fabric. The capacity should also reflect the operational status of
        the links.";

      container state {
        config false;
        description
          "Operational state parameters relating to backplane capacity.";

        uses backplane-capacity-state;
      }
    }
  }

  grouping backplane-capacity-state {
    description
      "Operational state relating to backplane capacity.";

    leaf total {
      type uint64;
      units "bits per second";
      description
        "Total backplane-facing capacity that is available in the presence
        of no link failures or degradation.";
      oc-ext:telemetry-on-change;
    }

    leaf consumed-capacity {
      type uint64;
      units "bits per second";
      description
        "Backplane-facing capacity that is consumed by front-panel ports that are connected
        to the integrated circuit.";
      oc-ext:telemetry-on-change;
    }

    leaf available-pct {
      type oc-types:percentage;
      description
        "Percentage of the total backplane-facing capacity that is currently available to the front
        panel ports taking into account failures and/or degradation within the system.";
      oc-ext:telemetry-on-change;
    }
  }

  augment "/oc-platform:components/oc-platform:component/oc-platform:integrated-circuit" {
    description
      "Augment integrated circuit components with backplane-facing capacity.";
    uses backplane-facing-capacity-structural;
  }
}
