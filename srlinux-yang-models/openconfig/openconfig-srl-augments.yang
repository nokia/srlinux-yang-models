module openconfig-srl-augments {
  yang-version "1";
  namespace "urn:nokia.com:srlinux:openconfig:openconfig-srl-augments";

  prefix "oc-srl-aug";

  import openconfig-interfaces { prefix oc-if; }
  import openconfig-if-aggregate { prefix oc-if-agg; }
  import openconfig-if-ethernet { prefix oc-if-eth; }
  import openconfig-system-grpc { prefix oc-grpc; }

  description
    "SRL augments to the OpenConfig models";

  revision 2026-07-31 {
    description
      "SRLinux 26.7.1";
  }
  revision 2024-07-31 {
    description
      "SRLinux 24.7.1";
  }
  revision 2022-03-31 {
    description
      "SRLinux 22.3.1";
  }

  // copy of srl_nokia-extensions:no-globbing (yang/modules/models/srl_nokia/models/common/srl_nokia-extensions.yang)
  extension no-globbing {
    description
      "Disables globbing for this leaf (useful for fields defining regex patterns)";
  }

  grouping lag-augments
  {
    leaf member-speed {
      type identityref {
        base oc-if-eth:ETHERNET_SPEED;
      }
      description
        "SRL mandates that a lag be configured with a speed.";
    }
  }

  augment "/oc-if:interfaces/oc-if:interface/oc-if-agg:aggregation/" +
    "oc-if-agg:config" {
    uses lag-augments;
  }
  augment "/oc-if:interfaces/oc-if:interface/oc-if-agg:aggregation/" +
    "oc-if-agg:state" {
    uses lag-augments;
  }
}
