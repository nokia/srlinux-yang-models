module openconfig-srl-deviations {
  yang-version 1.1;
  namespace "urn:nokia.com:srlinux:openconfig:openconfig-srl-deviations";
  prefix openconfig-srl-deviations;

  import openconfig-acl {
    prefix openconfig-acl;
  }

  import openconfig-alarms {
    prefix openconfig-alarms;
  }

  import openconfig-bgp-policy {
    prefix openconfig-bgp-policy;
  }

  import openconfig-defined-sets {
    prefix openconfig-defined-sets;
  }

  import openconfig-flexalgo {
    prefix openconfig-flexalgo;
  }

  import openconfig-gnsi-acctz {
    prefix openconfig-gnsi-acctz;
  }

  import openconfig-gnsi-certz {
    prefix openconfig-gnsi-certz;
  }

  import openconfig-gnsi-credentialz {
    prefix openconfig-gnsi-credentialz;
  }

  import openconfig-if-aggregate {
    prefix openconfig-if-aggregate;
  }

  import openconfig-if-ethernet {
    prefix openconfig-if-ethernet;
  }

  import openconfig-if-ip {
    prefix openconfig-if-ip;
  }

  import openconfig-if-sdn-ext {
    prefix openconfig-if-sdn-ext;
  }

  import openconfig-interfaces {
    prefix openconfig-interfaces;
  }

  import openconfig-isis-policy {
    prefix openconfig-isis-policy;
  }

  import openconfig-lacp {
    prefix openconfig-lacp;
  }

  import openconfig-lldp {
    prefix openconfig-lldp;
  }

  import openconfig-local-routing-network-instance {
    prefix openconfig-local-routing-network-instance;
  }

  import openconfig-network-instance {
    prefix openconfig-network-instance;
  }

  import openconfig-platform {
    prefix openconfig-platform;
  }

  import openconfig-platform-controller-card {
    prefix openconfig-platform-controller-card;
  }

  import openconfig-platform-cpu {
    prefix openconfig-platform-cpu;
  }

  import openconfig-platform-fabric {
    prefix openconfig-platform-fabric;
  }

  import openconfig-platform-integrated-circuit {
    prefix openconfig-platform-integrated-circuit;
  }

  import openconfig-platform-linecard {
    prefix openconfig-platform-linecard;
  }

  import openconfig-platform-pipeline-counters {
    prefix openconfig-platform-pipeline-counters;
  }

  import openconfig-platform-port {
    prefix openconfig-platform-port;
  }

  import openconfig-platform-psu {
    prefix openconfig-platform-psu;
  }

  import openconfig-platform-transceiver {
    prefix openconfig-platform-transceiver;
  }

  import openconfig-policy-types {
    prefix openconfig-policy-types;
  }

  import openconfig-qos {
    prefix openconfig-qos;
  }

  import openconfig-routing-policy {
    prefix openconfig-routing-policy;
  }

  import openconfig-sampling {
    prefix openconfig-sampling;
  }

  import openconfig-sampling-sflow {
    prefix openconfig-sampling-sflow;
  }

  import openconfig-system {
    prefix openconfig-system;
  }

  import openconfig-system-bootz {
    prefix openconfig-system-bootz;
  }

  import openconfig-system-controlplane {
    prefix openconfig-system-controlplane;
  }

  import openconfig-system-grpc {
    prefix openconfig-system-grpc;
  }

  import openconfig-system-utilization {
    prefix openconfig-system-utilization;
  }

  import openconfig-terminal-device {
    prefix openconfig-terminal-device;
  }

  import openconfig-types {
    prefix openconfig-types;
  }

  import openconfig-vlan {
    prefix openconfig-vlan;
  }

  import srl_nokia-common {
    prefix srl_nokia-common;
  }

  organization "Nokia";
  contact
    "Nokia SR Linux Support
     Web: <http://www.nokia.com>";
  description
    "This module contains deviations related to openconfig on SR Linux";
  revision 2026-07-31 {
    description "yang deviations";
  }

  deviation "/openconfig-acl:acl/openconfig-acl:acl-sets/openconfig-acl:acl-set/openconfig-acl:acl-entries/openconfig-acl:acl-entry/openconfig-acl:ipv4/openconfig-acl:config/openconfig-acl:destination-address" {
    deviate replace {
      type srl_nokia-common:ipv4-prefix;
    }
  }

  deviation "/openconfig-acl:acl/openconfig-acl:acl-sets/openconfig-acl:acl-set/openconfig-acl:acl-entries/openconfig-acl:acl-entry/openconfig-acl:ipv4/openconfig-acl:config/openconfig-acl:source-address" {
    deviate replace {
      type srl_nokia-common:ipv4-prefix;
    }
  }

  deviation "/openconfig-acl:acl/openconfig-acl:acl-sets/openconfig-acl:acl-set/openconfig-acl:acl-entries/openconfig-acl:acl-entry/openconfig-acl:ipv4/openconfig-acl:state/openconfig-acl:destination-address" {
    deviate replace {
      type srl_nokia-common:ipv4-prefix;
    }
  }

  deviation "/openconfig-acl:acl/openconfig-acl:acl-sets/openconfig-acl:acl-set/openconfig-acl:acl-entries/openconfig-acl:acl-entry/openconfig-acl:ipv4/openconfig-acl:state/openconfig-acl:source-address" {
    deviate replace {
      type srl_nokia-common:ipv4-prefix;
    }
  }

  deviation "/openconfig-acl:acl/openconfig-acl:acl-sets/openconfig-acl:acl-set/openconfig-acl:acl-entries/openconfig-acl:acl-entry/openconfig-acl:ipv6/openconfig-acl:config/openconfig-acl:destination-address" {
    deviate replace {
      type srl_nokia-common:ipv6-prefix;
    }
  }

  deviation "/openconfig-acl:acl/openconfig-acl:acl-sets/openconfig-acl:acl-set/openconfig-acl:acl-entries/openconfig-acl:acl-entry/openconfig-acl:ipv6/openconfig-acl:config/openconfig-acl:source-address" {
    deviate replace {
      type srl_nokia-common:ipv6-prefix;
    }
  }

  deviation "/openconfig-acl:acl/openconfig-acl:acl-sets/openconfig-acl:acl-set/openconfig-acl:acl-entries/openconfig-acl:acl-entry/openconfig-acl:ipv6/openconfig-acl:state/openconfig-acl:destination-address" {
    deviate replace {
      type srl_nokia-common:ipv6-prefix;
    }
  }

  deviation "/openconfig-acl:acl/openconfig-acl:acl-sets/openconfig-acl:acl-set/openconfig-acl:acl-entries/openconfig-acl:acl-entry/openconfig-acl:ipv6/openconfig-acl:state/openconfig-acl:source-address" {
    deviate replace {
      type srl_nokia-common:ipv6-prefix;
    }
  }

  deviation "/openconfig-acl:acl/openconfig-acl:acl-sets/openconfig-acl:acl-set/openconfig-acl:config/openconfig-acl:name" {
    deviate replace {
      type srl_nokia-common:name;
    }
  }

  deviation "/openconfig-acl:acl/openconfig-acl:acl-sets/openconfig-acl:acl-set/openconfig-acl:state/openconfig-acl:name" {
    deviate replace {
      type srl_nokia-common:name;
    }
  }

  deviation "/openconfig-acl:acl/openconfig-acl:interfaces/openconfig-acl:interface/openconfig-acl:config/openconfig-acl:id" {
    deviate replace {
      type srl_nokia-common:name;
    }
  }

  deviation "/openconfig-acl:acl/openconfig-acl:interfaces/openconfig-acl:interface/openconfig-acl:state/openconfig-acl:id" {
    deviate replace {
      type srl_nokia-common:name;
    }
  }

  deviation "/openconfig-defined-sets:defined-sets/openconfig-defined-sets:ipv4-prefix-sets/openconfig-defined-sets:ipv4-prefix-set/openconfig-defined-sets:config/openconfig-defined-sets:prefix" {
    deviate replace {
      type srl_nokia-common:ipv4-prefix;
    }
  }

  deviation "/openconfig-defined-sets:defined-sets/openconfig-defined-sets:ipv4-prefix-sets/openconfig-defined-sets:ipv4-prefix-set/openconfig-defined-sets:state/openconfig-defined-sets:prefix" {
    deviate replace {
      type srl_nokia-common:ipv4-prefix;
    }
  }

  deviation "/openconfig-defined-sets:defined-sets/openconfig-defined-sets:ipv6-prefix-sets/openconfig-defined-sets:ipv6-prefix-set/openconfig-defined-sets:config/openconfig-defined-sets:prefix" {
    deviate replace {
      type srl_nokia-common:ipv6-prefix;
    }
  }

  deviation "/openconfig-defined-sets:defined-sets/openconfig-defined-sets:ipv6-prefix-sets/openconfig-defined-sets:ipv6-prefix-set/openconfig-defined-sets:state/openconfig-defined-sets:prefix" {
    deviate replace {
      type srl_nokia-common:ipv6-prefix;
    }
  }

  deviation "/openconfig-interfaces:interfaces/openconfig-interfaces:interface/openconfig-if-ethernet:ethernet/openconfig-if-ethernet:config/openconfig-if-ethernet:mac-address" {
    deviate replace {
      type srl_nokia-common:mac-address;
    }
  }

  deviation "/openconfig-interfaces:interfaces/openconfig-interfaces:interface/openconfig-if-ethernet:ethernet/openconfig-if-ethernet:state/openconfig-if-ethernet:mac-address" {
    deviate replace {
      type srl_nokia-common:mac-address;
    }
  }

  deviation "/openconfig-interfaces:interfaces/openconfig-interfaces:interface/openconfig-interfaces:config/openconfig-interfaces:name" {
    deviate replace {
      type srl_nokia-common:interface-all;
    }
  }

  deviation "/openconfig-interfaces:interfaces/openconfig-interfaces:interface/openconfig-interfaces:state/openconfig-interfaces:name" {
    deviate replace {
      type srl_nokia-common:interface-all;
    }
  }

  deviation "/openconfig-interfaces:interfaces/openconfig-interfaces:interface/openconfig-interfaces:subinterfaces/openconfig-interfaces:subinterface/openconfig-if-ip:ipv4/openconfig-if-ip:addresses/openconfig-if-ip:address/openconfig-if-ip:config/openconfig-if-ip:ip" {
    deviate replace {
      type srl_nokia-common:ipv4-address;
    }
  }

  deviation "/openconfig-interfaces:interfaces/openconfig-interfaces:interface/openconfig-interfaces:subinterfaces/openconfig-interfaces:subinterface/openconfig-if-ip:ipv4/openconfig-if-ip:addresses/openconfig-if-ip:address/openconfig-if-ip:state/openconfig-if-ip:ip" {
    deviate replace {
      type srl_nokia-common:ipv4-address;
    }
  }

  deviation "/openconfig-interfaces:interfaces/openconfig-interfaces:interface/openconfig-interfaces:subinterfaces/openconfig-interfaces:subinterface/openconfig-if-ip:ipv4/openconfig-if-ip:neighbors/openconfig-if-ip:neighbor/openconfig-if-ip:config/openconfig-if-ip:ip" {
    deviate replace {
      type srl_nokia-common:ipv4-address;
    }
  }

  deviation "/openconfig-interfaces:interfaces/openconfig-interfaces:interface/openconfig-interfaces:subinterfaces/openconfig-interfaces:subinterface/openconfig-if-ip:ipv4/openconfig-if-ip:neighbors/openconfig-if-ip:neighbor/openconfig-if-ip:config/openconfig-if-ip:link-layer-address" {
    deviate replace {
      type srl_nokia-common:mac-address;
    }
  }

  deviation "/openconfig-interfaces:interfaces/openconfig-interfaces:interface/openconfig-interfaces:subinterfaces/openconfig-interfaces:subinterface/openconfig-if-ip:ipv4/openconfig-if-ip:neighbors/openconfig-if-ip:neighbor/openconfig-if-ip:state/openconfig-if-ip:ip" {
    deviate replace {
      type srl_nokia-common:ipv4-address;
    }
  }

  deviation "/openconfig-interfaces:interfaces/openconfig-interfaces:interface/openconfig-interfaces:subinterfaces/openconfig-interfaces:subinterface/openconfig-if-ip:ipv4/openconfig-if-ip:neighbors/openconfig-if-ip:neighbor/openconfig-if-ip:state/openconfig-if-ip:link-layer-address" {
    deviate replace {
      type srl_nokia-common:mac-address;
    }
  }

  deviation "/openconfig-interfaces:interfaces/openconfig-interfaces:interface/openconfig-interfaces:subinterfaces/openconfig-interfaces:subinterface/openconfig-if-ip:ipv6/openconfig-if-ip:addresses/openconfig-if-ip:address/openconfig-if-ip:config/openconfig-if-ip:ip" {
    deviate replace {
      type srl_nokia-common:ipv6-address;
    }
  }

  deviation "/openconfig-interfaces:interfaces/openconfig-interfaces:interface/openconfig-interfaces:subinterfaces/openconfig-interfaces:subinterface/openconfig-if-ip:ipv6/openconfig-if-ip:addresses/openconfig-if-ip:address/openconfig-if-ip:state/openconfig-if-ip:ip" {
    deviate replace {
      type srl_nokia-common:ipv6-address;
    }
  }

  deviation "/openconfig-interfaces:interfaces/openconfig-interfaces:interface/openconfig-interfaces:subinterfaces/openconfig-interfaces:subinterface/openconfig-if-ip:ipv6/openconfig-if-ip:config/openconfig-if-ip:mtu" {
    deviate replace {
      type uint16;
    }
  }

  deviation "/openconfig-interfaces:interfaces/openconfig-interfaces:interface/openconfig-interfaces:subinterfaces/openconfig-interfaces:subinterface/openconfig-if-ip:ipv6/openconfig-if-ip:neighbors/openconfig-if-ip:neighbor/openconfig-if-ip:config/openconfig-if-ip:ip" {
    deviate replace {
      type srl_nokia-common:ipv6-address;
    }
  }

  deviation "/openconfig-interfaces:interfaces/openconfig-interfaces:interface/openconfig-interfaces:subinterfaces/openconfig-interfaces:subinterface/openconfig-if-ip:ipv6/openconfig-if-ip:neighbors/openconfig-if-ip:neighbor/openconfig-if-ip:config/openconfig-if-ip:link-layer-address" {
    deviate replace {
      type srl_nokia-common:mac-address;
    }
  }

  deviation "/openconfig-interfaces:interfaces/openconfig-interfaces:interface/openconfig-interfaces:subinterfaces/openconfig-interfaces:subinterface/openconfig-if-ip:ipv6/openconfig-if-ip:neighbors/openconfig-if-ip:neighbor/openconfig-if-ip:state/openconfig-if-ip:ip" {
    deviate replace {
      type srl_nokia-common:ipv6-address;
    }
  }

  deviation "/openconfig-interfaces:interfaces/openconfig-interfaces:interface/openconfig-interfaces:subinterfaces/openconfig-interfaces:subinterface/openconfig-if-ip:ipv6/openconfig-if-ip:neighbors/openconfig-if-ip:neighbor/openconfig-if-ip:state/openconfig-if-ip:link-layer-address" {
    deviate replace {
      type srl_nokia-common:mac-address;
    }
  }

  deviation "/openconfig-interfaces:interfaces/openconfig-interfaces:interface/openconfig-interfaces:subinterfaces/openconfig-interfaces:subinterface/openconfig-if-ip:ipv6/openconfig-if-ip:state/openconfig-if-ip:mtu" {
    deviate replace {
      type uint16;
    }
  }

  deviation "/openconfig-lldp:lldp/openconfig-lldp:interfaces/openconfig-lldp:interface/openconfig-lldp:config/openconfig-lldp:name" {
    deviate replace {
      type srl_nokia-common:interface-all;
    }
  }

  deviation "/openconfig-lldp:lldp/openconfig-lldp:interfaces/openconfig-lldp:interface/openconfig-lldp:state/openconfig-lldp:name" {
    deviate replace {
      type srl_nokia-common:interface-all;
    }
  }

  deviation "/openconfig-network-instance:network-instances/openconfig-network-instance:network-instance/openconfig-network-instance:afts/openconfig-network-instance:ipv4-unicast/openconfig-network-instance:ipv4-entry/openconfig-network-instance:state/openconfig-network-instance:prefix" {
    deviate replace {
      type srl_nokia-common:ip-prefix;
    }
  }

  deviation "/openconfig-network-instance:network-instances/openconfig-network-instance:network-instance/openconfig-network-instance:afts/openconfig-network-instance:ipv6-unicast/openconfig-network-instance:ipv6-entry/openconfig-network-instance:state/openconfig-network-instance:prefix" {
    deviate replace {
      type srl_nokia-common:ip-prefix;
    }
  }

  deviation "/openconfig-network-instance:network-instances/openconfig-network-instance:network-instance/openconfig-network-instance:afts/openconfig-network-instance:next-hops/openconfig-network-instance:next-hop/openconfig-network-instance:encap-headers/openconfig-network-instance:encap-header/openconfig-network-instance:gre/openconfig-network-instance:state/openconfig-network-instance:dst-ip" {
    deviate replace {
      type srl_nokia-common:ip-address;
    }
  }

  deviation "/openconfig-network-instance:network-instances/openconfig-network-instance:network-instance/openconfig-network-instance:afts/openconfig-network-instance:next-hops/openconfig-network-instance:next-hop/openconfig-network-instance:encap-headers/openconfig-network-instance:encap-header/openconfig-network-instance:gre/openconfig-network-instance:state/openconfig-network-instance:src-ip" {
    deviate replace {
      type srl_nokia-common:ip-address;
    }
  }

  deviation "/openconfig-network-instance:network-instances/openconfig-network-instance:network-instance/openconfig-network-instance:afts/openconfig-network-instance:next-hops/openconfig-network-instance:next-hop/openconfig-network-instance:encap-headers/openconfig-network-instance:encap-header/openconfig-network-instance:ipv4/openconfig-network-instance:state/openconfig-network-instance:dst-ip" {
    deviate replace {
      type srl_nokia-common:ipv4-address;
    }
  }

  deviation "/openconfig-network-instance:network-instances/openconfig-network-instance:network-instance/openconfig-network-instance:afts/openconfig-network-instance:next-hops/openconfig-network-instance:next-hop/openconfig-network-instance:encap-headers/openconfig-network-instance:encap-header/openconfig-network-instance:ipv4/openconfig-network-instance:state/openconfig-network-instance:src-ip" {
    deviate replace {
      type srl_nokia-common:ipv4-address;
    }
  }

  deviation "/openconfig-network-instance:network-instances/openconfig-network-instance:network-instance/openconfig-network-instance:afts/openconfig-network-instance:next-hops/openconfig-network-instance:next-hop/openconfig-network-instance:encap-headers/openconfig-network-instance:encap-header/openconfig-network-instance:ipv6/openconfig-network-instance:state/openconfig-network-instance:dst-ip" {
    deviate replace {
      type srl_nokia-common:ipv6-address;
    }
  }

  deviation "/openconfig-network-instance:network-instances/openconfig-network-instance:network-instance/openconfig-network-instance:afts/openconfig-network-instance:next-hops/openconfig-network-instance:next-hop/openconfig-network-instance:encap-headers/openconfig-network-instance:encap-header/openconfig-network-instance:ipv6/openconfig-network-instance:state/openconfig-network-instance:src-ip" {
    deviate replace {
      type srl_nokia-common:ipv6-address;
    }
  }

  deviation "/openconfig-network-instance:network-instances/openconfig-network-instance:network-instance/openconfig-network-instance:afts/openconfig-network-instance:next-hops/openconfig-network-instance:next-hop/openconfig-network-instance:encap-headers/openconfig-network-instance:encap-header/openconfig-network-instance:state/openconfig-network-instance:type" {
    deviate replace {
      type srl_nokia-common:encapsulation-header-type;
    }
  }

  deviation "/openconfig-network-instance:network-instances/openconfig-network-instance:network-instance/openconfig-network-instance:afts/openconfig-network-instance:next-hops/openconfig-network-instance:next-hop/openconfig-network-instance:encap-headers/openconfig-network-instance:encap-header/openconfig-network-instance:udp-v4/openconfig-network-instance:state/openconfig-network-instance:dst-ip" {
    deviate replace {
      type srl_nokia-common:ipv4-address;
    }
  }

  deviation "/openconfig-network-instance:network-instances/openconfig-network-instance:network-instance/openconfig-network-instance:afts/openconfig-network-instance:next-hops/openconfig-network-instance:next-hop/openconfig-network-instance:encap-headers/openconfig-network-instance:encap-header/openconfig-network-instance:udp-v4/openconfig-network-instance:state/openconfig-network-instance:src-ip" {
    deviate replace {
      type srl_nokia-common:ipv4-address;
    }
  }

  deviation "/openconfig-network-instance:network-instances/openconfig-network-instance:network-instance/openconfig-network-instance:afts/openconfig-network-instance:next-hops/openconfig-network-instance:next-hop/openconfig-network-instance:encap-headers/openconfig-network-instance:encap-header/openconfig-network-instance:udp-v6/openconfig-network-instance:state/openconfig-network-instance:dst-ip" {
    deviate replace {
      type srl_nokia-common:ipv6-address;
    }
  }

  deviation "/openconfig-network-instance:network-instances/openconfig-network-instance:network-instance/openconfig-network-instance:afts/openconfig-network-instance:next-hops/openconfig-network-instance:next-hop/openconfig-network-instance:encap-headers/openconfig-network-instance:encap-header/openconfig-network-instance:udp-v6/openconfig-network-instance:state/openconfig-network-instance:src-ip" {
    deviate replace {
      type srl_nokia-common:ipv6-address;
    }
  }

  deviation "/openconfig-network-instance:network-instances/openconfig-network-instance:network-instance/openconfig-network-instance:afts/openconfig-network-instance:next-hops/openconfig-network-instance:next-hop/openconfig-network-instance:state/openconfig-network-instance:mac-address" {
    deviate replace {
      type srl_nokia-common:mac-address;
    }
  }

  deviation "/openconfig-network-instance:network-instances/openconfig-network-instance:network-instance/openconfig-network-instance:policy-forwarding/openconfig-network-instance:policies/openconfig-network-instance:policy/openconfig-network-instance:rules/openconfig-network-instance:rule/openconfig-network-instance:config/openconfig-network-instance:sequence-id" {
    deviate replace {
      type srl_nokia-common:rule-sequence-id;
    }
  }

  deviation "/openconfig-network-instance:network-instances/openconfig-network-instance:network-instance/openconfig-network-instance:policy-forwarding/openconfig-network-instance:policies/openconfig-network-instance:policy/openconfig-network-instance:rules/openconfig-network-instance:rule/openconfig-network-instance:state/openconfig-network-instance:sequence-id" {
    deviate replace {
      type srl_nokia-common:rule-sequence-id;
    }
  }

  deviation "/openconfig-network-instance:network-instances/openconfig-network-instance:network-instance/openconfig-network-instance:protocols/openconfig-network-instance:protocol/openconfig-network-instance:bgp/openconfig-network-instance:global/openconfig-network-instance:dynamic-neighbor-prefixes/openconfig-network-instance:dynamic-neighbor-prefix/openconfig-network-instance:config/openconfig-network-instance:prefix" {
    deviate replace {
      type srl_nokia-common:ip-prefix;
    }
  }

  deviation "/openconfig-network-instance:network-instances/openconfig-network-instance:network-instance/openconfig-network-instance:protocols/openconfig-network-instance:protocol/openconfig-network-instance:bgp/openconfig-network-instance:global/openconfig-network-instance:dynamic-neighbor-prefixes/openconfig-network-instance:dynamic-neighbor-prefix/openconfig-network-instance:state/openconfig-network-instance:prefix" {
    deviate replace {
      type srl_nokia-common:ip-prefix;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:config/openconfig-network-instance:auth-password" {
    deviate replace {
      type srl_nokia-common:routing-password;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:config/openconfig-network-instance:neighbor-address" {
    deviate replace {
      type srl_nokia-common:ip-address-with-zone;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:state/openconfig-network-instance:auth-password" {
    deviate replace {
      type srl_nokia-common:routing-password;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:state/openconfig-network-instance:neighbor-address" {
    deviate replace {
      type srl_nokia-common:ip-address-with-zone;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:transport/openconfig-network-instance:config/openconfig-network-instance:local-address" {
    deviate replace {
      type union {
        type srl_nokia-common:ip-address;
        type string;
      }
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:transport/openconfig-network-instance:state/openconfig-network-instance:local-address" {
    deviate replace {
      type union {
        type srl_nokia-common:ip-address;
        type string;
      }
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:config/openconfig-network-instance:auth-password" {
    deviate replace {
      type srl_nokia-common:routing-password;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:state/openconfig-network-instance:auth-password" {
    deviate replace {
      type srl_nokia-common:routing-password;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:transport/openconfig-network-instance:config/openconfig-network-instance:local-address" {
    deviate replace {
      type union {
        type srl_nokia-common:ip-address;
        type string;
      }
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:transport/openconfig-network-instance:state/openconfig-network-instance:local-address" {
    deviate replace {
      type union {
        type srl_nokia-common:ip-address;
        type string;
      }
    }
  }

  deviation "/openconfig-network-instance:network-instances/openconfig-network-instance:network-instance/openconfig-network-instance:protocols/openconfig-network-instance:protocol/openconfig-network-instance:bgp/openconfig-network-instance:rib/openconfig-network-instance:attr-sets/openconfig-network-instance:attr-set/openconfig-network-instance:state/openconfig-network-instance:cluster-list" {
    deviate replace {
      type srl_nokia-common:ip-address;
    }
  }

  deviation "/openconfig-network-instance:network-instances/openconfig-network-instance:network-instance/openconfig-network-instance:protocols/openconfig-network-instance:protocol/openconfig-network-instance:bgp/openconfig-network-instance:rib/openconfig-network-instance:attr-sets/openconfig-network-instance:attr-set/openconfig-network-instance:state/openconfig-network-instance:next-hop" {
    deviate replace {
      type srl_nokia-common:ip-address-with-zone;
    }
  }

  deviation "/openconfig-network-instance:network-instances/openconfig-network-instance:network-instance/openconfig-network-instance:protocols/openconfig-network-instance:protocol/openconfig-network-instance:isis/openconfig-network-instance:interfaces/openconfig-network-instance:interface/openconfig-network-instance:authentication/openconfig-network-instance:config/openconfig-network-instance:auth-password" {
    deviate replace {
      type srl_nokia-common:routing-password;
    }
  }

  deviation "/openconfig-network-instance:network-instances/openconfig-network-instance:network-instance/openconfig-network-instance:protocols/openconfig-network-instance:protocol/openconfig-network-instance:isis/openconfig-network-instance:interfaces/openconfig-network-instance:interface/openconfig-network-instance:authentication/openconfig-network-instance:state/openconfig-network-instance:auth-password" {
    deviate replace {
      type srl_nokia-common:routing-password;
    }
  }

  deviation "/openconfig-network-instance:network-instances/openconfig-network-instance:network-instance/openconfig-network-instance:protocols/openconfig-network-instance:protocol/openconfig-network-instance:isis/openconfig-network-instance:interfaces/openconfig-network-instance:interface/openconfig-network-instance:levels/openconfig-network-instance:level/openconfig-network-instance:hello-authentication/openconfig-network-instance:config/openconfig-network-instance:auth-password" {
    deviate replace {
      type srl_nokia-common:routing-password;
    }
  }

  deviation "/openconfig-network-instance:network-instances/openconfig-network-instance:network-instance/openconfig-network-instance:protocols/openconfig-network-instance:protocol/openconfig-network-instance:isis/openconfig-network-instance:levels/openconfig-network-instance:level/openconfig-network-instance:authentication/openconfig-network-instance:config/openconfig-network-instance:auth-password" {
    deviate replace {
      type srl_nokia-common:routing-password;
    }
  }

  deviation "/openconfig-network-instance:network-instances/openconfig-network-instance:network-instance/openconfig-network-instance:protocols/openconfig-network-instance:protocol/openconfig-network-instance:isis/openconfig-network-instance:levels/openconfig-network-instance:level/openconfig-network-instance:authentication/openconfig-network-instance:state/openconfig-network-instance:auth-password" {
    deviate replace {
      type srl_nokia-common:routing-password;
    }
  }

  deviation "/openconfig-network-instance:network-instances/openconfig-network-instance:network-instance/openconfig-network-instance:protocols/openconfig-network-instance:protocol/openconfig-network-instance:isis/openconfig-network-instance:levels/openconfig-network-instance:level/openconfig-network-instance:link-state-database/openconfig-network-instance:lsp/openconfig-network-instance:lsp-id" {
    deviate replace {
      type srl_nokia-common:isis-lsp-id;
    }
  }

  deviation "/openconfig-network-instance:network-instances/openconfig-network-instance:network-instance/openconfig-network-instance:protocols/openconfig-network-instance:protocol/openconfig-network-instance:isis/openconfig-network-instance:levels/openconfig-network-instance:level/openconfig-network-instance:link-state-database/openconfig-network-instance:lsp/openconfig-network-instance:tlvs/openconfig-network-instance:tlv/openconfig-network-instance:extended-ipv4-reachability/openconfig-network-instance:prefixes/openconfig-network-instance:prefix/openconfig-network-instance:state/openconfig-network-instance:prefix" {
    deviate replace {
      type srl_nokia-common:ip-prefix;
    }
  }

  deviation "/openconfig-network-instance:network-instances/openconfig-network-instance:network-instance/openconfig-network-instance:protocols/openconfig-network-instance:protocol/openconfig-network-instance:isis/openconfig-network-instance:levels/openconfig-network-instance:level/openconfig-network-instance:link-state-database/openconfig-network-instance:lsp/openconfig-network-instance:tlvs/openconfig-network-instance:tlv/openconfig-network-instance:extended-is-reachability/openconfig-network-instance:neighbors/openconfig-network-instance:neighbor/openconfig-network-instance:instances/openconfig-network-instance:instance/openconfig-network-instance:subtlvs/openconfig-network-instance:subtlv/openconfig-network-instance:ipv4-interface-address/openconfig-network-instance:state/openconfig-network-instance:address" {
    deviate replace {
      type srl_nokia-common:ip-address;
    }
  }

  deviation "/openconfig-network-instance:network-instances/openconfig-network-instance:network-instance/openconfig-network-instance:protocols/openconfig-network-instance:protocol/openconfig-network-instance:isis/openconfig-network-instance:levels/openconfig-network-instance:level/openconfig-network-instance:link-state-database/openconfig-network-instance:lsp/openconfig-network-instance:tlvs/openconfig-network-instance:tlv/openconfig-network-instance:extended-is-reachability/openconfig-network-instance:neighbors/openconfig-network-instance:neighbor/openconfig-network-instance:instances/openconfig-network-instance:instance/openconfig-network-instance:subtlvs/openconfig-network-instance:subtlv/openconfig-network-instance:ipv4-neighbor-address/openconfig-network-instance:state/openconfig-network-instance:address" {
    deviate replace {
      type srl_nokia-common:ip-address;
    }
  }

  deviation "/openconfig-network-instance:network-instances/openconfig-network-instance:network-instance/openconfig-network-instance:protocols/openconfig-network-instance:protocol/openconfig-network-instance:isis/openconfig-network-instance:levels/openconfig-network-instance:level/openconfig-network-instance:link-state-database/openconfig-network-instance:lsp/openconfig-network-instance:tlvs/openconfig-network-instance:tlv/openconfig-network-instance:extended-is-reachability/openconfig-network-instance:neighbors/openconfig-network-instance:neighbor/openconfig-network-instance:instances/openconfig-network-instance:instance/openconfig-network-instance:subtlvs/openconfig-network-instance:subtlv/openconfig-network-instance:ipv6-interface-address/openconfig-network-instance:state/openconfig-network-instance:address" {
    deviate replace {
      type srl_nokia-common:ip-address;
    }
  }

  deviation "/openconfig-network-instance:network-instances/openconfig-network-instance:network-instance/openconfig-network-instance:protocols/openconfig-network-instance:protocol/openconfig-network-instance:isis/openconfig-network-instance:levels/openconfig-network-instance:level/openconfig-network-instance:link-state-database/openconfig-network-instance:lsp/openconfig-network-instance:tlvs/openconfig-network-instance:tlv/openconfig-network-instance:extended-is-reachability/openconfig-network-instance:neighbors/openconfig-network-instance:neighbor/openconfig-network-instance:instances/openconfig-network-instance:instance/openconfig-network-instance:subtlvs/openconfig-network-instance:subtlv/openconfig-network-instance:ipv6-neighbor-address/openconfig-network-instance:state/openconfig-network-instance:address" {
    deviate replace {
      type srl_nokia-common:ip-address;
    }
  }

  deviation "/openconfig-network-instance:network-instances/openconfig-network-instance:network-instance/openconfig-network-instance:protocols/openconfig-network-instance:protocol/openconfig-network-instance:isis/openconfig-network-instance:levels/openconfig-network-instance:level/openconfig-network-instance:link-state-database/openconfig-network-instance:lsp/openconfig-network-instance:tlvs/openconfig-network-instance:tlv/openconfig-network-instance:ipv4-external-reachability/openconfig-network-instance:prefixes/openconfig-network-instance:prefix/openconfig-network-instance:state/openconfig-network-instance:prefix" {
    deviate replace {
      type srl_nokia-common:ip-prefix;
    }
  }

  deviation "/openconfig-network-instance:network-instances/openconfig-network-instance:network-instance/openconfig-network-instance:protocols/openconfig-network-instance:protocol/openconfig-network-instance:isis/openconfig-network-instance:levels/openconfig-network-instance:level/openconfig-network-instance:link-state-database/openconfig-network-instance:lsp/openconfig-network-instance:tlvs/openconfig-network-instance:tlv/openconfig-network-instance:ipv4-interface-addresses/openconfig-network-instance:state/openconfig-network-instance:address" {
    deviate replace {
      type srl_nokia-common:ip-address;
    }
  }

  deviation "/openconfig-network-instance:network-instances/openconfig-network-instance:network-instance/openconfig-network-instance:protocols/openconfig-network-instance:protocol/openconfig-network-instance:isis/openconfig-network-instance:levels/openconfig-network-instance:level/openconfig-network-instance:link-state-database/openconfig-network-instance:lsp/openconfig-network-instance:tlvs/openconfig-network-instance:tlv/openconfig-network-instance:ipv4-internal-reachability/openconfig-network-instance:prefixes/openconfig-network-instance:prefix/openconfig-network-instance:state/openconfig-network-instance:prefix" {
    deviate replace {
      type srl_nokia-common:ip-prefix;
    }
  }

  deviation "/openconfig-network-instance:network-instances/openconfig-network-instance:network-instance/openconfig-network-instance:protocols/openconfig-network-instance:protocol/openconfig-network-instance:isis/openconfig-network-instance:levels/openconfig-network-instance:level/openconfig-network-instance:link-state-database/openconfig-network-instance:lsp/openconfig-network-instance:tlvs/openconfig-network-instance:tlv/openconfig-network-instance:ipv4-te-router-id/openconfig-network-instance:state/openconfig-network-instance:router-id" {
    deviate replace {
      type srl_nokia-common:ip-address;
    }
  }

  deviation "/openconfig-network-instance:network-instances/openconfig-network-instance:network-instance/openconfig-network-instance:protocols/openconfig-network-instance:protocol/openconfig-network-instance:isis/openconfig-network-instance:levels/openconfig-network-instance:level/openconfig-network-instance:link-state-database/openconfig-network-instance:lsp/openconfig-network-instance:tlvs/openconfig-network-instance:tlv/openconfig-network-instance:ipv6-interface-addresses/openconfig-network-instance:state/openconfig-network-instance:address" {
    deviate replace {
      type srl_nokia-common:ip-address;
    }
  }

  deviation "/openconfig-network-instance:network-instances/openconfig-network-instance:network-instance/openconfig-network-instance:protocols/openconfig-network-instance:protocol/openconfig-network-instance:isis/openconfig-network-instance:levels/openconfig-network-instance:level/openconfig-network-instance:link-state-database/openconfig-network-instance:lsp/openconfig-network-instance:tlvs/openconfig-network-instance:tlv/openconfig-network-instance:ipv6-reachability/openconfig-network-instance:prefixes/openconfig-network-instance:prefix/openconfig-network-instance:state/openconfig-network-instance:prefix" {
    deviate replace {
      type srl_nokia-common:ip-prefix;
    }
  }

  deviation "/openconfig-network-instance:network-instances/openconfig-network-instance:network-instance/openconfig-network-instance:protocols/openconfig-network-instance:protocol/openconfig-network-instance:isis/openconfig-network-instance:levels/openconfig-network-instance:level/openconfig-network-instance:link-state-database/openconfig-network-instance:lsp/openconfig-network-instance:tlvs/openconfig-network-instance:tlv/openconfig-network-instance:ipv6-te-router-id/openconfig-network-instance:state/openconfig-network-instance:router-id" {
    deviate replace {
      type srl_nokia-common:ip-address;
    }
  }

  deviation "/openconfig-network-instance:network-instances/openconfig-network-instance:network-instance/openconfig-network-instance:protocols/openconfig-network-instance:protocol/openconfig-network-instance:isis/openconfig-network-instance:levels/openconfig-network-instance:level/openconfig-network-instance:link-state-database/openconfig-network-instance:lsp/openconfig-network-instance:tlvs/openconfig-network-instance:tlv/openconfig-network-instance:mt-ipv4-reachability/openconfig-network-instance:prefixes/openconfig-network-instance:prefix/openconfig-network-instance:prefix" {
    deviate replace {
      type srl_nokia-common:ip-prefix;
    }
  }

  deviation "/openconfig-network-instance:network-instances/openconfig-network-instance:network-instance/openconfig-network-instance:protocols/openconfig-network-instance:protocol/openconfig-network-instance:isis/openconfig-network-instance:levels/openconfig-network-instance:level/openconfig-network-instance:link-state-database/openconfig-network-instance:lsp/openconfig-network-instance:tlvs/openconfig-network-instance:tlv/openconfig-network-instance:mt-ipv4-reachability/openconfig-network-instance:prefixes/openconfig-network-instance:prefix/openconfig-network-instance:state/openconfig-network-instance:prefix" {
    deviate replace {
      type srl_nokia-common:ip-prefix;
    }
  }

  deviation "/openconfig-network-instance:network-instances/openconfig-network-instance:network-instance/openconfig-network-instance:protocols/openconfig-network-instance:protocol/openconfig-network-instance:isis/openconfig-network-instance:levels/openconfig-network-instance:level/openconfig-network-instance:link-state-database/openconfig-network-instance:lsp/openconfig-network-instance:tlvs/openconfig-network-instance:tlv/openconfig-network-instance:mt-ipv6-reachability/openconfig-network-instance:prefixes/openconfig-network-instance:prefix/openconfig-network-instance:prefix" {
    deviate replace {
      type srl_nokia-common:ip-prefix;
    }
  }

  deviation "/openconfig-network-instance:network-instances/openconfig-network-instance:network-instance/openconfig-network-instance:protocols/openconfig-network-instance:protocol/openconfig-network-instance:isis/openconfig-network-instance:levels/openconfig-network-instance:level/openconfig-network-instance:link-state-database/openconfig-network-instance:lsp/openconfig-network-instance:tlvs/openconfig-network-instance:tlv/openconfig-network-instance:mt-isn/openconfig-network-instance:neighbors/openconfig-network-instance:neighbor/openconfig-network-instance:instances/openconfig-network-instance:instance/openconfig-network-instance:subtlvs/openconfig-network-instance:subtlv/openconfig-network-instance:ipv4-interface-address/openconfig-network-instance:state/openconfig-network-instance:address" {
    deviate replace {
      type srl_nokia-common:ip-address;
    }
  }

  deviation "/openconfig-network-instance:network-instances/openconfig-network-instance:network-instance/openconfig-network-instance:protocols/openconfig-network-instance:protocol/openconfig-network-instance:isis/openconfig-network-instance:levels/openconfig-network-instance:level/openconfig-network-instance:link-state-database/openconfig-network-instance:lsp/openconfig-network-instance:tlvs/openconfig-network-instance:tlv/openconfig-network-instance:mt-isn/openconfig-network-instance:neighbors/openconfig-network-instance:neighbor/openconfig-network-instance:instances/openconfig-network-instance:instance/openconfig-network-instance:subtlvs/openconfig-network-instance:subtlv/openconfig-network-instance:ipv4-neighbor-address/openconfig-network-instance:state/openconfig-network-instance:address" {
    deviate replace {
      type srl_nokia-common:ip-address;
    }
  }

  deviation "/openconfig-network-instance:network-instances/openconfig-network-instance:network-instance/openconfig-network-instance:protocols/openconfig-network-instance:protocol/openconfig-network-instance:isis/openconfig-network-instance:levels/openconfig-network-instance:level/openconfig-network-instance:link-state-database/openconfig-network-instance:lsp/openconfig-network-instance:tlvs/openconfig-network-instance:tlv/openconfig-network-instance:mt-isn/openconfig-network-instance:neighbors/openconfig-network-instance:neighbor/openconfig-network-instance:instances/openconfig-network-instance:instance/openconfig-network-instance:subtlvs/openconfig-network-instance:subtlv/openconfig-network-instance:ipv6-interface-address/openconfig-network-instance:state/openconfig-network-instance:address" {
    deviate replace {
      type srl_nokia-common:ip-address;
    }
  }

  deviation "/openconfig-network-instance:network-instances/openconfig-network-instance:network-instance/openconfig-network-instance:protocols/openconfig-network-instance:protocol/openconfig-network-instance:isis/openconfig-network-instance:levels/openconfig-network-instance:level/openconfig-network-instance:link-state-database/openconfig-network-instance:lsp/openconfig-network-instance:tlvs/openconfig-network-instance:tlv/openconfig-network-instance:mt-isn/openconfig-network-instance:neighbors/openconfig-network-instance:neighbor/openconfig-network-instance:instances/openconfig-network-instance:instance/openconfig-network-instance:subtlvs/openconfig-network-instance:subtlv/openconfig-network-instance:ipv6-neighbor-address/openconfig-network-instance:state/openconfig-network-instance:address" {
    deviate replace {
      type srl_nokia-common:ip-address;
    }
  }

  deviation "/openconfig-network-instance:network-instances/openconfig-network-instance:network-instance/openconfig-network-instance:protocols/openconfig-network-instance:protocol/openconfig-network-instance:local-aggregates/openconfig-network-instance:aggregate/openconfig-network-instance:config/openconfig-network-instance:prefix" {
    deviate replace {
      type srl_nokia-common:ip-prefix;
    }
  }

  deviation "/openconfig-network-instance:network-instances/openconfig-network-instance:network-instance/openconfig-network-instance:protocols/openconfig-network-instance:protocol/openconfig-network-instance:local-aggregates/openconfig-network-instance:aggregate/openconfig-network-instance:state/openconfig-network-instance:prefix" {
    deviate replace {
      type srl_nokia-common:ip-prefix;
    }
  }

  deviation "/openconfig-network-instance:network-instances/openconfig-network-instance:network-instance/openconfig-network-instance:protocols/openconfig-network-instance:protocol/openconfig-network-instance:static-routes/openconfig-network-instance:static/openconfig-network-instance:config/openconfig-network-instance:prefix" {
    deviate replace {
      type srl_nokia-common:ip-prefix;
    }
  }

  deviation "/openconfig-network-instance:network-instances/openconfig-network-instance:network-instance/openconfig-network-instance:protocols/openconfig-network-instance:protocol/openconfig-network-instance:static-routes/openconfig-network-instance:static/openconfig-network-instance:state/openconfig-network-instance:prefix" {
    deviate replace {
      type srl_nokia-common:ip-prefix;
    }
  }

  deviation "/openconfig-network-instance:network-instances/openconfig-network-instance:network-instance/openconfig-network-instance:table-connections/openconfig-network-instance:table-connection/openconfig-network-instance:config/openconfig-network-instance:address-family" {
    deviate replace {
      type identityref { base openconfig-types:ADDRESS_FAMILY;}
    }
  }

  deviation "/openconfig-network-instance:network-instances/openconfig-network-instance:network-instance/openconfig-network-instance:table-connections/openconfig-network-instance:table-connection/openconfig-network-instance:config/openconfig-network-instance:dst-protocol" {
    deviate replace {
      type identityref { base openconfig-policy-types:INSTALL_PROTOCOL_TYPE;}
    }
  }

  deviation "/openconfig-network-instance:network-instances/openconfig-network-instance:network-instance/openconfig-network-instance:table-connections/openconfig-network-instance:table-connection/openconfig-network-instance:config/openconfig-network-instance:src-protocol" {
    deviate replace {
      type identityref { base openconfig-policy-types:INSTALL_PROTOCOL_TYPE;}
    }
  }

  deviation "/openconfig-network-instance:network-instances/openconfig-network-instance:network-instance/openconfig-network-instance:table-connections/openconfig-network-instance:table-connection/openconfig-network-instance:state/openconfig-network-instance:address-family" {
    deviate replace {
      type identityref { base openconfig-types:ADDRESS_FAMILY;}
    }
  }

  deviation "/openconfig-network-instance:network-instances/openconfig-network-instance:network-instance/openconfig-network-instance:table-connections/openconfig-network-instance:table-connection/openconfig-network-instance:state/openconfig-network-instance:dst-protocol" {
    deviate replace {
      type identityref { base openconfig-policy-types:INSTALL_PROTOCOL_TYPE;}
    }
  }

  deviation "/openconfig-network-instance:network-instances/openconfig-network-instance:network-instance/openconfig-network-instance:table-connections/openconfig-network-instance:table-connection/openconfig-network-instance:state/openconfig-network-instance:src-protocol" {
    deviate replace {
      type identityref { base openconfig-policy-types:INSTALL_PROTOCOL_TYPE;}
    }
  }

  deviation "/openconfig-platform:components/openconfig-platform:component/openconfig-platform:config/openconfig-platform:name" {
    deviate replace {
      type srl_nokia-common:component-name;
    }
  }

  deviation "/openconfig-platform:components/openconfig-platform:component/openconfig-platform:state/openconfig-platform:base-mac-address" {
    deviate replace {
      type srl_nokia-common:mac-address;
    }
  }

  deviation "/openconfig-platform:components/openconfig-platform:component/openconfig-platform:state/openconfig-platform:name" {
    deviate replace {
      type srl_nokia-common:component-name;
    }
  }

  deviation "/openconfig-routing-policy:routing-policy/openconfig-routing-policy:defined-sets/openconfig-routing-policy:prefix-sets/openconfig-routing-policy:prefix-set/openconfig-routing-policy:prefixes/openconfig-routing-policy:prefix/openconfig-routing-policy:config/openconfig-routing-policy:ip-prefix" {
    deviate replace {
      type srl_nokia-common:ip-prefix;
    }
  }

  deviation "/openconfig-routing-policy:routing-policy/openconfig-routing-policy:defined-sets/openconfig-routing-policy:prefix-sets/openconfig-routing-policy:prefix-set/openconfig-routing-policy:prefixes/openconfig-routing-policy:prefix/openconfig-routing-policy:state/openconfig-routing-policy:ip-prefix" {
    deviate replace {
      type srl_nokia-common:ip-prefix;
    }
  }

  deviation "/openconfig-routing-policy:routing-policy/openconfig-routing-policy:policy-definitions/openconfig-routing-policy:policy-definition/openconfig-routing-policy:statements/openconfig-routing-policy:statement/openconfig-routing-policy:actions/openconfig-bgp-policy:bgp-actions/openconfig-bgp-policy:config/openconfig-bgp-policy:set-next-hop" {
    deviate replace {
      type srl_nokia-common:bgp-next-hop-type;
    }
  }

  deviation "/openconfig-routing-policy:routing-policy/openconfig-routing-policy:policy-definitions/openconfig-routing-policy:policy-definition/openconfig-routing-policy:statements/openconfig-routing-policy:statement/openconfig-routing-policy:actions/openconfig-bgp-policy:bgp-actions/openconfig-bgp-policy:state/openconfig-bgp-policy:set-next-hop" {
    deviate replace {
      type srl_nokia-common:bgp-next-hop-type;
    }
  }

  deviation "/openconfig-sampling:sampling/openconfig-sampling-sflow:sflow/openconfig-sampling-sflow:collectors/openconfig-sampling-sflow:collector/openconfig-sampling-sflow:config/openconfig-sampling-sflow:address" {
    deviate replace {
      type srl_nokia-common:ip-address;
    }
  }

  deviation "/openconfig-sampling:sampling/openconfig-sampling-sflow:sflow/openconfig-sampling-sflow:collectors/openconfig-sampling-sflow:collector/openconfig-sampling-sflow:config/openconfig-sampling-sflow:source-address" {
    deviate replace {
      type srl_nokia-common:ip-address;
    }
  }

  deviation "/openconfig-sampling:sampling/openconfig-sampling-sflow:sflow/openconfig-sampling-sflow:collectors/openconfig-sampling-sflow:collector/openconfig-sampling-sflow:state/openconfig-sampling-sflow:address" {
    deviate replace {
      type srl_nokia-common:ip-address;
    }
  }

  deviation "/openconfig-sampling:sampling/openconfig-sampling-sflow:sflow/openconfig-sampling-sflow:collectors/openconfig-sampling-sflow:collector/openconfig-sampling-sflow:state/openconfig-sampling-sflow:source-address" {
    deviate replace {
      type srl_nokia-common:ip-address;
    }
  }

  deviation "/openconfig-sampling:sampling/openconfig-sampling-sflow:sflow/openconfig-sampling-sflow:interfaces/openconfig-sampling-sflow:interface/openconfig-sampling-sflow:config/openconfig-sampling-sflow:name" {
    deviate replace {
      type srl_nokia-common:interface-all;
    }
  }

  deviation "/openconfig-sampling:sampling/openconfig-sampling-sflow:sflow/openconfig-sampling-sflow:interfaces/openconfig-sampling-sflow:interface/openconfig-sampling-sflow:state/openconfig-sampling-sflow:name" {
    deviate replace {
      type srl_nokia-common:interface-all;
    }
  }

  deviation "/openconfig-system:system/openconfig-system-grpc:grpc-servers/openconfig-system-grpc:grpc-server/openconfig-system-grpc:config/openconfig-system-grpc:listen-addresses" {
    deviate replace {
      type srl_nokia-common:ip-address;
    }
  }

  deviation "/openconfig-system:system/openconfig-system-grpc:grpc-servers/openconfig-system-grpc:grpc-server/openconfig-system-grpc:state/openconfig-system-grpc:listen-addresses" {
    deviate replace {
      type srl_nokia-common:ip-address;
    }
  }

  deviation "/openconfig-system:system/openconfig-system:aaa/openconfig-system:authentication/openconfig-system:admin-user/openconfig-system:config/openconfig-system:admin-password" {
    deviate replace {
      type srl_nokia-common:user-password;
    }
  }

  deviation "/openconfig-system:system/openconfig-system:aaa/openconfig-system:authentication/openconfig-system:admin-user/openconfig-system:state/openconfig-system:admin-password" {
    deviate replace {
      type srl_nokia-common:user-password;
    }
  }

  deviation "/openconfig-system:system/openconfig-system:aaa/openconfig-system:authentication/openconfig-system:users/openconfig-system:user/openconfig-system:state/openconfig-system:password" {
    deviate replace {
      type srl_nokia-common:user-password;
    }
  }

  deviation "/openconfig-system:system/openconfig-system:aaa/openconfig-system:server-groups/openconfig-system:server-group/openconfig-system:servers/openconfig-system:server/openconfig-system:config/openconfig-system:address" {
    deviate replace {
      type srl_nokia-common:ip-address;
    }
  }

  deviation "/openconfig-system:system/openconfig-system:aaa/openconfig-system:server-groups/openconfig-system:server-group/openconfig-system:servers/openconfig-system:server/openconfig-system:state/openconfig-system:address" {
    deviate replace {
      type srl_nokia-common:ip-address;
    }
  }

  deviation "/openconfig-system:system/openconfig-system:aaa/openconfig-system:server-groups/openconfig-system:server-group/openconfig-system:servers/openconfig-system:server/openconfig-system:tacacs/openconfig-system:config/openconfig-system:secret-key" {
    deviate replace {
      type srl_nokia-common:routing-password;
    }
  }

  deviation "/openconfig-system:system/openconfig-system:aaa/openconfig-system:server-groups/openconfig-system:server-group/openconfig-system:servers/openconfig-system:server/openconfig-system:tacacs/openconfig-system:state/openconfig-system:secret-key" {
    deviate replace {
      type srl_nokia-common:routing-password;
    }
  }

  deviation "/openconfig-system:system/openconfig-system:dns/openconfig-system:host-entries/openconfig-system:host-entry/openconfig-system:config/openconfig-system:ipv4-address" {
    deviate replace {
      type srl_nokia-common:ipv4-address;
    }
  }

  deviation "/openconfig-system:system/openconfig-system:dns/openconfig-system:host-entries/openconfig-system:host-entry/openconfig-system:config/openconfig-system:ipv6-address" {
    deviate replace {
      type srl_nokia-common:ipv6-address;
    }
  }

  deviation "/openconfig-system:system/openconfig-system:dns/openconfig-system:host-entries/openconfig-system:host-entry/openconfig-system:state/openconfig-system:ipv4-address" {
    deviate replace {
      type srl_nokia-common:ipv4-address;
    }
  }

  deviation "/openconfig-system:system/openconfig-system:dns/openconfig-system:host-entries/openconfig-system:host-entry/openconfig-system:state/openconfig-system:ipv6-address" {
    deviate replace {
      type srl_nokia-common:ipv6-address;
    }
  }

  deviation "/openconfig-system:system/openconfig-system:dns/openconfig-system:servers/openconfig-system:server/openconfig-system:config/openconfig-system:address" {
    deviate replace {
      type srl_nokia-common:ip-address;
    }
  }

  deviation "/openconfig-system:system/openconfig-system:dns/openconfig-system:servers/openconfig-system:server/openconfig-system:state/openconfig-system:address" {
    deviate replace {
      type srl_nokia-common:ip-address;
    }
  }

  deviation "/openconfig-system:system/openconfig-system:logging/openconfig-system:remote-servers/openconfig-system:remote-server/openconfig-system:config/openconfig-system:host" {
    deviate replace {
      type srl_nokia-common:host-ietf;
    }
  }

  deviation "/openconfig-system:system/openconfig-system:logging/openconfig-system:remote-servers/openconfig-system:remote-server/openconfig-system:state/openconfig-system:host" {
    deviate replace {
      type srl_nokia-common:host-ietf;
    }
  }

  deviation "/openconfig-system:system/openconfig-system:mac-address/openconfig-system:config/openconfig-system:routing-mac" {
    deviate replace {
      type srl_nokia-common:mac-address;
    }
  }

  deviation "/openconfig-system:system/openconfig-system:mac-address/openconfig-system:state/openconfig-system:routing-mac" {
    deviate replace {
      type srl_nokia-common:mac-address;
    }
  }

  deviation "/openconfig-interfaces:interfaces/openconfig-interfaces:interface/openconfig-interfaces:config/openconfig-interfaces:type" {
    deviate add {
      must ". = 'ethernetCsmacd' or not (starts-with(../name,'ethernet') or starts-with(../name,'mgmt'))" {
        error-message "ethernet and mgmt interfaces must be a type of ethernetCsmacd";
      }
    }
  }

  deviation "/openconfig-interfaces:interfaces/openconfig-interfaces:interface/openconfig-interfaces:config/openconfig-interfaces:type" {
    deviate add {
      must ". = 'softwareLoopback' or not (starts-with(../name,'lo') or starts-with(../name,'system'))" {
        error-message "loopback and system interfaces must be a type of softwareLoopback";
      }
    }
  }

  deviation "/openconfig-interfaces:interfaces/openconfig-interfaces:interface/openconfig-interfaces:config/openconfig-interfaces:type" {
    deviate add {
      must ". = 'ipForward' or not (starts-with(../name,'irb'))" {
        error-message "irb interfaces must be a type of ipForward";
      }
    }
  }

  deviation "/openconfig-interfaces:interfaces/openconfig-interfaces:interface/openconfig-interfaces:config/openconfig-interfaces:type" {
    deviate add {
      must ". = 'ieee8023adLag' or not (starts-with(../name,'lag'))" {
        error-message "lag interfaces must be a type of ieee8023adLag";
      }
    }
  }

  deviation "/openconfig-interfaces:interfaces/openconfig-interfaces:interface/openconfig-interfaces:state/openconfig-interfaces:type" {
    deviate add {
      must ". = 'ethernetCsmacd' or not (starts-with(../name,'ethernet') or starts-with(../name,'mgmt'))" {
        error-message "ethernet and mgmt interfaces must be a type of ethernetCsmacd";
      }
    }
  }

  deviation "/openconfig-interfaces:interfaces/openconfig-interfaces:interface/openconfig-interfaces:state/openconfig-interfaces:type" {
    deviate add {
      must ". = 'softwareLoopback' or not (starts-with(../name,'lo') or starts-with(../name,'system'))" {
        error-message "loopback and system interfaces must be a type of softwareLoopback";
      }
    }
  }

  deviation "/openconfig-interfaces:interfaces/openconfig-interfaces:interface/openconfig-interfaces:state/openconfig-interfaces:type" {
    deviate add {
      must ". = 'ipForward' or not (starts-with(../name,'irb'))" {
        error-message "irb interfaces must be a type of ipForward";
      }
    }
  }

  deviation "/openconfig-interfaces:interfaces/openconfig-interfaces:interface/openconfig-interfaces:state/openconfig-interfaces:type" {
    deviate add {
      must ". = 'ieee8023adLag' or not (starts-with(../name,'lag'))" {
        error-message "lag interfaces must be a type of ieee8023adLag";
      }
    }
  }

  deviation "/openconfig-interfaces:interfaces/openconfig-interfaces:interface/openconfig-interfaces:subinterfaces/openconfig-interfaces:subinterface/openconfig-if-ip:ipv4/openconfig-if-ip:config/openconfig-if-ip:mtu" {
    deviate add {
      must ". = ../../../ipv6/config/mtu" {
        error-message "ipv4 and ipv6 mtu values must be the same";
      }
    }
  }

  deviation "/openconfig-interfaces:interfaces/openconfig-interfaces:interface/openconfig-interfaces:subinterfaces/openconfig-interfaces:subinterface/openconfig-if-ip:ipv4/openconfig-if-ip:state/openconfig-if-ip:mtu" {
    deviate add {
      must ". = ../../../ipv6/config/mtu" {
        error-message "ipv4 and ipv6 mtu values must be the same";
      }
    }
  }

  deviation "/openconfig-interfaces:interfaces/openconfig-interfaces:interface/openconfig-interfaces:subinterfaces/openconfig-interfaces:subinterface/openconfig-if-ip:ipv6/openconfig-if-ip:config/openconfig-if-ip:mtu" {
    deviate add {
      must ". = ../../../ipv4/config/mtu" {
        error-message "ipv4 and ipv6 mtu values must be the same";
      }
    }
  }

  deviation "/openconfig-network-instance:network-instances/openconfig-network-instance:network-instance/openconfig-network-instance:protocols/openconfig-network-instance:protocol/openconfig-network-instance:bgp" {
    deviate add {
      must "../config/identifier = 'BGP'" {
        
      }
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:ipv4-unicast/openconfig-network-instance:config/openconfig-network-instance:send-default-route" {
    deviate add {
      must "../../../config/afi-safi-name = 'IPV4_UNICAST'" {
        
      }
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:ipv4-unicast/openconfig-network-instance:state/openconfig-network-instance:send-default-route" {
    deviate add {
      must "../../../config/afi-safi-name = 'IPV4_UNICAST'" {
        
      }
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:ipv6-unicast/openconfig-network-instance:config/openconfig-network-instance:send-default-route" {
    deviate add {
      must "../../../config/afi-safi-name = 'IPV6_UNICAST'" {
        
      }
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:ipv6-unicast/openconfig-network-instance:state/openconfig-network-instance:send-default-route" {
    deviate add {
      must "../../../config/afi-safi-name = 'IPV6_UNICAST'" {
        
      }
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:ipv4-unicast/openconfig-network-instance:config/openconfig-network-instance:send-default-route" {
    deviate add {
      must "../../../config/afi-safi-name = 'IPV4_UNICAST'" {
        
      }
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:ipv4-unicast/openconfig-network-instance:state/openconfig-network-instance:send-default-route" {
    deviate add {
      must "../../../config/afi-safi-name = 'IPV4_UNICAST'" {
        
      }
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:ipv6-unicast/openconfig-network-instance:config/openconfig-network-instance:send-default-route" {
    deviate add {
      must "../../../config/afi-safi-name = 'IPV6_UNICAST'" {
        
      }
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:ipv6-unicast/openconfig-network-instance:state/openconfig-network-instance:send-default-route" {
    deviate add {
      must "../../../config/afi-safi-name = 'IPV6_UNICAST'" {
        
      }
    }
  }

  deviation "/openconfig-network-instance:network-instances/openconfig-network-instance:network-instance/openconfig-network-instance:protocols/openconfig-network-instance:protocol/openconfig-network-instance:config/openconfig-network-instance:enabled" {
    deviate add {
      must "../identifier != 'LOCAL_AGGREGATE'" {
        error-message "enable leaf is not supported on LOCAL_AGGREGATE types";
      }
    }
  }

  deviation "/openconfig-network-instance:network-instances/openconfig-network-instance:network-instance/openconfig-network-instance:protocols/openconfig-network-instance:protocol/openconfig-network-instance:config/openconfig-network-instance:enabled" {
    deviate add {
      must "../identifier != 'STATIC' or . = true()" {
        error-message "enable leaf can only be set to true for STATIC types";
      }
    }
  }

  deviation "/openconfig-network-instance:network-instances/openconfig-network-instance:network-instance/openconfig-network-instance:protocols/openconfig-network-instance:protocol/openconfig-network-instance:isis/openconfig-network-instance:global/openconfig-network-instance:afi-safi/openconfig-network-instance:af/openconfig-network-instance:config/openconfig-network-instance:enabled" {
    deviate add {
      must ". = true()" {
        error-message "enabled must always be set to true";
      }
    }
  }

  deviation "/openconfig-network-instance:network-instances/openconfig-network-instance:network-instance/openconfig-network-instance:protocols/openconfig-network-instance:protocol/openconfig-network-instance:isis/openconfig-network-instance:global/openconfig-network-instance:afi-safi/openconfig-network-instance:af/openconfig-network-instance:state/openconfig-network-instance:enabled" {
    deviate add {
      must ". = true()" {
        error-message "enabled must always be set to true";
      }
    }
  }

  deviation "/openconfig-network-instance:network-instances/openconfig-network-instance:network-instance/openconfig-network-instance:protocols/openconfig-network-instance:protocol/openconfig-network-instance:isis/openconfig-network-instance:global/openconfig-network-instance:reference-bandwidth/openconfig-network-instance:config/openconfig-network-instance:reference-bandwidth" {
    deviate add {
      must ". >= 0 and . <= 8000000" {
        error-message "reference bandwidth value should be between 1mbps and 8000000mbps";
      }
    }
  }

  deviation "/openconfig-network-instance:network-instances/openconfig-network-instance:network-instance/openconfig-network-instance:protocols/openconfig-network-instance:protocol/openconfig-network-instance:isis/openconfig-network-instance:global/openconfig-network-instance:reference-bandwidth/openconfig-network-instance:state/openconfig-network-instance:reference-bandwidth" {
    deviate add {
      must ". >= 0 and . <= 8000000" {
        error-message "reference bandwidth value should be between 1mbps and 8000000mbps";
      }
    }
  }

  deviation "/openconfig-network-instance:network-instances/openconfig-network-instance:network-instance/openconfig-network-instance:protocols/openconfig-network-instance:protocol/openconfig-network-instance:isis/openconfig-network-instance:interfaces/openconfig-network-instance:interface/openconfig-network-instance:afi-safi/openconfig-network-instance:af/openconfig-network-instance:config/openconfig-network-instance:enabled" {
    deviate add {
      must ". = true()" {
        error-message "enabled must always be set to true";
      }
    }
  }

  deviation "/openconfig-network-instance:network-instances/openconfig-network-instance:network-instance/openconfig-network-instance:protocols/openconfig-network-instance:protocol/openconfig-network-instance:isis/openconfig-network-instance:interfaces/openconfig-network-instance:interface/openconfig-network-instance:afi-safi/openconfig-network-instance:af/openconfig-network-instance:state/openconfig-network-instance:enabled" {
    deviate add {
      must ". = true()" {
        error-message "enabled must always be set to true";
      }
    }
  }

  deviation "/openconfig-network-instance:network-instances/openconfig-network-instance:network-instance/openconfig-network-instance:protocols/openconfig-network-instance:protocol/openconfig-network-instance:isis/openconfig-network-instance:interfaces/openconfig-network-instance:interface/openconfig-network-instance:authentication/openconfig-network-instance:config/openconfig-network-instance:auth-password" {
    deviate add {
      must "../auth-type = 'SIMPLE_KEY'" {
        error-message "auth-type other than SIMPLE_KEY are not allowed";
      }
    }
  }

  deviation "/openconfig-network-instance:network-instances/openconfig-network-instance:network-instance/openconfig-network-instance:protocols/openconfig-network-instance:protocol/openconfig-network-instance:isis/openconfig-network-instance:interfaces/openconfig-network-instance:interface/openconfig-network-instance:authentication/openconfig-network-instance:config/openconfig-network-instance:auth-type" {
    deviate add {
      must "boolean(../auth-password) or boolean(../keychain)" {
        error-message "auth-password or keychain must be configured";
      }
    }
  }

  deviation "/openconfig-network-instance:network-instances/openconfig-network-instance:network-instance/openconfig-network-instance:protocols/openconfig-network-instance:protocol/openconfig-network-instance:isis/openconfig-network-instance:interfaces/openconfig-network-instance:interface/openconfig-network-instance:authentication/openconfig-network-instance:state/openconfig-network-instance:auth-password" {
    deviate add {
      must "../auth-type = 'SIMPLE_KEY'" {
        error-message "auth-type other than SIMPLE_KEY are not allowed";
      }
    }
  }

  deviation "/openconfig-network-instance:network-instances/openconfig-network-instance:network-instance/openconfig-network-instance:protocols/openconfig-network-instance:protocol/openconfig-network-instance:isis/openconfig-network-instance:interfaces/openconfig-network-instance:interface/openconfig-network-instance:authentication/openconfig-network-instance:state/openconfig-network-instance:auth-type" {
    deviate add {
      must "boolean(../auth-password) or boolean(../keychain)" {
        error-message "auth-password or keychain must be configured";
      }
    }
  }

  deviation "/openconfig-network-instance:network-instances/openconfig-network-instance:network-instance/openconfig-network-instance:protocols/openconfig-network-instance:protocol/openconfig-network-instance:isis/openconfig-network-instance:interfaces/openconfig-network-instance:interface/openconfig-network-instance:levels/openconfig-network-instance:level/openconfig-network-instance:hello-authentication/openconfig-network-instance:config/openconfig-network-instance:auth-password" {
    deviate add {
      must "../auth-type = 'SIMPLE_KEY'" {
        error-message "auth-type other than SIMPLE_KEY are not allowed";
      }
    }
  }

  deviation "/openconfig-network-instance:network-instances/openconfig-network-instance:network-instance/openconfig-network-instance:protocols/openconfig-network-instance:protocol/openconfig-network-instance:isis/openconfig-network-instance:interfaces/openconfig-network-instance:interface/openconfig-network-instance:levels/openconfig-network-instance:level/openconfig-network-instance:hello-authentication/openconfig-network-instance:config/openconfig-network-instance:auth-type" {
    deviate add {
      must "boolean(../auth-password) or boolean(../keychain)" {
        error-message "auth-password or keychain must be configured";
      }
    }
  }

  deviation "/openconfig-network-instance:network-instances/openconfig-network-instance:network-instance/openconfig-network-instance:protocols/openconfig-network-instance:protocol/openconfig-network-instance:isis/openconfig-network-instance:levels/openconfig-network-instance:level/openconfig-network-instance:authentication/openconfig-network-instance:config/openconfig-network-instance:auth-password" {
    deviate add {
      must "../auth-type = 'SIMPLE_KEY'" {
        error-message "auth-type other than SIMPLE_KEY are not allowed";
      }
    }
  }

  deviation "/openconfig-network-instance:network-instances/openconfig-network-instance:network-instance/openconfig-network-instance:protocols/openconfig-network-instance:protocol/openconfig-network-instance:isis/openconfig-network-instance:levels/openconfig-network-instance:level/openconfig-network-instance:authentication/openconfig-network-instance:config/openconfig-network-instance:auth-type" {
    deviate add {
      must "boolean(../auth-password) or boolean(../keychain)" {
        error-message "auth-password or keychain must be configured";
      }
    }
  }

  deviation "/openconfig-network-instance:network-instances/openconfig-network-instance:network-instance/openconfig-network-instance:protocols/openconfig-network-instance:protocol/openconfig-network-instance:isis/openconfig-network-instance:levels/openconfig-network-instance:level/openconfig-network-instance:authentication/openconfig-network-instance:state/openconfig-network-instance:auth-password" {
    deviate add {
      must "../auth-type = 'SIMPLE_KEY'" {
        error-message "auth-type other than SIMPLE_KEY are not allowed";
      }
    }
  }

  deviation "/openconfig-network-instance:network-instances/openconfig-network-instance:network-instance/openconfig-network-instance:protocols/openconfig-network-instance:protocol/openconfig-network-instance:isis/openconfig-network-instance:levels/openconfig-network-instance:level/openconfig-network-instance:authentication/openconfig-network-instance:state/openconfig-network-instance:auth-type" {
    deviate add {
      must "boolean(../auth-password) or boolean(../keychain)" {
        error-message "auth-password or keychain must be configured";
      }
    }
  }

  deviation "/openconfig-network-instance:network-instances/openconfig-network-instance:network-instance/openconfig-network-instance:protocols/openconfig-network-instance:protocol/openconfig-network-instance:isis/openconfig-network-instance:levels/openconfig-network-instance:level/openconfig-network-instance:route-preference/openconfig-network-instance:config/openconfig-network-instance:external-route-preference" {
    deviate add {
      must ". <= 255" {
        
      }
    }
  }

  deviation "/openconfig-network-instance:network-instances/openconfig-network-instance:network-instance/openconfig-network-instance:protocols/openconfig-network-instance:protocol/openconfig-network-instance:isis/openconfig-network-instance:levels/openconfig-network-instance:level/openconfig-network-instance:route-preference/openconfig-network-instance:config/openconfig-network-instance:internal-route-preference" {
    deviate add {
      must ". <= 255" {
        
      }
    }
  }

  deviation "/openconfig-network-instance:network-instances/openconfig-network-instance:network-instance/openconfig-network-instance:protocols/openconfig-network-instance:protocol/openconfig-network-instance:isis/openconfig-network-instance:levels/openconfig-network-instance:level/openconfig-network-instance:route-preference/openconfig-network-instance:state/openconfig-network-instance:external-route-preference" {
    deviate add {
      must ". <= 255" {
        
      }
    }
  }

  deviation "/openconfig-network-instance:network-instances/openconfig-network-instance:network-instance/openconfig-network-instance:protocols/openconfig-network-instance:protocol/openconfig-network-instance:isis/openconfig-network-instance:levels/openconfig-network-instance:level/openconfig-network-instance:route-preference/openconfig-network-instance:state/openconfig-network-instance:internal-route-preference" {
    deviate add {
      must ". <= 255" {
        
      }
    }
  }

  deviation "/openconfig-network-instance:network-instances/openconfig-network-instance:network-instance/openconfig-network-instance:protocols/openconfig-network-instance:protocol/openconfig-network-instance:local-aggregates" {
    deviate add {
      must "../config/identifier = 'LOCAL_AGGREGATE'" {
        
      }
    }
  }

  deviation "/openconfig-network-instance:network-instances/openconfig-network-instance:network-instance/openconfig-network-instance:protocols/openconfig-network-instance:protocol/openconfig-network-instance:state/openconfig-network-instance:enabled" {
    deviate add {
      must "../identifier != 'LOCAL_AGGREGATE'" {
        error-message "enable leaf is not supported on LOCAL_AGGREGATE types";
      }
    }
  }

  deviation "/openconfig-network-instance:network-instances/openconfig-network-instance:network-instance/openconfig-network-instance:protocols/openconfig-network-instance:protocol/openconfig-network-instance:state/openconfig-network-instance:enabled" {
    deviate add {
      must "../identifier != 'STATIC' or . = true()" {
        error-message "enable leaf can only be set to true for STATIC types";
      }
    }
  }

  deviation "/openconfig-network-instance:network-instances/openconfig-network-instance:network-instance/openconfig-network-instance:protocols/openconfig-network-instance:protocol/openconfig-network-instance:static-routes" {
    deviate add {
      must "../config/identifier = 'STATIC'" {
        
      }
    }
  }

  deviation "/openconfig-network-instance:network-instances/openconfig-network-instance:network-instance/openconfig-network-instance:protocols/openconfig-network-instance:protocol/openconfig-network-instance:static-routes/openconfig-network-instance:static" {
    deviate add {
      must "next-hops or next-hop-group/config/name" {
        error-message "Must create next-hops container or configure next-hop-group name";
      }
    }
  }

  deviation "/openconfig-network-instance:network-instances/openconfig-network-instance:network-instance/openconfig-network-instance:protocols/openconfig-network-instance:protocol/openconfig-network-instance:static-routes/openconfig-network-instance:static" {
    deviate add {
      must "not (next-hops and next-hop-group/config/name)" {
        error-message "Only one of next-hops container or next-hop-group name may be configured";
      }
    }
  }

  deviation "/openconfig-network-instance:network-instances/openconfig-network-instance:network-instance/openconfig-network-instance:protocols/openconfig-network-instance:protocol/openconfig-network-instance:static-routes/openconfig-network-instance:static/openconfig-network-instance:next-hops/openconfig-network-instance:next-hop/openconfig-network-instance:config/openconfig-network-instance:metric" {
    deviate add {
      must "../next-hop != 'DROP'" {
        error-message "Cannot set metric if next-hop is DROP";
      }
    }
  }

  deviation "/openconfig-network-instance:network-instances/openconfig-network-instance:network-instance/openconfig-network-instance:protocols/openconfig-network-instance:protocol/openconfig-network-instance:static-routes/openconfig-network-instance:static/openconfig-network-instance:next-hops/openconfig-network-instance:next-hop/openconfig-network-instance:config/openconfig-network-instance:preference" {
    deviate add {
      must ". <= 255" {
        error-message "supported range is 0..255";
      }
    }
  }

  deviation "/openconfig-network-instance:network-instances/openconfig-network-instance:network-instance/openconfig-network-instance:protocols/openconfig-network-instance:protocol/openconfig-network-instance:static-routes/openconfig-network-instance:static/openconfig-network-instance:next-hops/openconfig-network-instance:next-hop/openconfig-network-instance:config/openconfig-network-instance:preference" {
    deviate add {
      must "../next-hop != 'DROP'" {
        error-message "Cannot set preference if next-hop is DROP";
      }
    }
  }

  deviation "/openconfig-network-instance:network-instances/openconfig-network-instance:network-instance/openconfig-network-instance:protocols/openconfig-network-instance:protocol/openconfig-network-instance:static-routes/openconfig-network-instance:static/openconfig-network-instance:next-hops/openconfig-network-instance:next-hop/openconfig-network-instance:config/openconfig-network-instance:recurse" {
    deviate add {
      must ". = false() or ../next-hop != 'DROP'" {
        error-message "Cannot set next-hop to DROP and recurse to true";
      }
    }
  }

  deviation "/openconfig-network-instance:network-instances/openconfig-network-instance:network-instance/openconfig-network-instance:static/openconfig-network-instance:next-hops/openconfig-network-instance:next-hop/openconfig-network-instance:config/openconfig-network-instance:recurse" {
    deviate add {
      must "../next-hop != 'DROP' and ../next-hop != 'LOCAL_LINK'" {
        error-message "next-hop must be an IP address";
      }
    }
  }

  deviation "/openconfig-network-instance:network-instances/openconfig-network-instance:network-instance/openconfig-network-instance:static/openconfig-network-instance:next-hops/openconfig-network-instance:next-hop/openconfig-network-instance:state/openconfig-network-instance:recurse" {
    deviate add {
      must "../next-hop != 'DROP' and ../next-hop != 'LOCAL_LINK'" {
        error-message "next-hop must be an IP address";
      }
    }
  }

  deviation "/openconfig-platform:components/openconfig-platform:component/openconfig-platform:port/openconfig-platform-port:breakout-mode/openconfig-platform-port:groups/openconfig-platform-port:group/openconfig-platform-port:config/openconfig-platform-port:index" {
    deviate add {
      must ". = 1" {
        error-message "only single group with index 1 is supported";
      }
    }
  }

  deviation "/openconfig-platform:components/openconfig-platform:component/openconfig-platform:port/openconfig-platform-port:breakout-mode/openconfig-platform-port:groups/openconfig-platform-port:group/openconfig-platform-port:state/openconfig-platform-port:index" {
    deviate add {
      must ". = 1" {
        error-message "only single group with index 1 is supported";
      }
    }
  }

  deviation "/openconfig-qos:qos/openconfig-qos:queue-management-profiles/openconfig-qos:queue-management-profile/openconfig-qos:wred/openconfig-qos:uniform/openconfig-qos:config/openconfig-qos:weight" {
    deviate add {
      must ". <= 15" {
        error-message "supported range is 0..15";
      }
    }
  }

  deviation "/openconfig-qos:qos/openconfig-qos:queue-management-profiles/openconfig-qos:queue-management-profile/openconfig-qos:wred/openconfig-qos:uniform/openconfig-qos:state/openconfig-qos:weight" {
    deviate add {
      must ". <= 15" {
        error-message "supported range is 0..15";
      }
    }
  }

  deviation "/openconfig-qos:qos/openconfig-qos:scheduler-policies/openconfig-qos:scheduler-policy/openconfig-qos:schedulers/openconfig-qos:scheduler/openconfig-qos:inputs/openconfig-qos:input/openconfig-qos:config/openconfig-qos:input-type" {
    deviate add {
      must ". = 'QUEUE'" {
        error-message "supported type is QUEUE";
      }
    }
  }

  deviation "/openconfig-qos:qos/openconfig-qos:scheduler-policies/openconfig-qos:scheduler-policy/openconfig-qos:schedulers/openconfig-qos:scheduler/openconfig-qos:inputs/openconfig-qos:input/openconfig-qos:state/openconfig-qos:input-type" {
    deviate add {
      must ". = 'QUEUE'" {
        error-message "supported type is QUEUE";
      }
    }
  }

  deviation "/openconfig-qos:qos/openconfig-qos:scheduler-policies/openconfig-qos:scheduler-policy/openconfig-qos:schedulers/openconfig-qos:scheduler/openconfig-qos:sequence" {
    deviate add {
      must ". <= 1" {
        error-message "supported range is 0..1";
      }
    }
  }

  deviation "/openconfig-routing-policy:routing-policy/openconfig-routing-policy:policy-definitions/openconfig-routing-policy:policy-definition/openconfig-routing-policy:statements/openconfig-routing-policy:statement/openconfig-routing-policy:actions/openconfig-bgp-policy:bgp-actions/openconfig-bgp-policy:config/openconfig-bgp-policy:set-med-action" {
    deviate add {
      must "string(../set-med) != ''" {
        error-message "set-med-action cannot be specified without a set-med value";
      }
    }
  }

  deviation "/openconfig-routing-policy:routing-policy/openconfig-routing-policy:policy-definitions/openconfig-routing-policy:policy-definition/openconfig-routing-policy:statements/openconfig-routing-policy:statement/openconfig-routing-policy:actions/openconfig-bgp-policy:bgp-actions/openconfig-bgp-policy:config/openconfig-bgp-policy:set-med-action" {
    deviate delete {
      must "../set-med" {
        
      }
    }
  }

  deviation "/openconfig-routing-policy:routing-policy/openconfig-routing-policy:policy-definitions/openconfig-routing-policy:policy-definition/openconfig-routing-policy:statements/openconfig-routing-policy:statement/openconfig-routing-policy:actions/openconfig-bgp-policy:bgp-actions/openconfig-bgp-policy:set-as-path-prepend/openconfig-bgp-policy:config/openconfig-bgp-policy:asn" {
    deviate add {
      must ". != 0" {
        error-message "asn zero is not supported";
      }
    }
  }

  deviation "/openconfig-routing-policy:routing-policy/openconfig-routing-policy:policy-definitions/openconfig-routing-policy:policy-definition/openconfig-routing-policy:statements/openconfig-routing-policy:statement/openconfig-routing-policy:actions/openconfig-bgp-policy:bgp-actions/openconfig-bgp-policy:set-as-path-prepend/openconfig-bgp-policy:config/openconfig-bgp-policy:repeat-n" {
    deviate add {
      must ". <= 50" {
        error-message "max supported is 50";
      }
    }
  }

  deviation "/openconfig-routing-policy:routing-policy/openconfig-routing-policy:policy-definitions/openconfig-routing-policy:policy-definition/openconfig-routing-policy:statements/openconfig-routing-policy:statement/openconfig-routing-policy:actions/openconfig-bgp-policy:bgp-actions/openconfig-bgp-policy:set-as-path-prepend/openconfig-bgp-policy:state/openconfig-bgp-policy:asn" {
    deviate add {
      must ". != 0" {
        error-message "asn zero is not supported";
      }
    }
  }

  deviation "/openconfig-routing-policy:routing-policy/openconfig-routing-policy:policy-definitions/openconfig-routing-policy:policy-definition/openconfig-routing-policy:statements/openconfig-routing-policy:statement/openconfig-routing-policy:actions/openconfig-bgp-policy:bgp-actions/openconfig-bgp-policy:set-as-path-prepend/openconfig-bgp-policy:state/openconfig-bgp-policy:repeat-n" {
    deviate add {
      must ". <= 50" {
        error-message "max supported is 50";
      }
    }
  }

  deviation "/openconfig-routing-policy:routing-policy/openconfig-routing-policy:policy-definitions/openconfig-routing-policy:policy-definition/openconfig-routing-policy:statements/openconfig-routing-policy:statement/openconfig-routing-policy:actions/openconfig-bgp-policy:bgp-actions/openconfig-bgp-policy:set-community/openconfig-bgp-policy:config/openconfig-bgp-policy:method" {
    deviate add {
      must "(.='REFERENCE')" {
        error-message "only REFERENCE method is supported";
      }
    }
  }

  deviation "/openconfig-routing-policy:routing-policy/openconfig-routing-policy:policy-definitions/openconfig-routing-policy:policy-definition/openconfig-routing-policy:statements/openconfig-routing-policy:statement/openconfig-routing-policy:actions/openconfig-bgp-policy:bgp-actions/openconfig-bgp-policy:set-community/openconfig-bgp-policy:state/openconfig-bgp-policy:method" {
    deviate add {
      must "(.='REFERENCE')" {
        error-message "only REFERENCE method is supported";
      }
    }
  }

  deviation "/openconfig-routing-policy:routing-policy/openconfig-routing-policy:policy-definitions/openconfig-routing-policy:policy-definition/openconfig-routing-policy:statements/openconfig-routing-policy:statement/openconfig-routing-policy:actions/openconfig-bgp-policy:bgp-actions/openconfig-bgp-policy:set-ext-community/openconfig-bgp-policy:config/openconfig-bgp-policy:method" {
    deviate add {
      must "(.='REFERENCE')" {
        error-message "only REFERENCE method is supported";
      }
    }
  }

  deviation "/openconfig-routing-policy:routing-policy/openconfig-routing-policy:policy-definitions/openconfig-routing-policy:policy-definition/openconfig-routing-policy:statements/openconfig-routing-policy:statement/openconfig-routing-policy:actions/openconfig-bgp-policy:bgp-actions/openconfig-bgp-policy:set-ext-community/openconfig-bgp-policy:state/openconfig-bgp-policy:method" {
    deviate add {
      must "(.='REFERENCE')" {
        error-message "only REFERENCE method is supported";
      }
    }
  }

  deviation "/openconfig-routing-policy:routing-policy/openconfig-routing-policy:policy-definitions/openconfig-routing-policy:policy-definition/openconfig-routing-policy:statements/openconfig-routing-policy:statement/openconfig-routing-policy:actions/openconfig-bgp-policy:bgp-actions/openconfig-bgp-policy:state/openconfig-bgp-policy:set-med-action" {
    deviate add {
      must "string(../set-med) != ''" {
        error-message "set-med-action cannot be specified without a set-med value";
      }
    }
  }

  deviation "/openconfig-routing-policy:routing-policy/openconfig-routing-policy:policy-definitions/openconfig-routing-policy:policy-definition/openconfig-routing-policy:statements/openconfig-routing-policy:statement/openconfig-routing-policy:actions/openconfig-bgp-policy:bgp-actions/openconfig-bgp-policy:state/openconfig-bgp-policy:set-med-action" {
    deviate delete {
      must "../set-med" {
        
      }
    }
  }

  deviation "/openconfig-routing-policy:routing-policy/openconfig-routing-policy:policy-definitions/openconfig-routing-policy:policy-definition/openconfig-routing-policy:statements/openconfig-routing-policy:statement/openconfig-routing-policy:actions/openconfig-isis-policy:isis-actions/openconfig-isis-policy:config/openconfig-isis-policy:set-metric-style-type" {
    deviate add {
      must "(.='WIDE_METRIC')" {
        error-message "only WIDE_METRIC method is supported";
      }
    }
  }

  deviation "/openconfig-routing-policy:routing-policy/openconfig-routing-policy:policy-definitions/openconfig-routing-policy:policy-definition/openconfig-routing-policy:statements/openconfig-routing-policy:statement/openconfig-routing-policy:actions/openconfig-isis-policy:isis-actions/openconfig-isis-policy:state/openconfig-isis-policy:set-metric-style-type" {
    deviate add {
      must "(.='WIDE_METRIC')" {
        error-message "only WIDE_METRIC method is supported";
      }
    }
  }

  deviation "/openconfig-routing-policy:routing-policy/openconfig-routing-policy:policy-definitions/openconfig-routing-policy:policy-definition/openconfig-routing-policy:statements/openconfig-routing-policy:statement/openconfig-routing-policy:conditions/openconfig-bgp-policy:bgp-conditions/openconfig-bgp-policy:as-path-length/openconfig-bgp-policy:config/openconfig-bgp-policy:value" {
    deviate add {
      must ". <= 255" {
        error-message "max supported is 255";
      }
    }
  }

  deviation "/openconfig-routing-policy:routing-policy/openconfig-routing-policy:policy-definitions/openconfig-routing-policy:policy-definition/openconfig-routing-policy:statements/openconfig-routing-policy:statement/openconfig-routing-policy:conditions/openconfig-bgp-policy:bgp-conditions/openconfig-bgp-policy:as-path-length/openconfig-bgp-policy:state/openconfig-bgp-policy:value" {
    deviate add {
      must ". <= 255" {
        error-message "max supported is 255";
      }
    }
  }

  deviation "/openconfig-system:system/openconfig-system:aaa/openconfig-system:server-groups/openconfig-system:server-group/openconfig-system:servers/openconfig-system:server/openconfig-system:config/openconfig-system:timeout" {
    deviate add {
      must ". >= 1 and . <= 3600" {
        error-message "supported range is 1..3600";
      }
    }
  }

  deviation "/openconfig-system:system/openconfig-system:aaa/openconfig-system:server-groups/openconfig-system:server-group/openconfig-system:servers/openconfig-system:server/openconfig-system:state/openconfig-system:timeout" {
    deviate add {
      must ". >= 1 and . <= 3600" {
        error-message "supported range is 1..3600";
      }
    }
  }

  deviation "/openconfig-acl:acl/openconfig-acl:acl-sets/openconfig-acl:acl-set/openconfig-acl:acl-entries/openconfig-acl:acl-entry/openconfig-acl:actions/openconfig-acl:config/openconfig-acl:log-action" {
    deviate delete {
      default oc-acl:LOG_NONE;
    }
  }

  deviation "/openconfig-acl:acl/openconfig-acl:acl-sets/openconfig-acl:acl-set/openconfig-acl:acl-entries/openconfig-acl:acl-entry/openconfig-acl:actions/openconfig-acl:state/openconfig-acl:log-action" {
    deviate delete {
      default oc-acl:LOG_NONE;
    }
  }

  deviation "/openconfig-interfaces:interfaces/openconfig-interfaces:interface/openconfig-interfaces:config/openconfig-if-sdn-ext:forwarding-viable" {
    deviate delete {
      default true;
    }
  }

  deviation "/openconfig-interfaces:interfaces/openconfig-interfaces:interface/openconfig-interfaces:config/openconfig-interfaces:enabled" {
    deviate delete {
      default true;
    }
  }

  deviation "/openconfig-interfaces:interfaces/openconfig-interfaces:interface/openconfig-interfaces:hold-time/openconfig-interfaces:config/openconfig-interfaces:down" {
    deviate delete {
      default 0;
    }
  }

  deviation "/openconfig-interfaces:interfaces/openconfig-interfaces:interface/openconfig-interfaces:hold-time/openconfig-interfaces:config/openconfig-interfaces:up" {
    deviate delete {
      default 0;
    }
  }

  deviation "/openconfig-interfaces:interfaces/openconfig-interfaces:interface/openconfig-interfaces:hold-time/openconfig-interfaces:state/openconfig-interfaces:down" {
    deviate delete {
      default 0;
    }
  }

  deviation "/openconfig-interfaces:interfaces/openconfig-interfaces:interface/openconfig-interfaces:hold-time/openconfig-interfaces:state/openconfig-interfaces:up" {
    deviate delete {
      default 0;
    }
  }

  deviation "/openconfig-interfaces:interfaces/openconfig-interfaces:interface/openconfig-interfaces:state/openconfig-if-sdn-ext:forwarding-viable" {
    deviate delete {
      default true;
    }
  }

  deviation "/openconfig-interfaces:interfaces/openconfig-interfaces:interface/openconfig-interfaces:state/openconfig-interfaces:enabled" {
    deviate delete {
      default true;
    }
  }

  deviation "/openconfig-interfaces:interfaces/openconfig-interfaces:interface/openconfig-interfaces:subinterfaces/openconfig-interfaces:subinterface/openconfig-if-ip:ipv4/openconfig-if-ip:config/openconfig-if-ip:enabled" {
    deviate delete {
      default true;
    }
  }

  deviation "/openconfig-interfaces:interfaces/openconfig-interfaces:interface/openconfig-interfaces:subinterfaces/openconfig-interfaces:subinterface/openconfig-if-ip:ipv4/openconfig-if-ip:state/openconfig-if-ip:enabled" {
    deviate delete {
      default true;
    }
  }

  deviation "/openconfig-interfaces:interfaces/openconfig-interfaces:interface/openconfig-interfaces:subinterfaces/openconfig-interfaces:subinterface/openconfig-if-ip:ipv6/openconfig-if-ip:addresses/openconfig-if-ip:address/openconfig-if-ip:config/openconfig-if-ip:type" {
    deviate delete {
      default GLOBAL_UNICAST;
    }
  }

  deviation "/openconfig-interfaces:interfaces/openconfig-interfaces:interface/openconfig-interfaces:subinterfaces/openconfig-interfaces:subinterface/openconfig-if-ip:ipv6/openconfig-if-ip:addresses/openconfig-if-ip:address/openconfig-if-ip:state/openconfig-if-ip:type" {
    deviate delete {
      default GLOBAL_UNICAST;
    }
  }

  deviation "/openconfig-interfaces:interfaces/openconfig-interfaces:interface/openconfig-interfaces:subinterfaces/openconfig-interfaces:subinterface/openconfig-if-ip:ipv6/openconfig-if-ip:config/openconfig-if-ip:enabled" {
    deviate delete {
      default true;
    }
  }

  deviation "/openconfig-interfaces:interfaces/openconfig-interfaces:interface/openconfig-interfaces:subinterfaces/openconfig-interfaces:subinterface/openconfig-if-ip:ipv6/openconfig-if-ip:router-advertisement/openconfig-if-ip:config/openconfig-if-ip:enable" {
    deviate delete {
      default true;
    }
  }

  deviation "/openconfig-interfaces:interfaces/openconfig-interfaces:interface/openconfig-interfaces:subinterfaces/openconfig-interfaces:subinterface/openconfig-if-ip:ipv6/openconfig-if-ip:router-advertisement/openconfig-if-ip:state/openconfig-if-ip:enable" {
    deviate delete {
      default true;
    }
  }

  deviation "/openconfig-interfaces:interfaces/openconfig-interfaces:interface/openconfig-interfaces:subinterfaces/openconfig-interfaces:subinterface/openconfig-if-ip:ipv6/openconfig-if-ip:state/openconfig-if-ip:enabled" {
    deviate delete {
      default true;
    }
  }

  deviation "/openconfig-interfaces:interfaces/openconfig-interfaces:interface/openconfig-interfaces:subinterfaces/openconfig-interfaces:subinterface/openconfig-interfaces:config/openconfig-interfaces:enabled" {
    deviate delete {
      default true;
    }
  }

  deviation "/openconfig-interfaces:interfaces/openconfig-interfaces:interface/openconfig-interfaces:subinterfaces/openconfig-interfaces:subinterface/openconfig-interfaces:config/openconfig-interfaces:index" {
    deviate delete {
      default 0;
    }
  }

  deviation "/openconfig-interfaces:interfaces/openconfig-interfaces:interface/openconfig-interfaces:subinterfaces/openconfig-interfaces:subinterface/openconfig-interfaces:state/openconfig-interfaces:enabled" {
    deviate delete {
      default true;
    }
  }

  deviation "/openconfig-interfaces:interfaces/openconfig-interfaces:interface/openconfig-interfaces:subinterfaces/openconfig-interfaces:subinterface/openconfig-interfaces:state/openconfig-interfaces:index" {
    deviate delete {
      default 0;
    }
  }

  deviation "/openconfig-lacp:lacp/openconfig-lacp:interfaces/openconfig-lacp:interface/openconfig-lacp:config/openconfig-lacp:interval" {
    deviate delete {
      default SLOW;
    }
  }

  deviation "/openconfig-lacp:lacp/openconfig-lacp:interfaces/openconfig-lacp:interface/openconfig-lacp:config/openconfig-lacp:lacp-mode" {
    deviate delete {
      default ACTIVE;
    }
  }

  deviation "/openconfig-lacp:lacp/openconfig-lacp:interfaces/openconfig-lacp:interface/openconfig-lacp:state/openconfig-lacp:interval" {
    deviate delete {
      default SLOW;
    }
  }

  deviation "/openconfig-lacp:lacp/openconfig-lacp:interfaces/openconfig-lacp:interface/openconfig-lacp:state/openconfig-lacp:lacp-mode" {
    deviate delete {
      default ACTIVE;
    }
  }

  deviation "/openconfig-lldp:lldp/openconfig-lldp:config/openconfig-lldp:enabled" {
    deviate delete {
      default true;
    }
  }

  deviation "/openconfig-lldp:lldp/openconfig-lldp:interfaces/openconfig-lldp:interface/openconfig-lldp:config/openconfig-lldp:enabled" {
    deviate delete {
      default true;
    }
  }

  deviation "/openconfig-lldp:lldp/openconfig-lldp:interfaces/openconfig-lldp:interface/openconfig-lldp:state/openconfig-lldp:enabled" {
    deviate delete {
      default true;
    }
  }

  deviation "/openconfig-lldp:lldp/openconfig-lldp:state/openconfig-lldp:enabled" {
    deviate delete {
      default true;
    }
  }

  deviation "/openconfig-network-instance:network-instances/openconfig-network-instance:network-instance/openconfig-flexalgo:flex-algorithm/openconfig-flexalgo:flex-algorithm-definition/openconfig-flexalgo:algorithm/openconfig-flexalgo:config/openconfig-flexalgo:metric-type" {
    deviate delete {
      default IGP;
    }
  }

  deviation "/openconfig-network-instance:network-instances/openconfig-network-instance:network-instance/openconfig-flexalgo:flex-algorithm/openconfig-flexalgo:flex-algorithm-definition/openconfig-flexalgo:algorithm/openconfig-flexalgo:config/openconfig-flexalgo:priority" {
    deviate delete {
      default 237;
    }
  }

  deviation "/openconfig-network-instance:network-instances/openconfig-network-instance:network-instance/openconfig-flexalgo:flex-algorithm/openconfig-flexalgo:flex-algorithm-definition/openconfig-flexalgo:algorithm/openconfig-flexalgo:state/openconfig-flexalgo:metric-type" {
    deviate delete {
      default IGP;
    }
  }

  deviation "/openconfig-network-instance:network-instances/openconfig-network-instance:network-instance/openconfig-flexalgo:flex-algorithm/openconfig-flexalgo:flex-algorithm-definition/openconfig-flexalgo:algorithm/openconfig-flexalgo:state/openconfig-flexalgo:priority" {
    deviate delete {
      default 237;
    }
  }

  deviation "/openconfig-network-instance:network-instances/openconfig-network-instance:network-instance/openconfig-network-instance:afts/openconfig-network-instance:next-hop-groups/openconfig-network-instance:next-hop-group/openconfig-network-instance:state/openconfig-network-instance:backup-active" {
    deviate delete {
      default false;
    }
  }

  deviation "/openconfig-network-instance:network-instances/openconfig-network-instance:network-instance/openconfig-network-instance:policy-forwarding/openconfig-network-instance:policies/openconfig-network-instance:policy/openconfig-network-instance:config/openconfig-network-instance:type" {
    deviate delete {
      default PBR_POLICY;
    }
  }

  deviation "/openconfig-network-instance:network-instances/openconfig-network-instance:network-instance/openconfig-network-instance:policy-forwarding/openconfig-network-instance:policies/openconfig-network-instance:policy/openconfig-network-instance:rules/openconfig-network-instance:rule/openconfig-network-instance:action/openconfig-network-instance:config/openconfig-network-instance:decapsulate-gre" {
    deviate delete {
      default false;
    }
  }

  deviation "/openconfig-network-instance:network-instances/openconfig-network-instance:network-instance/openconfig-network-instance:policy-forwarding/openconfig-network-instance:policies/openconfig-network-instance:policy/openconfig-network-instance:rules/openconfig-network-instance:rule/openconfig-network-instance:action/openconfig-network-instance:config/openconfig-network-instance:decapsulate-gue" {
    deviate delete {
      default false;
    }
  }

  deviation "/openconfig-network-instance:network-instances/openconfig-network-instance:network-instance/openconfig-network-instance:policy-forwarding/openconfig-network-instance:policies/openconfig-network-instance:policy/openconfig-network-instance:rules/openconfig-network-instance:rule/openconfig-network-instance:action/openconfig-network-instance:config/openconfig-network-instance:decapsulate-mpls-in-udp" {
    deviate delete {
      default false;
    }
  }

  deviation "/openconfig-network-instance:network-instances/openconfig-network-instance:network-instance/openconfig-network-instance:policy-forwarding/openconfig-network-instance:policies/openconfig-network-instance:policy/openconfig-network-instance:rules/openconfig-network-instance:rule/openconfig-network-instance:action/openconfig-network-instance:state/openconfig-network-instance:decapsulate-gre" {
    deviate delete {
      default false;
    }
  }

  deviation "/openconfig-network-instance:network-instances/openconfig-network-instance:network-instance/openconfig-network-instance:policy-forwarding/openconfig-network-instance:policies/openconfig-network-instance:policy/openconfig-network-instance:rules/openconfig-network-instance:rule/openconfig-network-instance:action/openconfig-network-instance:state/openconfig-network-instance:decapsulate-gue" {
    deviate delete {
      default false;
    }
  }

  deviation "/openconfig-network-instance:network-instances/openconfig-network-instance:network-instance/openconfig-network-instance:policy-forwarding/openconfig-network-instance:policies/openconfig-network-instance:policy/openconfig-network-instance:rules/openconfig-network-instance:rule/openconfig-network-instance:action/openconfig-network-instance:state/openconfig-network-instance:decapsulate-mpls-in-udp" {
    deviate delete {
      default false;
    }
  }

  deviation "/openconfig-network-instance:network-instances/openconfig-network-instance:network-instance/openconfig-network-instance:policy-forwarding/openconfig-network-instance:policies/openconfig-network-instance:policy/openconfig-network-instance:state/openconfig-network-instance:type" {
    deviate delete {
      default PBR_POLICY;
    }
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:add-paths/openconfig-network-instance:config/openconfig-network-instance:receive" {
    deviate delete {
      default false;
    }
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:add-paths/openconfig-network-instance:config/openconfig-network-instance:send" {
    deviate delete {
      default false;
    }
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:add-paths/openconfig-network-instance:state/openconfig-network-instance:receive" {
    deviate delete {
      default false;
    }
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:add-paths/openconfig-network-instance:state/openconfig-network-instance:send" {
    deviate delete {
      default false;
    }
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:config/openconfig-network-instance:enabled" {
    deviate delete {
      default false;
    }
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:ipv4-unicast/openconfig-network-instance:config/openconfig-network-instance:extended-next-hop-encoding" {
    deviate delete {
      default false;
    }
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:ipv4-unicast/openconfig-network-instance:state/openconfig-network-instance:extended-next-hop-encoding" {
    deviate delete {
      default false;
    }
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:route-selection-options/openconfig-network-instance:config/openconfig-network-instance:enable-aigp" {
    deviate delete {
      default false;
    }
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:route-selection-options/openconfig-network-instance:state/openconfig-network-instance:enable-aigp" {
    deviate delete {
      default false;
    }
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:state/openconfig-network-instance:enabled" {
    deviate delete {
      default false;
    }
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:use-multiple-paths/openconfig-network-instance:ebgp/openconfig-network-instance:config/openconfig-network-instance:allow-multiple-as" {
    deviate delete {
      default false;
    }
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:use-multiple-paths/openconfig-network-instance:ebgp/openconfig-network-instance:config/openconfig-network-instance:maximum-paths" {
    deviate delete {
      default 1;
    }
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:use-multiple-paths/openconfig-network-instance:ebgp/openconfig-network-instance:state/openconfig-network-instance:allow-multiple-as" {
    deviate delete {
      default false;
    }
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:use-multiple-paths/openconfig-network-instance:ebgp/openconfig-network-instance:state/openconfig-network-instance:maximum-paths" {
    deviate delete {
      default 1;
    }
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:use-multiple-paths/openconfig-network-instance:ibgp/openconfig-network-instance:config/openconfig-network-instance:maximum-paths" {
    deviate delete {
      default 1;
    }
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:use-multiple-paths/openconfig-network-instance:ibgp/openconfig-network-instance:state/openconfig-network-instance:maximum-paths" {
    deviate delete {
      default 1;
    }
  }

  deviation "/openconfig-network-instance:network-instances/openconfig-network-instance:network-instance/openconfig-network-instance:protocols/openconfig-network-instance:protocol/openconfig-network-instance:bgp/openconfig-network-instance:global/openconfig-network-instance:route-selection-options/openconfig-network-instance:config/openconfig-network-instance:always-compare-med" {
    deviate delete {
      default false;
    }
  }

  deviation "/openconfig-network-instance:network-instances/openconfig-network-instance:network-instance/openconfig-network-instance:protocols/openconfig-network-instance:protocol/openconfig-network-instance:bgp/openconfig-network-instance:global/openconfig-network-instance:route-selection-options/openconfig-network-instance:state/openconfig-network-instance:always-compare-med" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:add-paths/openconfig-network-instance:config/openconfig-network-instance:receive" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:add-paths/openconfig-network-instance:config/openconfig-network-instance:send" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:add-paths/openconfig-network-instance:state/openconfig-network-instance:receive" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:add-paths/openconfig-network-instance:state/openconfig-network-instance:send" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:apply-policy/openconfig-network-instance:config/openconfig-network-instance:default-export-policy" {
    deviate delete {
      default REJECT_ROUTE;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:apply-policy/openconfig-network-instance:config/openconfig-network-instance:default-import-policy" {
    deviate delete {
      default REJECT_ROUTE;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:apply-policy/openconfig-network-instance:state/openconfig-network-instance:default-export-policy" {
    deviate delete {
      default REJECT_ROUTE;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:apply-policy/openconfig-network-instance:state/openconfig-network-instance:default-import-policy" {
    deviate delete {
      default REJECT_ROUTE;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:ipv4-unicast/openconfig-network-instance:config/openconfig-network-instance:extended-next-hop-encoding" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:ipv4-unicast/openconfig-network-instance:config/openconfig-network-instance:send-default-route" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:ipv4-unicast/openconfig-network-instance:prefix-limit-received/openconfig-network-instance:config/openconfig-network-instance:prevent-teardown" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:ipv4-unicast/openconfig-network-instance:prefix-limit-received/openconfig-network-instance:state/openconfig-network-instance:prevent-teardown" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:ipv4-unicast/openconfig-network-instance:prefix-limit/openconfig-network-instance:config/openconfig-network-instance:prevent-teardown" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:ipv4-unicast/openconfig-network-instance:prefix-limit/openconfig-network-instance:state/openconfig-network-instance:prevent-teardown" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:ipv4-unicast/openconfig-network-instance:state/openconfig-network-instance:extended-next-hop-encoding" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:ipv4-unicast/openconfig-network-instance:state/openconfig-network-instance:send-default-route" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:ipv6-unicast/openconfig-network-instance:config/openconfig-network-instance:send-default-route" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:ipv6-unicast/openconfig-network-instance:prefix-limit-received/openconfig-network-instance:config/openconfig-network-instance:prevent-teardown" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:ipv6-unicast/openconfig-network-instance:prefix-limit-received/openconfig-network-instance:state/openconfig-network-instance:prevent-teardown" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:ipv6-unicast/openconfig-network-instance:prefix-limit/openconfig-network-instance:config/openconfig-network-instance:prevent-teardown" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:ipv6-unicast/openconfig-network-instance:prefix-limit/openconfig-network-instance:state/openconfig-network-instance:prevent-teardown" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:ipv6-unicast/openconfig-network-instance:state/openconfig-network-instance:send-default-route" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:l3vpn-ipv4-unicast/openconfig-network-instance:prefix-limit-received/openconfig-network-instance:config/openconfig-network-instance:prevent-teardown" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:l3vpn-ipv4-unicast/openconfig-network-instance:prefix-limit-received/openconfig-network-instance:state/openconfig-network-instance:prevent-teardown" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:l3vpn-ipv4-unicast/openconfig-network-instance:prefix-limit/openconfig-network-instance:config/openconfig-network-instance:prevent-teardown" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:l3vpn-ipv4-unicast/openconfig-network-instance:prefix-limit/openconfig-network-instance:state/openconfig-network-instance:prevent-teardown" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:l3vpn-ipv6-unicast/openconfig-network-instance:prefix-limit-received/openconfig-network-instance:config/openconfig-network-instance:prevent-teardown" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:l3vpn-ipv6-unicast/openconfig-network-instance:prefix-limit-received/openconfig-network-instance:state/openconfig-network-instance:prevent-teardown" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:l3vpn-ipv6-unicast/openconfig-network-instance:prefix-limit/openconfig-network-instance:config/openconfig-network-instance:prevent-teardown" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:l3vpn-ipv6-unicast/openconfig-network-instance:prefix-limit/openconfig-network-instance:state/openconfig-network-instance:prevent-teardown" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:as-path-options/openconfig-network-instance:config/openconfig-network-instance:allow-own-as" {
    deviate delete {
      default 0;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:as-path-options/openconfig-network-instance:config/openconfig-network-instance:replace-peer-as" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:as-path-options/openconfig-network-instance:state/openconfig-network-instance:allow-own-as" {
    deviate delete {
      default 0;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:as-path-options/openconfig-network-instance:state/openconfig-network-instance:replace-peer-as" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:auto-link-bandwidth/openconfig-network-instance:import/openconfig-network-instance:config/openconfig-network-instance:enabled" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:auto-link-bandwidth/openconfig-network-instance:import/openconfig-network-instance:config/openconfig-network-instance:transitive" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:auto-link-bandwidth/openconfig-network-instance:import/openconfig-network-instance:state/openconfig-network-instance:enabled" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:auto-link-bandwidth/openconfig-network-instance:import/openconfig-network-instance:state/openconfig-network-instance:transitive" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:config/openconfig-network-instance:enabled" {
    deviate delete {
      default true;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:ebgp-multihop/openconfig-network-instance:config/openconfig-network-instance:enabled" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:ebgp-multihop/openconfig-network-instance:state/openconfig-network-instance:enabled" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:route-reflector/openconfig-network-instance:config/openconfig-network-instance:route-reflector-client" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:route-reflector/openconfig-network-instance:state/openconfig-network-instance:route-reflector-client" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:state/openconfig-network-instance:dynamically-configured" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:state/openconfig-network-instance:enabled" {
    deviate delete {
      default true;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:timers/openconfig-network-instance:config/openconfig-network-instance:connect-retry" {
    deviate delete {
      default 30;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:timers/openconfig-network-instance:config/openconfig-network-instance:hold-time" {
    deviate delete {
      default 90;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:timers/openconfig-network-instance:config/openconfig-network-instance:keepalive-interval" {
    deviate delete {
      default 30;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:timers/openconfig-network-instance:config/openconfig-network-instance:minimum-advertisement-interval" {
    deviate delete {
      default 30;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:timers/openconfig-network-instance:state/openconfig-network-instance:connect-retry" {
    deviate delete {
      default 30;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:timers/openconfig-network-instance:state/openconfig-network-instance:hold-time" {
    deviate delete {
      default 90;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:timers/openconfig-network-instance:state/openconfig-network-instance:keepalive-interval" {
    deviate delete {
      default 30;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:timers/openconfig-network-instance:state/openconfig-network-instance:minimum-advertisement-interval" {
    deviate delete {
      default 30;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:transport/openconfig-network-instance:config/openconfig-network-instance:mtu-discovery" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:transport/openconfig-network-instance:config/openconfig-network-instance:passive-mode" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:transport/openconfig-network-instance:state/openconfig-network-instance:mtu-discovery" {
    deviate delete {
      default false;
    }
  }

  deviation "/openconfig-network-instance:network-instances/openconfig-network-instance:network-instance/openconfig-network-instance:protocols/openconfig-network-instance:protocol/openconfig-network-instance:bgp/openconfig-network-instance:neighbors/openconfig-network-instance:neighbor/openconfig-network-instance:transport/openconfig-network-instance:state/openconfig-network-instance:passive-mode" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:add-paths/openconfig-network-instance:config/openconfig-network-instance:receive" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:add-paths/openconfig-network-instance:config/openconfig-network-instance:send" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:add-paths/openconfig-network-instance:state/openconfig-network-instance:receive" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:add-paths/openconfig-network-instance:state/openconfig-network-instance:send" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:apply-policy/openconfig-network-instance:config/openconfig-network-instance:default-export-policy" {
    deviate delete {
      default REJECT_ROUTE;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:apply-policy/openconfig-network-instance:config/openconfig-network-instance:default-import-policy" {
    deviate delete {
      default REJECT_ROUTE;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:apply-policy/openconfig-network-instance:state/openconfig-network-instance:default-export-policy" {
    deviate delete {
      default REJECT_ROUTE;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:apply-policy/openconfig-network-instance:state/openconfig-network-instance:default-import-policy" {
    deviate delete {
      default REJECT_ROUTE;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:ipv4-unicast/openconfig-network-instance:config/openconfig-network-instance:extended-next-hop-encoding" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:ipv4-unicast/openconfig-network-instance:config/openconfig-network-instance:send-default-route" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:ipv4-unicast/openconfig-network-instance:prefix-limit-received/openconfig-network-instance:config/openconfig-network-instance:prevent-teardown" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:ipv4-unicast/openconfig-network-instance:prefix-limit-received/openconfig-network-instance:state/openconfig-network-instance:prevent-teardown" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:ipv4-unicast/openconfig-network-instance:prefix-limit/openconfig-network-instance:config/openconfig-network-instance:prevent-teardown" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:ipv4-unicast/openconfig-network-instance:prefix-limit/openconfig-network-instance:state/openconfig-network-instance:prevent-teardown" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:ipv4-unicast/openconfig-network-instance:state/openconfig-network-instance:extended-next-hop-encoding" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:ipv4-unicast/openconfig-network-instance:state/openconfig-network-instance:send-default-route" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:ipv6-unicast/openconfig-network-instance:config/openconfig-network-instance:send-default-route" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:ipv6-unicast/openconfig-network-instance:prefix-limit-received/openconfig-network-instance:config/openconfig-network-instance:prevent-teardown" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:ipv6-unicast/openconfig-network-instance:prefix-limit-received/openconfig-network-instance:state/openconfig-network-instance:prevent-teardown" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:ipv6-unicast/openconfig-network-instance:prefix-limit/openconfig-network-instance:config/openconfig-network-instance:prevent-teardown" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:ipv6-unicast/openconfig-network-instance:prefix-limit/openconfig-network-instance:state/openconfig-network-instance:prevent-teardown" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:ipv6-unicast/openconfig-network-instance:state/openconfig-network-instance:send-default-route" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:l3vpn-ipv4-unicast/openconfig-network-instance:prefix-limit-received/openconfig-network-instance:config/openconfig-network-instance:prevent-teardown" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:l3vpn-ipv4-unicast/openconfig-network-instance:prefix-limit-received/openconfig-network-instance:state/openconfig-network-instance:prevent-teardown" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:l3vpn-ipv4-unicast/openconfig-network-instance:prefix-limit/openconfig-network-instance:config/openconfig-network-instance:prevent-teardown" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:l3vpn-ipv4-unicast/openconfig-network-instance:prefix-limit/openconfig-network-instance:state/openconfig-network-instance:prevent-teardown" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:l3vpn-ipv6-unicast/openconfig-network-instance:prefix-limit-received/openconfig-network-instance:config/openconfig-network-instance:prevent-teardown" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:l3vpn-ipv6-unicast/openconfig-network-instance:prefix-limit-received/openconfig-network-instance:state/openconfig-network-instance:prevent-teardown" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:l3vpn-ipv6-unicast/openconfig-network-instance:prefix-limit/openconfig-network-instance:config/openconfig-network-instance:prevent-teardown" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:l3vpn-ipv6-unicast/openconfig-network-instance:prefix-limit/openconfig-network-instance:state/openconfig-network-instance:prevent-teardown" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:as-path-options/openconfig-network-instance:config/openconfig-network-instance:allow-own-as" {
    deviate delete {
      default 0;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:as-path-options/openconfig-network-instance:config/openconfig-network-instance:replace-peer-as" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:as-path-options/openconfig-network-instance:state/openconfig-network-instance:allow-own-as" {
    deviate delete {
      default 0;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:as-path-options/openconfig-network-instance:state/openconfig-network-instance:replace-peer-as" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:auto-link-bandwidth/openconfig-network-instance:import/openconfig-network-instance:config/openconfig-network-instance:enabled" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:auto-link-bandwidth/openconfig-network-instance:import/openconfig-network-instance:config/openconfig-network-instance:transitive" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:auto-link-bandwidth/openconfig-network-instance:import/openconfig-network-instance:state/openconfig-network-instance:enabled" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:auto-link-bandwidth/openconfig-network-instance:import/openconfig-network-instance:state/openconfig-network-instance:transitive" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:ebgp-multihop/openconfig-network-instance:config/openconfig-network-instance:enabled" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:ebgp-multihop/openconfig-network-instance:state/openconfig-network-instance:enabled" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:route-reflector/openconfig-network-instance:config/openconfig-network-instance:route-reflector-client" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:route-reflector/openconfig-network-instance:state/openconfig-network-instance:route-reflector-client" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:timers/openconfig-network-instance:config/openconfig-network-instance:connect-retry" {
    deviate delete {
      default 30;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:timers/openconfig-network-instance:config/openconfig-network-instance:hold-time" {
    deviate delete {
      default 90;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:timers/openconfig-network-instance:config/openconfig-network-instance:keepalive-interval" {
    deviate delete {
      default 30;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:timers/openconfig-network-instance:config/openconfig-network-instance:minimum-advertisement-interval" {
    deviate delete {
      default 30;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:timers/openconfig-network-instance:state/openconfig-network-instance:connect-retry" {
    deviate delete {
      default 30;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:timers/openconfig-network-instance:state/openconfig-network-instance:hold-time" {
    deviate delete {
      default 90;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:timers/openconfig-network-instance:state/openconfig-network-instance:keepalive-interval" {
    deviate delete {
      default 30;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:timers/openconfig-network-instance:state/openconfig-network-instance:minimum-advertisement-interval" {
    deviate delete {
      default 30;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:transport/openconfig-network-instance:config/openconfig-network-instance:mtu-discovery" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:transport/openconfig-network-instance:config/openconfig-network-instance:passive-mode" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:transport/openconfig-network-instance:state/openconfig-network-instance:mtu-discovery" {
    deviate delete {
      default false;
    }
  }

  deviation "/openconfig-network-instance:network-instances/openconfig-network-instance:network-instance/openconfig-network-instance:protocols/openconfig-network-instance:protocol/openconfig-network-instance:bgp/openconfig-network-instance:peer-groups/openconfig-network-instance:peer-group/openconfig-network-instance:transport/openconfig-network-instance:state/openconfig-network-instance:passive-mode" {
    deviate delete {
      default false;
    }
  }

  deviation "/openconfig-network-instance:network-instances/openconfig-network-instance:network-instance/openconfig-network-instance:protocols/openconfig-network-instance:protocol/openconfig-network-instance:bgp/openconfig-network-instance:rib/openconfig-network-instance:afi-safis/openconfig-network-instance:afi-safi/openconfig-network-instance:ipv4-unicast/openconfig-network-instance:loc-rib/openconfig-network-instance:routes/openconfig-network-instance:route/openconfig-network-instance:state/openconfig-network-instance:path-id" {
    deviate delete {
      default 0;
    }
  }

  deviation "/openconfig-network-instance:network-instances/openconfig-network-instance:network-instance/openconfig-network-instance:protocols/openconfig-network-instance:protocol/openconfig-network-instance:bgp/openconfig-network-instance:rib/openconfig-network-instance:afi-safis/openconfig-network-instance:afi-safi/openconfig-network-instance:ipv6-unicast/openconfig-network-instance:loc-rib/openconfig-network-instance:routes/openconfig-network-instance:route/openconfig-network-instance:state/openconfig-network-instance:path-id" {
    deviate delete {
      default 0;
    }
  }

  deviation "/openconfig-network-instance:network-instances/openconfig-network-instance:network-instance/openconfig-network-instance:protocols/openconfig-network-instance:protocol/openconfig-network-instance:config/openconfig-network-instance:name" {
    deviate delete {
      default DEFAULT;
    }
  }

  deviation "/openconfig-network-instance:network-instances/openconfig-network-instance:network-instance/openconfig-network-instance:protocols/openconfig-network-instance:protocol/openconfig-network-instance:isis/openconfig-network-instance:global/openconfig-network-instance:config/openconfig-network-instance:csnp-enable-on-p2p-links" {
    deviate delete {
      default true;
    }
  }

  deviation "/openconfig-network-instance:network-instances/openconfig-network-instance:network-instance/openconfig-network-instance:protocols/openconfig-network-instance:protocol/openconfig-network-instance:isis/openconfig-network-instance:global/openconfig-network-instance:config/openconfig-network-instance:hello-padding" {
    deviate delete {
      default STRICT;
    }
  }

  deviation "/openconfig-network-instance:network-instances/openconfig-network-instance:network-instance/openconfig-network-instance:protocols/openconfig-network-instance:protocol/openconfig-network-instance:isis/openconfig-network-instance:global/openconfig-network-instance:config/openconfig-network-instance:iid-tlv" {
    deviate delete {
      default false;
    }
  }

  deviation "/openconfig-network-instance:network-instances/openconfig-network-instance:network-instance/openconfig-network-instance:protocols/openconfig-network-instance:protocol/openconfig-network-instance:isis/openconfig-network-instance:global/openconfig-network-instance:config/openconfig-network-instance:level-capability" {
    deviate delete {
      default LEVEL_1_2;
    }
  }

  deviation "/openconfig-network-instance:network-instances/openconfig-network-instance:network-instance/openconfig-network-instance:protocols/openconfig-network-instance:protocol/openconfig-network-instance:isis/openconfig-network-instance:global/openconfig-network-instance:config/openconfig-network-instance:poi-tlv" {
    deviate delete {
      default false;
    }
  }

  deviation "/openconfig-network-instance:network-instances/openconfig-network-instance:network-instance/openconfig-network-instance:protocols/openconfig-network-instance:protocol/openconfig-network-instance:isis/openconfig-network-instance:global/openconfig-network-instance:config/openconfig-network-instance:weighted-ecmp" {
    deviate delete {
      default false;
    }
  }

  deviation "/openconfig-network-instance:network-instances/openconfig-network-instance:network-instance/openconfig-network-instance:protocols/openconfig-network-instance:protocol/openconfig-network-instance:isis/openconfig-network-instance:global/openconfig-network-instance:graceful-restart/openconfig-network-instance:config/openconfig-network-instance:enabled" {
    deviate delete {
      default false;
    }
  }

  deviation "/openconfig-network-instance:network-instances/openconfig-network-instance:network-instance/openconfig-network-instance:protocols/openconfig-network-instance:protocol/openconfig-network-instance:isis/openconfig-network-instance:global/openconfig-network-instance:graceful-restart/openconfig-network-instance:state/openconfig-network-instance:enabled" {
    deviate delete {
      default false;
    }
  }

  deviation "/openconfig-network-instance:network-instances/openconfig-network-instance:network-instance/openconfig-network-instance:protocols/openconfig-network-instance:protocol/openconfig-network-instance:isis/openconfig-network-instance:global/openconfig-network-instance:lsp-bit/openconfig-network-instance:attached-bit/openconfig-network-instance:config/openconfig-network-instance:ignore-bit" {
    deviate delete {
      default false;
    }
  }

  deviation "/openconfig-network-instance:network-instances/openconfig-network-instance:network-instance/openconfig-network-instance:protocols/openconfig-network-instance:protocol/openconfig-network-instance:isis/openconfig-network-instance:global/openconfig-network-instance:lsp-bit/openconfig-network-instance:attached-bit/openconfig-network-instance:config/openconfig-network-instance:suppress-bit" {
    deviate delete {
      default false;
    }
  }

  deviation "/openconfig-network-instance:network-instances/openconfig-network-instance:network-instance/openconfig-network-instance:protocols/openconfig-network-instance:protocol/openconfig-network-instance:isis/openconfig-network-instance:global/openconfig-network-instance:lsp-bit/openconfig-network-instance:attached-bit/openconfig-network-instance:state/openconfig-network-instance:ignore-bit" {
    deviate delete {
      default false;
    }
  }

  deviation "/openconfig-network-instance:network-instances/openconfig-network-instance:network-instance/openconfig-network-instance:protocols/openconfig-network-instance:protocol/openconfig-network-instance:isis/openconfig-network-instance:global/openconfig-network-instance:lsp-bit/openconfig-network-instance:attached-bit/openconfig-network-instance:state/openconfig-network-instance:suppress-bit" {
    deviate delete {
      default false;
    }
  }

  deviation "/openconfig-network-instance:network-instances/openconfig-network-instance:network-instance/openconfig-network-instance:protocols/openconfig-network-instance:protocol/openconfig-network-instance:isis/openconfig-network-instance:global/openconfig-network-instance:lsp-bit/openconfig-network-instance:overload-bit/openconfig-network-instance:config/openconfig-network-instance:advertise-high-metric" {
    deviate delete {
      default false;
    }
  }

  deviation "/openconfig-network-instance:network-instances/openconfig-network-instance:network-instance/openconfig-network-instance:protocols/openconfig-network-instance:protocol/openconfig-network-instance:isis/openconfig-network-instance:global/openconfig-network-instance:lsp-bit/openconfig-network-instance:overload-bit/openconfig-network-instance:config/openconfig-network-instance:set-bit" {
    deviate delete {
      default false;
    }
  }

  deviation "/openconfig-network-instance:network-instances/openconfig-network-instance:network-instance/openconfig-network-instance:protocols/openconfig-network-instance:protocol/openconfig-network-instance:isis/openconfig-network-instance:global/openconfig-network-instance:lsp-bit/openconfig-network-instance:overload-bit/openconfig-network-instance:config/openconfig-network-instance:set-bit-on-boot" {
    deviate delete {
      default false;
    }
  }

  deviation "/openconfig-network-instance:network-instances/openconfig-network-instance:network-instance/openconfig-network-instance:protocols/openconfig-network-instance:protocol/openconfig-network-instance:isis/openconfig-network-instance:global/openconfig-network-instance:lsp-bit/openconfig-network-instance:overload-bit/openconfig-network-instance:state/openconfig-network-instance:advertise-high-metric" {
    deviate delete {
      default false;
    }
  }

  deviation "/openconfig-network-instance:network-instances/openconfig-network-instance:network-instance/openconfig-network-instance:protocols/openconfig-network-instance:protocol/openconfig-network-instance:isis/openconfig-network-instance:global/openconfig-network-instance:lsp-bit/openconfig-network-instance:overload-bit/openconfig-network-instance:state/openconfig-network-instance:set-bit" {
    deviate delete {
      default false;
    }
  }

  deviation "/openconfig-network-instance:network-instances/openconfig-network-instance:network-instance/openconfig-network-instance:protocols/openconfig-network-instance:protocol/openconfig-network-instance:isis/openconfig-network-instance:global/openconfig-network-instance:lsp-bit/openconfig-network-instance:overload-bit/openconfig-network-instance:state/openconfig-network-instance:set-bit-on-boot" {
    deviate delete {
      default false;
    }
  }

  deviation "/openconfig-network-instance:network-instances/openconfig-network-instance:network-instance/openconfig-network-instance:protocols/openconfig-network-instance:protocol/openconfig-network-instance:isis/openconfig-network-instance:global/openconfig-network-instance:state/openconfig-network-instance:csnp-enable-on-p2p-links" {
    deviate delete {
      default true;
    }
  }

  deviation "/openconfig-network-instance:network-instances/openconfig-network-instance:network-instance/openconfig-network-instance:protocols/openconfig-network-instance:protocol/openconfig-network-instance:isis/openconfig-network-instance:global/openconfig-network-instance:state/openconfig-network-instance:hello-padding" {
    deviate delete {
      default STRICT;
    }
  }

  deviation "/openconfig-network-instance:network-instances/openconfig-network-instance:network-instance/openconfig-network-instance:protocols/openconfig-network-instance:protocol/openconfig-network-instance:isis/openconfig-network-instance:global/openconfig-network-instance:state/openconfig-network-instance:iid-tlv" {
    deviate delete {
      default false;
    }
  }

  deviation "/openconfig-network-instance:network-instances/openconfig-network-instance:network-instance/openconfig-network-instance:protocols/openconfig-network-instance:protocol/openconfig-network-instance:isis/openconfig-network-instance:global/openconfig-network-instance:state/openconfig-network-instance:level-capability" {
    deviate delete {
      default LEVEL_1_2;
    }
  }

  deviation "/openconfig-network-instance:network-instances/openconfig-network-instance:network-instance/openconfig-network-instance:protocols/openconfig-network-instance:protocol/openconfig-network-instance:isis/openconfig-network-instance:global/openconfig-network-instance:state/openconfig-network-instance:poi-tlv" {
    deviate delete {
      default false;
    }
  }

  deviation "/openconfig-network-instance:network-instances/openconfig-network-instance:network-instance/openconfig-network-instance:protocols/openconfig-network-instance:protocol/openconfig-network-instance:isis/openconfig-network-instance:global/openconfig-network-instance:state/openconfig-network-instance:weighted-ecmp" {
    deviate delete {
      default false;
    }
  }

  deviation "/openconfig-network-instance:network-instances/openconfig-network-instance:network-instance/openconfig-network-instance:protocols/openconfig-network-instance:protocol/openconfig-network-instance:isis/openconfig-network-instance:global/openconfig-network-instance:timers/openconfig-network-instance:config/openconfig-network-instance:lsp-lifetime-interval" {
    deviate delete {
      default 1200;
    }
  }

  deviation "/openconfig-network-instance:network-instances/openconfig-network-instance:network-instance/openconfig-network-instance:protocols/openconfig-network-instance:protocol/openconfig-network-instance:isis/openconfig-network-instance:global/openconfig-network-instance:timers/openconfig-network-instance:spf/openconfig-network-instance:config/openconfig-network-instance:spf-hold-interval" {
    deviate delete {
      default 5000;
    }
  }

  deviation "/openconfig-network-instance:network-instances/openconfig-network-instance:network-instance/openconfig-network-instance:protocols/openconfig-network-instance:protocol/openconfig-network-instance:isis/openconfig-network-instance:global/openconfig-network-instance:timers/openconfig-network-instance:spf/openconfig-network-instance:state/openconfig-network-instance:spf-hold-interval" {
    deviate delete {
      default 5000;
    }
  }

  deviation "/openconfig-network-instance:network-instances/openconfig-network-instance:network-instance/openconfig-network-instance:protocols/openconfig-network-instance:protocol/openconfig-network-instance:isis/openconfig-network-instance:global/openconfig-network-instance:timers/openconfig-network-instance:state/openconfig-network-instance:lsp-lifetime-interval" {
    deviate delete {
      default 1200;
    }
  }

  deviation "/openconfig-network-instance:network-instances/openconfig-network-instance:network-instance/openconfig-network-instance:protocols/openconfig-network-instance:protocol/openconfig-network-instance:isis/openconfig-network-instance:interfaces/openconfig-network-instance:interface/openconfig-network-instance:authentication/openconfig-network-instance:config/openconfig-network-instance:enabled" {
    deviate delete {
      default false;
    }
  }

  deviation "/openconfig-network-instance:network-instances/openconfig-network-instance:network-instance/openconfig-network-instance:protocols/openconfig-network-instance:protocol/openconfig-network-instance:isis/openconfig-network-instance:interfaces/openconfig-network-instance:interface/openconfig-network-instance:authentication/openconfig-network-instance:state/openconfig-network-instance:enabled" {
    deviate delete {
      default false;
    }
  }

  deviation "/openconfig-network-instance:network-instances/openconfig-network-instance:network-instance/openconfig-network-instance:protocols/openconfig-network-instance:protocol/openconfig-network-instance:isis/openconfig-network-instance:interfaces/openconfig-network-instance:interface/openconfig-network-instance:config/openconfig-network-instance:enabled" {
    deviate delete {
      default false;
    }
  }

  deviation "/openconfig-network-instance:network-instances/openconfig-network-instance:network-instance/openconfig-network-instance:protocols/openconfig-network-instance:protocol/openconfig-network-instance:isis/openconfig-network-instance:interfaces/openconfig-network-instance:interface/openconfig-network-instance:config/openconfig-network-instance:passive" {
    deviate delete {
      default false;
    }
  }

  deviation "/openconfig-network-instance:network-instances/openconfig-network-instance:network-instance/openconfig-network-instance:protocols/openconfig-network-instance:protocol/openconfig-network-instance:isis/openconfig-network-instance:interfaces/openconfig-network-instance:interface/openconfig-network-instance:levels/openconfig-network-instance:level/openconfig-network-instance:afi-safi/openconfig-network-instance:af/openconfig-network-instance:config/openconfig-network-instance:metric" {
    deviate delete {
      default 10;
    }
  }

  deviation "/openconfig-network-instance:network-instances/openconfig-network-instance:network-instance/openconfig-network-instance:protocols/openconfig-network-instance:protocol/openconfig-network-instance:isis/openconfig-network-instance:interfaces/openconfig-network-instance:interface/openconfig-network-instance:levels/openconfig-network-instance:level/openconfig-network-instance:afi-safi/openconfig-network-instance:af/openconfig-network-instance:state/openconfig-network-instance:metric" {
    deviate delete {
      default 10;
    }
  }

  deviation "/openconfig-network-instance:network-instances/openconfig-network-instance:network-instance/openconfig-network-instance:protocols/openconfig-network-instance:protocol/openconfig-network-instance:isis/openconfig-network-instance:interfaces/openconfig-network-instance:interface/openconfig-network-instance:levels/openconfig-network-instance:level/openconfig-network-instance:config/openconfig-network-instance:enabled" {
    deviate delete {
      default false;
    }
  }

  deviation "/openconfig-network-instance:network-instances/openconfig-network-instance:network-instance/openconfig-network-instance:protocols/openconfig-network-instance:protocol/openconfig-network-instance:isis/openconfig-network-instance:interfaces/openconfig-network-instance:interface/openconfig-network-instance:levels/openconfig-network-instance:level/openconfig-network-instance:config/openconfig-network-instance:passive" {
    deviate delete {
      default false;
    }
  }

  deviation "/openconfig-network-instance:network-instances/openconfig-network-instance:network-instance/openconfig-network-instance:protocols/openconfig-network-instance:protocol/openconfig-network-instance:isis/openconfig-network-instance:interfaces/openconfig-network-instance:interface/openconfig-network-instance:levels/openconfig-network-instance:level/openconfig-network-instance:hello-authentication/openconfig-network-instance:config/openconfig-network-instance:enabled" {
    deviate delete {
      default false;
    }
  }

  deviation "/openconfig-network-instance:network-instances/openconfig-network-instance:network-instance/openconfig-network-instance:protocols/openconfig-network-instance:protocol/openconfig-network-instance:isis/openconfig-network-instance:interfaces/openconfig-network-instance:interface/openconfig-network-instance:levels/openconfig-network-instance:level/openconfig-network-instance:hello-authentication/openconfig-network-instance:state/openconfig-network-instance:enabled" {
    deviate delete {
      default false;
    }
  }

  deviation "/openconfig-network-instance:network-instances/openconfig-network-instance:network-instance/openconfig-network-instance:protocols/openconfig-network-instance:protocol/openconfig-network-instance:isis/openconfig-network-instance:interfaces/openconfig-network-instance:interface/openconfig-network-instance:levels/openconfig-network-instance:level/openconfig-network-instance:state/openconfig-network-instance:enabled" {
    deviate delete {
      default false;
    }
  }

  deviation "/openconfig-network-instance:network-instances/openconfig-network-instance:network-instance/openconfig-network-instance:protocols/openconfig-network-instance:protocol/openconfig-network-instance:isis/openconfig-network-instance:interfaces/openconfig-network-instance:interface/openconfig-network-instance:levels/openconfig-network-instance:level/openconfig-network-instance:state/openconfig-network-instance:passive" {
    deviate delete {
      default false;
    }
  }

  deviation "/openconfig-network-instance:network-instances/openconfig-network-instance:network-instance/openconfig-network-instance:protocols/openconfig-network-instance:protocol/openconfig-network-instance:isis/openconfig-network-instance:interfaces/openconfig-network-instance:interface/openconfig-network-instance:state/openconfig-network-instance:enabled" {
    deviate delete {
      default false;
    }
  }

  deviation "/openconfig-network-instance:network-instances/openconfig-network-instance:network-instance/openconfig-network-instance:protocols/openconfig-network-instance:protocol/openconfig-network-instance:isis/openconfig-network-instance:interfaces/openconfig-network-instance:interface/openconfig-network-instance:state/openconfig-network-instance:passive" {
    deviate delete {
      default false;
    }
  }

  deviation "/openconfig-network-instance:network-instances/openconfig-network-instance:network-instance/openconfig-network-instance:protocols/openconfig-network-instance:protocol/openconfig-network-instance:isis/openconfig-network-instance:interfaces/openconfig-network-instance:interface/openconfig-network-instance:weighted-ecmp/openconfig-network-instance:config/openconfig-network-instance:load-balancing-weight" {
    deviate delete {
      default auto;
    }
  }

  deviation "/openconfig-network-instance:network-instances/openconfig-network-instance:network-instance/openconfig-network-instance:protocols/openconfig-network-instance:protocol/openconfig-network-instance:isis/openconfig-network-instance:interfaces/openconfig-network-instance:interface/openconfig-network-instance:weighted-ecmp/openconfig-network-instance:state/openconfig-network-instance:load-balancing-weight" {
    deviate delete {
      default auto;
    }
  }

  deviation "/openconfig-network-instance:network-instances/openconfig-network-instance:network-instance/openconfig-network-instance:protocols/openconfig-network-instance:protocol/openconfig-network-instance:isis/openconfig-network-instance:levels/openconfig-network-instance:level/openconfig-network-instance:authentication/openconfig-network-instance:config/openconfig-network-instance:disable-csnp" {
    deviate delete {
      default false;
    }
  }

  deviation "/openconfig-network-instance:network-instances/openconfig-network-instance:network-instance/openconfig-network-instance:protocols/openconfig-network-instance:protocol/openconfig-network-instance:isis/openconfig-network-instance:levels/openconfig-network-instance:level/openconfig-network-instance:authentication/openconfig-network-instance:config/openconfig-network-instance:disable-lsp" {
    deviate delete {
      default false;
    }
  }

  deviation "/openconfig-network-instance:network-instances/openconfig-network-instance:network-instance/openconfig-network-instance:protocols/openconfig-network-instance:protocol/openconfig-network-instance:isis/openconfig-network-instance:levels/openconfig-network-instance:level/openconfig-network-instance:authentication/openconfig-network-instance:config/openconfig-network-instance:disable-psnp" {
    deviate delete {
      default false;
    }
  }

  deviation "/openconfig-network-instance:network-instances/openconfig-network-instance:network-instance/openconfig-network-instance:protocols/openconfig-network-instance:protocol/openconfig-network-instance:isis/openconfig-network-instance:levels/openconfig-network-instance:level/openconfig-network-instance:authentication/openconfig-network-instance:config/openconfig-network-instance:enabled" {
    deviate delete {
      default false;
    }
  }

  deviation "/openconfig-network-instance:network-instances/openconfig-network-instance:network-instance/openconfig-network-instance:protocols/openconfig-network-instance:protocol/openconfig-network-instance:isis/openconfig-network-instance:levels/openconfig-network-instance:level/openconfig-network-instance:authentication/openconfig-network-instance:state/openconfig-network-instance:disable-csnp" {
    deviate delete {
      default false;
    }
  }

  deviation "/openconfig-network-instance:network-instances/openconfig-network-instance:network-instance/openconfig-network-instance:protocols/openconfig-network-instance:protocol/openconfig-network-instance:isis/openconfig-network-instance:levels/openconfig-network-instance:level/openconfig-network-instance:authentication/openconfig-network-instance:state/openconfig-network-instance:disable-lsp" {
    deviate delete {
      default false;
    }
  }

  deviation "/openconfig-network-instance:network-instances/openconfig-network-instance:network-instance/openconfig-network-instance:protocols/openconfig-network-instance:protocol/openconfig-network-instance:isis/openconfig-network-instance:levels/openconfig-network-instance:level/openconfig-network-instance:authentication/openconfig-network-instance:state/openconfig-network-instance:disable-psnp" {
    deviate delete {
      default false;
    }
  }

  deviation "/openconfig-network-instance:network-instances/openconfig-network-instance:network-instance/openconfig-network-instance:protocols/openconfig-network-instance:protocol/openconfig-network-instance:isis/openconfig-network-instance:levels/openconfig-network-instance:level/openconfig-network-instance:authentication/openconfig-network-instance:state/openconfig-network-instance:enabled" {
    deviate delete {
      default false;
    }
  }

  deviation "/openconfig-network-instance:network-instances/openconfig-network-instance:network-instance/openconfig-network-instance:protocols/openconfig-network-instance:protocol/openconfig-network-instance:isis/openconfig-network-instance:levels/openconfig-network-instance:level/openconfig-network-instance:link-state-database/openconfig-network-instance:lsp/openconfig-network-instance:state/openconfig-network-instance:version" {
    deviate delete {
      default 1;
    }
  }

  deviation "/openconfig-network-instance:network-instances/openconfig-network-instance:network-instance/openconfig-network-instance:protocols/openconfig-network-instance:protocol/openconfig-network-instance:isis/openconfig-network-instance:levels/openconfig-network-instance:level/openconfig-network-instance:link-state-database/openconfig-network-instance:lsp/openconfig-network-instance:state/openconfig-network-instance:version2" {
    deviate delete {
      default 1;
    }
  }

  deviation "/openconfig-network-instance:network-instances/openconfig-network-instance:network-instance/openconfig-network-instance:protocols/openconfig-network-instance:protocol/openconfig-network-instance:state/openconfig-network-instance:name" {
    deviate delete {
      default DEFAULT;
    }
  }

  deviation "/openconfig-network-instance:network-instances/openconfig-network-instance:network-instance/openconfig-network-instance:protocols/openconfig-network-instance:protocol/openconfig-network-instance:static-routes/openconfig-network-instance:static/openconfig-network-instance:next-hops/openconfig-network-instance:next-hop/openconfig-network-instance:config/openconfig-network-instance:recurse" {
    deviate delete {
      default false;
    }
  }

  deviation "/openconfig-network-instance:network-instances/openconfig-network-instance:network-instance/openconfig-network-instance:protocols/openconfig-network-instance:protocol/openconfig-network-instance:static-routes/openconfig-network-instance:static/openconfig-network-instance:next-hops/openconfig-network-instance:next-hop/openconfig-network-instance:state/openconfig-network-instance:recurse" {
    deviate delete {
      default false;
    }
  }

  deviation "/openconfig-network-instance:network-instances/openconfig-network-instance:network-instance/openconfig-network-instance:static/openconfig-network-instance:next-hops/openconfig-network-instance:next-hop/openconfig-network-instance:config/openconfig-network-instance:recurse" {
    deviate delete {
      default false;
    }
  }

  deviation "/openconfig-network-instance:network-instances/openconfig-network-instance:network-instance/openconfig-network-instance:static/openconfig-network-instance:next-hops/openconfig-network-instance:next-hop/openconfig-network-instance:state/openconfig-network-instance:recurse" {
    deviate delete {
      default false;
    }
  }

  deviation "/openconfig-network-instance:network-instances/openconfig-network-instance:network-instance/openconfig-network-instance:table-connections/openconfig-network-instance:table-connection/openconfig-network-instance:config/openconfig-network-instance:default-import-policy" {
    deviate delete {
      default REJECT_ROUTE;
    }
  }

  deviation "/openconfig-network-instance:network-instances/openconfig-network-instance:network-instance/openconfig-network-instance:table-connections/openconfig-network-instance:table-connection/openconfig-network-instance:config/openconfig-network-instance:disable-metric-propagation" {
    deviate delete {
      default false;
    }
  }

  deviation "/openconfig-network-instance:network-instances/openconfig-network-instance:network-instance/openconfig-network-instance:table-connections/openconfig-network-instance:table-connection/openconfig-network-instance:state/openconfig-network-instance:default-import-policy" {
    deviate delete {
      default REJECT_ROUTE;
    }
  }

  deviation "/openconfig-network-instance:network-instances/openconfig-network-instance:network-instance/openconfig-network-instance:table-connections/openconfig-network-instance:table-connection/openconfig-network-instance:state/openconfig-network-instance:disable-metric-propagation" {
    deviate delete {
      default false;
    }
  }

  deviation "/openconfig-platform:components/openconfig-platform:component/openconfig-platform-linecard:linecard/openconfig-platform-linecard:config/openconfig-platform-linecard:power-admin-state" {
    deviate delete {
      default POWER_ENABLED;
    }
  }

  deviation "/openconfig-platform:components/openconfig-platform:component/openconfig-platform-linecard:linecard/openconfig-platform-linecard:state/openconfig-platform-linecard:power-admin-state" {
    deviate delete {
      default POWER_ENABLED;
    }
  }

  deviation "/openconfig-platform:components/openconfig-platform:component/openconfig-platform:fabric/openconfig-platform:config/openconfig-platform-fabric:power-admin-state" {
    deviate delete {
      default POWER_ENABLED;
    }
  }

  deviation "/openconfig-platform:components/openconfig-platform:component/openconfig-platform:fabric/openconfig-platform:state/openconfig-platform-fabric:power-admin-state" {
    deviate delete {
      default POWER_ENABLED;
    }
  }

  deviation "/openconfig-platform:components/openconfig-platform:component/openconfig-platform:state/openconfig-platform:empty" {
    deviate delete {
      default false;
    }
  }

  deviation "/openconfig-qos:qos/openconfig-qos:queue-management-profiles/openconfig-qos:queue-management-profile/openconfig-qos:wred/openconfig-qos:uniform/openconfig-qos:config/openconfig-qos:drop" {
    deviate delete {
      default false;
    }
  }

  deviation "/openconfig-qos:qos/openconfig-qos:queue-management-profiles/openconfig-qos:queue-management-profile/openconfig-qos:wred/openconfig-qos:uniform/openconfig-qos:config/openconfig-qos:enable-ecn" {
    deviate delete {
      default false;
    }
  }

  deviation "/openconfig-qos:qos/openconfig-qos:queue-management-profiles/openconfig-qos:queue-management-profile/openconfig-qos:wred/openconfig-qos:uniform/openconfig-qos:state/openconfig-qos:drop" {
    deviate delete {
      default false;
    }
  }

  deviation "/openconfig-qos:qos/openconfig-qos:queue-management-profiles/openconfig-qos:queue-management-profile/openconfig-qos:wred/openconfig-qos:uniform/openconfig-qos:state/openconfig-qos:enable-ecn" {
    deviate delete {
      default false;
    }
  }

  deviation "/openconfig-sampling:sampling/openconfig-sampling-sflow:sflow/openconfig-sampling-sflow:collectors/openconfig-sampling-sflow:collector/openconfig-sampling-sflow:config/openconfig-sampling-sflow:port" {
    deviate delete {
      default 6343;
    }
  }

  deviation "/openconfig-sampling:sampling/openconfig-sampling-sflow:sflow/openconfig-sampling-sflow:collectors/openconfig-sampling-sflow:collector/openconfig-sampling-sflow:state/openconfig-sampling-sflow:port" {
    deviate delete {
      default 6343;
    }
  }

  deviation "/openconfig-sampling:sampling/openconfig-sampling-sflow:sflow/openconfig-sampling-sflow:config/openconfig-sampling-sflow:enabled" {
    deviate delete {
      default false;
    }
  }

  deviation "/openconfig-sampling:sampling/openconfig-sampling-sflow:sflow/openconfig-sampling-sflow:config/openconfig-sampling-sflow:sample-size" {
    deviate delete {
      default 128;
    }
  }

  deviation "/openconfig-sampling:sampling/openconfig-sampling-sflow:sflow/openconfig-sampling-sflow:state/openconfig-sampling-sflow:enabled" {
    deviate delete {
      default false;
    }
  }

  deviation "/openconfig-sampling:sampling/openconfig-sampling-sflow:sflow/openconfig-sampling-sflow:state/openconfig-sampling-sflow:sample-size" {
    deviate delete {
      default 128;
    }
  }

  deviation "/openconfig-system:system/openconfig-system-grpc:grpc-servers/openconfig-system-grpc:grpc-server/openconfig-system-grpc:config/openconfig-system-grpc:name" {
    deviate delete {
      default DEFAULT;
    }
  }

  deviation "/openconfig-system:system/openconfig-system-grpc:grpc-servers/openconfig-system-grpc:grpc-server/openconfig-system-grpc:state/openconfig-system-grpc:name" {
    deviate delete {
      default DEFAULT;
    }
  }

  deviation "/openconfig-system:system/openconfig-system:aaa/openconfig-system:server-groups/openconfig-system:server-group/openconfig-system:servers/openconfig-system:server/openconfig-system:tacacs/openconfig-system:config/openconfig-system:port" {
    deviate delete {
      default 49;
    }
  }

  deviation "/openconfig-system:system/openconfig-system:aaa/openconfig-system:server-groups/openconfig-system:server-group/openconfig-system:servers/openconfig-system:server/openconfig-system:tacacs/openconfig-system:state/openconfig-system:port" {
    deviate delete {
      default 49;
    }
  }

  deviation "/openconfig-system:system/openconfig-system:logging/openconfig-system:remote-servers/openconfig-system:remote-server/openconfig-system:config/openconfig-system:remote-port" {
    deviate delete {
      default 514;
    }
  }

  deviation "/openconfig-system:system/openconfig-system:logging/openconfig-system:remote-servers/openconfig-system:remote-server/openconfig-system:state/openconfig-system:remote-port" {
    deviate delete {
      default 514;
    }
  }

  deviation "/openconfig-system:system/openconfig-system:ntp/openconfig-system:config/openconfig-system:enabled" {
    deviate delete {
      default false;
    }
  }

  deviation "/openconfig-system:system/openconfig-system:ntp/openconfig-system:servers/openconfig-system:server/openconfig-system:config/openconfig-system:iburst" {
    deviate delete {
      default false;
    }
  }

  deviation "/openconfig-system:system/openconfig-system:ntp/openconfig-system:servers/openconfig-system:server/openconfig-system:config/openconfig-system:prefer" {
    deviate delete {
      default false;
    }
  }

  deviation "/openconfig-system:system/openconfig-system:ntp/openconfig-system:servers/openconfig-system:server/openconfig-system:state/openconfig-system:iburst" {
    deviate delete {
      default false;
    }
  }

  deviation "/openconfig-system:system/openconfig-system:ntp/openconfig-system:servers/openconfig-system:server/openconfig-system:state/openconfig-system:prefer" {
    deviate delete {
      default false;
    }
  }

  deviation "/openconfig-system:system/openconfig-system:ntp/openconfig-system:state/openconfig-system:enabled" {
    deviate delete {
      default false;
    }
  }

  deviation "/openconfig-system:system/openconfig-system:ssh-server/openconfig-system:config/openconfig-system:enable" {
    deviate delete {
      default true;
    }
  }

  deviation "/openconfig-system:system/openconfig-system:ssh-server/openconfig-system:state/openconfig-system:enable" {
    deviate delete {
      default true;
    }
  }

  deviation "/openconfig-system:system/openconfig-system:ssh-server/openconfig-system:state/openconfig-system:protocol-version" {
    deviate delete {
      default V2;
    }
  }

  deviation "/openconfig-acl:acl/openconfig-acl:acl-sets/openconfig-acl:acl-set/openconfig-acl:acl-entries/openconfig-acl:acl-entry/openconfig-acl:ipv4/openconfig-acl:config/openconfig-acl:dscp" {
    deviate not-supported;
  }

  deviation "/openconfig-acl:acl/openconfig-acl:acl-sets/openconfig-acl:acl-set/openconfig-acl:acl-entries/openconfig-acl:acl-entry/openconfig-acl:ipv4/openconfig-acl:config/openconfig-acl:hop-limit" {
    deviate not-supported;
  }

  deviation "/openconfig-acl:acl/openconfig-acl:acl-sets/openconfig-acl:acl-set/openconfig-acl:acl-entries/openconfig-acl:acl-entry/openconfig-acl:ipv4/openconfig-acl:config/openconfig-acl:length" {
    deviate not-supported;
  }

  deviation "/openconfig-acl:acl/openconfig-acl:acl-sets/openconfig-acl:acl-set/openconfig-acl:acl-entries/openconfig-acl:acl-entry/openconfig-acl:ipv4/openconfig-acl:state/openconfig-acl:dscp" {
    deviate not-supported;
  }

  deviation "/openconfig-acl:acl/openconfig-acl:acl-sets/openconfig-acl:acl-set/openconfig-acl:acl-entries/openconfig-acl:acl-entry/openconfig-acl:ipv4/openconfig-acl:state/openconfig-acl:hop-limit" {
    deviate not-supported;
  }

  deviation "/openconfig-acl:acl/openconfig-acl:acl-sets/openconfig-acl:acl-set/openconfig-acl:acl-entries/openconfig-acl:acl-entry/openconfig-acl:ipv4/openconfig-acl:state/openconfig-acl:length" {
    deviate not-supported;
  }

  deviation "/openconfig-acl:acl/openconfig-acl:acl-sets/openconfig-acl:acl-set/openconfig-acl:acl-entries/openconfig-acl:acl-entry/openconfig-acl:ipv6/openconfig-acl:config/openconfig-acl:dscp" {
    deviate not-supported;
  }

  deviation "/openconfig-acl:acl/openconfig-acl:acl-sets/openconfig-acl:acl-set/openconfig-acl:acl-entries/openconfig-acl:acl-entry/openconfig-acl:ipv6/openconfig-acl:config/openconfig-acl:hop-limit" {
    deviate not-supported;
  }

  deviation "/openconfig-acl:acl/openconfig-acl:acl-sets/openconfig-acl:acl-set/openconfig-acl:acl-entries/openconfig-acl:acl-entry/openconfig-acl:ipv6/openconfig-acl:config/openconfig-acl:length" {
    deviate not-supported;
  }

  deviation "/openconfig-acl:acl/openconfig-acl:acl-sets/openconfig-acl:acl-set/openconfig-acl:acl-entries/openconfig-acl:acl-entry/openconfig-acl:ipv6/openconfig-acl:state/openconfig-acl:dscp" {
    deviate not-supported;
  }

  deviation "/openconfig-acl:acl/openconfig-acl:acl-sets/openconfig-acl:acl-set/openconfig-acl:acl-entries/openconfig-acl:acl-entry/openconfig-acl:ipv6/openconfig-acl:state/openconfig-acl:hop-limit" {
    deviate not-supported;
  }

  deviation "/openconfig-acl:acl/openconfig-acl:acl-sets/openconfig-acl:acl-set/openconfig-acl:acl-entries/openconfig-acl:acl-entry/openconfig-acl:ipv6/openconfig-acl:state/openconfig-acl:length" {
    deviate not-supported;
  }

  deviation "/openconfig-acl:acl/openconfig-acl:acl-sets/openconfig-acl:acl-set/openconfig-acl:acl-entries/openconfig-acl:acl-entry/openconfig-acl:l2" {
    deviate not-supported;
  }

  deviation "/openconfig-acl:acl/openconfig-acl:acl-sets/openconfig-acl:acl-set/openconfig-acl:acl-entries/openconfig-acl:acl-entry/openconfig-acl:state/openconfig-acl:matched-octets" {
    deviate not-supported;
  }

  deviation "/openconfig-acl:acl/openconfig-acl:acl-sets/openconfig-acl:acl-set/openconfig-acl:acl-entries/openconfig-acl:acl-entry/openconfig-acl:transport/openconfig-acl:config/openconfig-acl:builtin-detail" {
    deviate not-supported;
  }

  deviation "/openconfig-acl:acl/openconfig-acl:acl-sets/openconfig-acl:acl-set/openconfig-acl:acl-entries/openconfig-acl:acl-entry/openconfig-acl:transport/openconfig-acl:config/openconfig-acl:destination-port-set" {
    deviate not-supported;
  }

  deviation "/openconfig-acl:acl/openconfig-acl:acl-sets/openconfig-acl:acl-set/openconfig-acl:acl-entries/openconfig-acl:acl-entry/openconfig-acl:transport/openconfig-acl:config/openconfig-acl:detail-mode" {
    deviate not-supported;
  }

  deviation "/openconfig-acl:acl/openconfig-acl:acl-sets/openconfig-acl:acl-set/openconfig-acl:acl-entries/openconfig-acl:acl-entry/openconfig-acl:transport/openconfig-acl:config/openconfig-acl:explicit-detail-match-mode" {
    deviate not-supported;
  }

  deviation "/openconfig-acl:acl/openconfig-acl:acl-sets/openconfig-acl:acl-set/openconfig-acl:acl-entries/openconfig-acl:acl-entry/openconfig-acl:transport/openconfig-acl:config/openconfig-acl:explicit-tcp-flags" {
    deviate not-supported;
  }

  deviation "/openconfig-acl:acl/openconfig-acl:acl-sets/openconfig-acl:acl-set/openconfig-acl:acl-entries/openconfig-acl:acl-entry/openconfig-acl:transport/openconfig-acl:config/openconfig-acl:source-port-set" {
    deviate not-supported;
  }

  deviation "/openconfig-acl:acl/openconfig-acl:acl-sets/openconfig-acl:acl-set/openconfig-acl:acl-entries/openconfig-acl:acl-entry/openconfig-acl:transport/openconfig-acl:state/openconfig-acl:builtin-detail" {
    deviate not-supported;
  }

  deviation "/openconfig-acl:acl/openconfig-acl:acl-sets/openconfig-acl:acl-set/openconfig-acl:acl-entries/openconfig-acl:acl-entry/openconfig-acl:transport/openconfig-acl:state/openconfig-acl:destination-port-set" {
    deviate not-supported;
  }

  deviation "/openconfig-acl:acl/openconfig-acl:acl-sets/openconfig-acl:acl-set/openconfig-acl:acl-entries/openconfig-acl:acl-entry/openconfig-acl:transport/openconfig-acl:state/openconfig-acl:detail-mode" {
    deviate not-supported;
  }

  deviation "/openconfig-acl:acl/openconfig-acl:acl-sets/openconfig-acl:acl-set/openconfig-acl:acl-entries/openconfig-acl:acl-entry/openconfig-acl:transport/openconfig-acl:state/openconfig-acl:explicit-detail-match-mode" {
    deviate not-supported;
  }

  deviation "/openconfig-acl:acl/openconfig-acl:acl-sets/openconfig-acl:acl-set/openconfig-acl:acl-entries/openconfig-acl:acl-entry/openconfig-acl:transport/openconfig-acl:state/openconfig-acl:explicit-tcp-flags" {
    deviate not-supported;
  }

  deviation "/openconfig-acl:acl/openconfig-acl:acl-sets/openconfig-acl:acl-set/openconfig-acl:acl-entries/openconfig-acl:acl-entry/openconfig-acl:transport/openconfig-acl:state/openconfig-acl:source-port-set" {
    deviate not-supported;
  }

  deviation "/openconfig-acl:acl/openconfig-acl:interfaces/openconfig-acl:interface/openconfig-acl:ingress-acl-sets/openconfig-acl:ingress-acl-set/openconfig-acl:acl-entries/openconfig-acl:acl-entry/openconfig-acl:state/openconfig-acl:matched-octets" {
    deviate not-supported;
  }

  deviation "/openconfig-acl:acl/openconfig-acl:state" {
    deviate not-supported;
  }

  deviation "/openconfig-defined-sets:defined-sets/openconfig-defined-sets:port-sets" {
    deviate not-supported;
  }

  deviation "/openconfig-interfaces:interfaces/openconfig-interfaces:interface/openconfig-if-aggregate:aggregation/openconfig-vlan:switched-vlan" {
    deviate not-supported;
  }

  deviation "/openconfig-interfaces:interfaces/openconfig-interfaces:interface/openconfig-if-ethernet:ethernet/openconfig-if-ethernet:config/openconfig-if-ethernet:auto-negotiate" {
    deviate not-supported;
  }

  deviation "/openconfig-interfaces:interfaces/openconfig-interfaces:interface/openconfig-if-ethernet:ethernet/openconfig-if-ethernet:config/openconfig-if-ethernet:duplex-mode" {
    deviate not-supported;
  }

  deviation "/openconfig-interfaces:interfaces/openconfig-interfaces:interface/openconfig-if-ethernet:ethernet/openconfig-if-ethernet:config/openconfig-if-ethernet:enable-flow-control" {
    deviate not-supported;
  }

  deviation "/openconfig-interfaces:interfaces/openconfig-interfaces:interface/openconfig-if-ethernet:ethernet/openconfig-if-ethernet:config/openconfig-if-ethernet:fec-mode" {
    deviate not-supported;
  }

  deviation "/openconfig-interfaces:interfaces/openconfig-interfaces:interface/openconfig-if-ethernet:ethernet/openconfig-if-ethernet:config/openconfig-if-ethernet:standalone-link-training" {
    deviate not-supported;
  }

  deviation "/openconfig-interfaces:interfaces/openconfig-interfaces:interface/openconfig-if-ethernet:ethernet/openconfig-if-ethernet:state/openconfig-if-ethernet:auto-negotiate" {
    deviate not-supported;
  }

  deviation "/openconfig-interfaces:interfaces/openconfig-interfaces:interface/openconfig-if-ethernet:ethernet/openconfig-if-ethernet:state/openconfig-if-ethernet:counters/openconfig-if-ethernet:in-8021q-frames" {
    deviate not-supported;
  }

  deviation "/openconfig-interfaces:interfaces/openconfig-interfaces:interface/openconfig-if-ethernet:ethernet/openconfig-if-ethernet:state/openconfig-if-ethernet:counters/openconfig-if-ethernet:in-block-errors" {
    deviate not-supported;
  }

  deviation "/openconfig-interfaces:interfaces/openconfig-interfaces:interface/openconfig-if-ethernet:ethernet/openconfig-if-ethernet:state/openconfig-if-ethernet:counters/openconfig-if-ethernet:in-carrier-errors" {
    deviate not-supported;
  }

  deviation "/openconfig-interfaces:interfaces/openconfig-interfaces:interface/openconfig-if-ethernet:ethernet/openconfig-if-ethernet:state/openconfig-if-ethernet:counters/openconfig-if-ethernet:in-interrupted-tx" {
    deviate not-supported;
  }

  deviation "/openconfig-interfaces:interfaces/openconfig-interfaces:interface/openconfig-if-ethernet:ethernet/openconfig-if-ethernet:state/openconfig-if-ethernet:counters/openconfig-if-ethernet:in-late-collision" {
    deviate not-supported;
  }

  deviation "/openconfig-interfaces:interfaces/openconfig-interfaces:interface/openconfig-if-ethernet:ethernet/openconfig-if-ethernet:state/openconfig-if-ethernet:counters/openconfig-if-ethernet:in-mac-control-frames" {
    deviate not-supported;
  }

  deviation "/openconfig-interfaces:interfaces/openconfig-interfaces:interface/openconfig-if-ethernet:ethernet/openconfig-if-ethernet:state/openconfig-if-ethernet:counters/openconfig-if-ethernet:in-mac-errors-rx" {
    deviate not-supported;
  }

  deviation "/openconfig-interfaces:interfaces/openconfig-interfaces:interface/openconfig-if-ethernet:ethernet/openconfig-if-ethernet:state/openconfig-if-ethernet:counters/openconfig-if-ethernet:in-maxsize-exceeded" {
    deviate not-supported;
  }

  deviation "/openconfig-interfaces:interfaces/openconfig-interfaces:interface/openconfig-if-ethernet:ethernet/openconfig-if-ethernet:state/openconfig-if-ethernet:counters/openconfig-if-ethernet:in-single-collision" {
    deviate not-supported;
  }

  deviation "/openconfig-interfaces:interfaces/openconfig-interfaces:interface/openconfig-if-ethernet:ethernet/openconfig-if-ethernet:state/openconfig-if-ethernet:counters/openconfig-if-ethernet:in-symbol-error" {
    deviate not-supported;
  }

  deviation "/openconfig-interfaces:interfaces/openconfig-interfaces:interface/openconfig-if-ethernet:ethernet/openconfig-if-ethernet:state/openconfig-if-ethernet:counters/openconfig-if-ethernet:out-8021q-frames" {
    deviate not-supported;
  }

  deviation "/openconfig-interfaces:interfaces/openconfig-interfaces:interface/openconfig-if-ethernet:ethernet/openconfig-if-ethernet:state/openconfig-if-ethernet:counters/openconfig-if-ethernet:out-mac-control-frames" {
    deviate not-supported;
  }

  deviation "/openconfig-interfaces:interfaces/openconfig-interfaces:interface/openconfig-if-ethernet:ethernet/openconfig-if-ethernet:state/openconfig-if-ethernet:counters/openconfig-if-ethernet:out-mac-errors-tx" {
    deviate not-supported;
  }

  deviation "/openconfig-interfaces:interfaces/openconfig-interfaces:interface/openconfig-if-ethernet:ethernet/openconfig-if-ethernet:state/openconfig-if-ethernet:duplex-mode" {
    deviate not-supported;
  }

  deviation "/openconfig-interfaces:interfaces/openconfig-interfaces:interface/openconfig-if-ethernet:ethernet/openconfig-if-ethernet:state/openconfig-if-ethernet:enable-flow-control" {
    deviate not-supported;
  }

  deviation "/openconfig-interfaces:interfaces/openconfig-interfaces:interface/openconfig-if-ethernet:ethernet/openconfig-if-ethernet:state/openconfig-if-ethernet:fec-mode" {
    deviate not-supported;
  }

  deviation "/openconfig-interfaces:interfaces/openconfig-interfaces:interface/openconfig-if-ethernet:ethernet/openconfig-if-ethernet:state/openconfig-if-ethernet:negotiated-duplex-mode" {
    deviate not-supported;
  }

  deviation "/openconfig-interfaces:interfaces/openconfig-interfaces:interface/openconfig-if-ethernet:ethernet/openconfig-if-ethernet:state/openconfig-if-ethernet:negotiated-port-speed" {
    deviate not-supported;
  }

  deviation "/openconfig-interfaces:interfaces/openconfig-interfaces:interface/openconfig-if-ethernet:ethernet/openconfig-if-ethernet:state/openconfig-if-ethernet:post-fec-ber/openconfig-if-ethernet:avg" {
    deviate not-supported;
  }

  deviation "/openconfig-interfaces:interfaces/openconfig-interfaces:interface/openconfig-if-ethernet:ethernet/openconfig-if-ethernet:state/openconfig-if-ethernet:post-fec-ber/openconfig-if-ethernet:interval" {
    deviate not-supported;
  }

  deviation "/openconfig-interfaces:interfaces/openconfig-interfaces:interface/openconfig-if-ethernet:ethernet/openconfig-if-ethernet:state/openconfig-if-ethernet:pre-fec-ber/openconfig-if-ethernet:avg" {
    deviate not-supported;
  }

  deviation "/openconfig-interfaces:interfaces/openconfig-interfaces:interface/openconfig-if-ethernet:ethernet/openconfig-if-ethernet:state/openconfig-if-ethernet:pre-fec-ber/openconfig-if-ethernet:interval" {
    deviate not-supported;
  }

  deviation "/openconfig-interfaces:interfaces/openconfig-interfaces:interface/openconfig-if-ethernet:ethernet/openconfig-if-ethernet:state/openconfig-if-ethernet:standalone-link-training" {
    deviate not-supported;
  }

  deviation "/openconfig-interfaces:interfaces/openconfig-interfaces:interface/openconfig-if-ethernet:ethernet/openconfig-vlan:switched-vlan" {
    deviate not-supported;
  }

  deviation "/openconfig-interfaces:interfaces/openconfig-interfaces:interface/openconfig-interfaces:config/openconfig-vlan:tpid" {
    deviate not-supported;
  }

  deviation "/openconfig-interfaces:interfaces/openconfig-interfaces:interface/openconfig-interfaces:penalty-based-aied" {
    deviate not-supported;
  }

  deviation "/openconfig-interfaces:interfaces/openconfig-interfaces:interface/openconfig-interfaces:state/openconfig-interfaces:counters/openconfig-interfaces:in-unknown-protos" {
    deviate not-supported;
  }

  deviation "/openconfig-interfaces:interfaces/openconfig-interfaces:interface/openconfig-interfaces:state/openconfig-interfaces:counters/openconfig-interfaces:resets" {
    deviate not-supported;
  }

  deviation "/openconfig-interfaces:interfaces/openconfig-interfaces:interface/openconfig-interfaces:state/openconfig-interfaces:cpu" {
    deviate not-supported;
  }

  deviation "/openconfig-interfaces:interfaces/openconfig-interfaces:interface/openconfig-interfaces:state/openconfig-interfaces:logical" {
    deviate not-supported;
  }

  deviation "/openconfig-interfaces:interfaces/openconfig-interfaces:interface/openconfig-interfaces:state/openconfig-vlan:tpid" {
    deviate not-supported;
  }

  deviation "/openconfig-interfaces:interfaces/openconfig-interfaces:interface/openconfig-interfaces:subinterfaces/openconfig-interfaces:subinterface/openconfig-if-ip:ipv4/openconfig-if-ip:addresses/openconfig-if-ip:address/openconfig-if-ip:config/openconfig-if-ip:type" {
    deviate not-supported;
  }

  deviation "/openconfig-interfaces:interfaces/openconfig-interfaces:interface/openconfig-interfaces:subinterfaces/openconfig-interfaces:subinterface/openconfig-if-ip:ipv4/openconfig-if-ip:addresses/openconfig-if-ip:address/openconfig-if-ip:state/openconfig-if-ip:type" {
    deviate not-supported;
  }

  deviation "/openconfig-interfaces:interfaces/openconfig-interfaces:interface/openconfig-interfaces:subinterfaces/openconfig-interfaces:subinterface/openconfig-if-ip:ipv4/openconfig-if-ip:addresses/openconfig-if-ip:address/openconfig-if-ip:vrrp" {
    deviate not-supported;
  }

  deviation "/openconfig-interfaces:interfaces/openconfig-interfaces:interface/openconfig-interfaces:subinterfaces/openconfig-interfaces:subinterface/openconfig-if-ip:ipv4/openconfig-if-ip:config/openconfig-if-ip:dhcp-client" {
    deviate not-supported;
  }

  deviation "/openconfig-interfaces:interfaces/openconfig-interfaces:interface/openconfig-interfaces:subinterfaces/openconfig-interfaces:subinterface/openconfig-if-ip:ipv4/openconfig-if-ip:proxy-arp/openconfig-if-ip:config/openconfig-if-ip:mode" {
    deviate not-supported;
  }

  deviation "/openconfig-interfaces:interfaces/openconfig-interfaces:interface/openconfig-interfaces:subinterfaces/openconfig-interfaces:subinterface/openconfig-if-ip:ipv4/openconfig-if-ip:proxy-arp/openconfig-if-ip:state/openconfig-if-ip:mode" {
    deviate not-supported;
  }

  deviation "/openconfig-interfaces:interfaces/openconfig-interfaces:interface/openconfig-interfaces:subinterfaces/openconfig-interfaces:subinterface/openconfig-if-ip:ipv4/openconfig-if-ip:state/openconfig-if-ip:counters/openconfig-if-ip:in-error-pkts" {
    deviate not-supported;
  }

  deviation "/openconfig-interfaces:interfaces/openconfig-interfaces:interface/openconfig-interfaces:subinterfaces/openconfig-interfaces:subinterface/openconfig-if-ip:ipv4/openconfig-if-ip:state/openconfig-if-ip:counters/openconfig-if-ip:in-multicast-octets" {
    deviate not-supported;
  }

  deviation "/openconfig-interfaces:interfaces/openconfig-interfaces:interface/openconfig-interfaces:subinterfaces/openconfig-interfaces:subinterface/openconfig-if-ip:ipv4/openconfig-if-ip:state/openconfig-if-ip:counters/openconfig-if-ip:in-multicast-pkts" {
    deviate not-supported;
  }

  deviation "/openconfig-interfaces:interfaces/openconfig-interfaces:interface/openconfig-interfaces:subinterfaces/openconfig-interfaces:subinterface/openconfig-if-ip:ipv4/openconfig-if-ip:state/openconfig-if-ip:counters/openconfig-if-ip:in-octets" {
    deviate not-supported;
  }

  deviation "/openconfig-interfaces:interfaces/openconfig-interfaces:interface/openconfig-interfaces:subinterfaces/openconfig-interfaces:subinterface/openconfig-if-ip:ipv4/openconfig-if-ip:state/openconfig-if-ip:counters/openconfig-if-ip:out-error-pkts" {
    deviate not-supported;
  }

  deviation "/openconfig-interfaces:interfaces/openconfig-interfaces:interface/openconfig-interfaces:subinterfaces/openconfig-interfaces:subinterface/openconfig-if-ip:ipv4/openconfig-if-ip:state/openconfig-if-ip:counters/openconfig-if-ip:out-multicast-octets" {
    deviate not-supported;
  }

  deviation "/openconfig-interfaces:interfaces/openconfig-interfaces:interface/openconfig-interfaces:subinterfaces/openconfig-interfaces:subinterface/openconfig-if-ip:ipv4/openconfig-if-ip:state/openconfig-if-ip:counters/openconfig-if-ip:out-multicast-pkts" {
    deviate not-supported;
  }

  deviation "/openconfig-interfaces:interfaces/openconfig-interfaces:interface/openconfig-interfaces:subinterfaces/openconfig-interfaces:subinterface/openconfig-if-ip:ipv4/openconfig-if-ip:state/openconfig-if-ip:counters/openconfig-if-ip:out-octets" {
    deviate not-supported;
  }

  deviation "/openconfig-interfaces:interfaces/openconfig-interfaces:interface/openconfig-interfaces:subinterfaces/openconfig-interfaces:subinterface/openconfig-if-ip:ipv4/openconfig-if-ip:state/openconfig-if-ip:dhcp-client" {
    deviate not-supported;
  }

  deviation "/openconfig-interfaces:interfaces/openconfig-interfaces:interface/openconfig-interfaces:subinterfaces/openconfig-interfaces:subinterface/openconfig-if-ip:ipv4/openconfig-if-ip:unnumbered/openconfig-if-ip:config/openconfig-if-ip:enabled" {
    deviate not-supported;
  }

  deviation "/openconfig-interfaces:interfaces/openconfig-interfaces:interface/openconfig-interfaces:subinterfaces/openconfig-interfaces:subinterface/openconfig-if-ip:ipv4/openconfig-if-ip:unnumbered/openconfig-if-ip:interface-ref/openconfig-if-ip:config/openconfig-if-ip:interface" {
    deviate not-supported;
  }

  deviation "/openconfig-interfaces:interfaces/openconfig-interfaces:interface/openconfig-interfaces:subinterfaces/openconfig-interfaces:subinterface/openconfig-if-ip:ipv4/openconfig-if-ip:unnumbered/openconfig-if-ip:interface-ref/openconfig-if-ip:config/openconfig-if-ip:subinterface" {
    deviate not-supported;
  }

  deviation "/openconfig-interfaces:interfaces/openconfig-interfaces:interface/openconfig-interfaces:subinterfaces/openconfig-interfaces:subinterface/openconfig-if-ip:ipv4/openconfig-if-ip:unnumbered/openconfig-if-ip:interface-ref/openconfig-if-ip:state/openconfig-if-ip:interface" {
    deviate not-supported;
  }

  deviation "/openconfig-interfaces:interfaces/openconfig-interfaces:interface/openconfig-interfaces:subinterfaces/openconfig-interfaces:subinterface/openconfig-if-ip:ipv4/openconfig-if-ip:unnumbered/openconfig-if-ip:interface-ref/openconfig-if-ip:state/openconfig-if-ip:subinterface" {
    deviate not-supported;
  }

  deviation "/openconfig-interfaces:interfaces/openconfig-interfaces:interface/openconfig-interfaces:subinterfaces/openconfig-interfaces:subinterface/openconfig-if-ip:ipv4/openconfig-if-ip:unnumbered/openconfig-if-ip:state/openconfig-if-ip:enabled" {
    deviate not-supported;
  }

  deviation "/openconfig-interfaces:interfaces/openconfig-interfaces:interface/openconfig-interfaces:subinterfaces/openconfig-interfaces:subinterface/openconfig-if-ip:ipv6/openconfig-if-ip:addresses/openconfig-if-ip:address/openconfig-if-ip:vrrp" {
    deviate not-supported;
  }

  deviation "/openconfig-interfaces:interfaces/openconfig-interfaces:interface/openconfig-interfaces:subinterfaces/openconfig-interfaces:subinterface/openconfig-if-ip:ipv6/openconfig-if-ip:config/openconfig-if-ip:dhcp-client" {
    deviate not-supported;
  }

  deviation "/openconfig-interfaces:interfaces/openconfig-interfaces:interface/openconfig-interfaces:subinterfaces/openconfig-interfaces:subinterface/openconfig-if-ip:ipv6/openconfig-if-ip:config/openconfig-if-ip:dup-addr-detect-transmits" {
    deviate not-supported;
  }

  deviation "/openconfig-interfaces:interfaces/openconfig-interfaces:interface/openconfig-interfaces:subinterfaces/openconfig-interfaces:subinterface/openconfig-if-ip:ipv6/openconfig-if-ip:router-advertisement/openconfig-if-ip:config/openconfig-if-ip:managed" {
    deviate not-supported;
  }

  deviation "/openconfig-interfaces:interfaces/openconfig-interfaces:interface/openconfig-interfaces:subinterfaces/openconfig-interfaces:subinterface/openconfig-if-ip:ipv6/openconfig-if-ip:router-advertisement/openconfig-if-ip:config/openconfig-if-ip:mode" {
    deviate not-supported;
  }

  deviation "/openconfig-interfaces:interfaces/openconfig-interfaces:interface/openconfig-interfaces:subinterfaces/openconfig-interfaces:subinterface/openconfig-if-ip:ipv6/openconfig-if-ip:router-advertisement/openconfig-if-ip:config/openconfig-if-ip:other-config" {
    deviate not-supported;
  }

  deviation "/openconfig-interfaces:interfaces/openconfig-interfaces:interface/openconfig-interfaces:subinterfaces/openconfig-interfaces:subinterface/openconfig-if-ip:ipv6/openconfig-if-ip:router-advertisement/openconfig-if-ip:config/openconfig-if-ip:suppress" {
    deviate not-supported;
  }

  deviation "/openconfig-interfaces:interfaces/openconfig-interfaces:interface/openconfig-interfaces:subinterfaces/openconfig-interfaces:subinterface/openconfig-if-ip:ipv6/openconfig-if-ip:router-advertisement/openconfig-if-ip:prefixes" {
    deviate not-supported;
  }

  deviation "/openconfig-interfaces:interfaces/openconfig-interfaces:interface/openconfig-interfaces:subinterfaces/openconfig-interfaces:subinterface/openconfig-if-ip:ipv6/openconfig-if-ip:router-advertisement/openconfig-if-ip:state/openconfig-if-ip:managed" {
    deviate not-supported;
  }

  deviation "/openconfig-interfaces:interfaces/openconfig-interfaces:interface/openconfig-interfaces:subinterfaces/openconfig-interfaces:subinterface/openconfig-if-ip:ipv6/openconfig-if-ip:router-advertisement/openconfig-if-ip:state/openconfig-if-ip:mode" {
    deviate not-supported;
  }

  deviation "/openconfig-interfaces:interfaces/openconfig-interfaces:interface/openconfig-interfaces:subinterfaces/openconfig-interfaces:subinterface/openconfig-if-ip:ipv6/openconfig-if-ip:router-advertisement/openconfig-if-ip:state/openconfig-if-ip:other-config" {
    deviate not-supported;
  }

  deviation "/openconfig-interfaces:interfaces/openconfig-interfaces:interface/openconfig-interfaces:subinterfaces/openconfig-interfaces:subinterface/openconfig-if-ip:ipv6/openconfig-if-ip:router-advertisement/openconfig-if-ip:state/openconfig-if-ip:suppress" {
    deviate not-supported;
  }

  deviation "/openconfig-interfaces:interfaces/openconfig-interfaces:interface/openconfig-interfaces:subinterfaces/openconfig-interfaces:subinterface/openconfig-if-ip:ipv6/openconfig-if-ip:state/openconfig-if-ip:counters/openconfig-if-ip:in-error-pkts" {
    deviate not-supported;
  }

  deviation "/openconfig-interfaces:interfaces/openconfig-interfaces:interface/openconfig-interfaces:subinterfaces/openconfig-interfaces:subinterface/openconfig-if-ip:ipv6/openconfig-if-ip:state/openconfig-if-ip:counters/openconfig-if-ip:in-multicast-octets" {
    deviate not-supported;
  }

  deviation "/openconfig-interfaces:interfaces/openconfig-interfaces:interface/openconfig-interfaces:subinterfaces/openconfig-interfaces:subinterface/openconfig-if-ip:ipv6/openconfig-if-ip:state/openconfig-if-ip:counters/openconfig-if-ip:in-multicast-pkts" {
    deviate not-supported;
  }

  deviation "/openconfig-interfaces:interfaces/openconfig-interfaces:interface/openconfig-interfaces:subinterfaces/openconfig-interfaces:subinterface/openconfig-if-ip:ipv6/openconfig-if-ip:state/openconfig-if-ip:counters/openconfig-if-ip:in-octets" {
    deviate not-supported;
  }

  deviation "/openconfig-interfaces:interfaces/openconfig-interfaces:interface/openconfig-interfaces:subinterfaces/openconfig-interfaces:subinterface/openconfig-if-ip:ipv6/openconfig-if-ip:state/openconfig-if-ip:counters/openconfig-if-ip:out-error-pkts" {
    deviate not-supported;
  }

  deviation "/openconfig-interfaces:interfaces/openconfig-interfaces:interface/openconfig-interfaces:subinterfaces/openconfig-interfaces:subinterface/openconfig-if-ip:ipv6/openconfig-if-ip:state/openconfig-if-ip:counters/openconfig-if-ip:out-multicast-octets" {
    deviate not-supported;
  }

  deviation "/openconfig-interfaces:interfaces/openconfig-interfaces:interface/openconfig-interfaces:subinterfaces/openconfig-interfaces:subinterface/openconfig-if-ip:ipv6/openconfig-if-ip:state/openconfig-if-ip:counters/openconfig-if-ip:out-multicast-pkts" {
    deviate not-supported;
  }

  deviation "/openconfig-interfaces:interfaces/openconfig-interfaces:interface/openconfig-interfaces:subinterfaces/openconfig-interfaces:subinterface/openconfig-if-ip:ipv6/openconfig-if-ip:state/openconfig-if-ip:counters/openconfig-if-ip:out-octets" {
    deviate not-supported;
  }

  deviation "/openconfig-interfaces:interfaces/openconfig-interfaces:interface/openconfig-interfaces:subinterfaces/openconfig-interfaces:subinterface/openconfig-if-ip:ipv6/openconfig-if-ip:state/openconfig-if-ip:dhcp-client" {
    deviate not-supported;
  }

  deviation "/openconfig-interfaces:interfaces/openconfig-interfaces:interface/openconfig-interfaces:subinterfaces/openconfig-interfaces:subinterface/openconfig-if-ip:ipv6/openconfig-if-ip:state/openconfig-if-ip:dup-addr-detect-transmits" {
    deviate not-supported;
  }

  deviation "/openconfig-interfaces:interfaces/openconfig-interfaces:interface/openconfig-interfaces:subinterfaces/openconfig-interfaces:subinterface/openconfig-if-ip:ipv6/openconfig-if-ip:unnumbered/openconfig-if-ip:config/openconfig-if-ip:enabled" {
    deviate not-supported;
  }

  deviation "/openconfig-interfaces:interfaces/openconfig-interfaces:interface/openconfig-interfaces:subinterfaces/openconfig-interfaces:subinterface/openconfig-if-ip:ipv6/openconfig-if-ip:unnumbered/openconfig-if-ip:interface-ref/openconfig-if-ip:config/openconfig-if-ip:interface" {
    deviate not-supported;
  }

  deviation "/openconfig-interfaces:interfaces/openconfig-interfaces:interface/openconfig-interfaces:subinterfaces/openconfig-interfaces:subinterface/openconfig-if-ip:ipv6/openconfig-if-ip:unnumbered/openconfig-if-ip:interface-ref/openconfig-if-ip:config/openconfig-if-ip:subinterface" {
    deviate not-supported;
  }

  deviation "/openconfig-interfaces:interfaces/openconfig-interfaces:interface/openconfig-interfaces:subinterfaces/openconfig-interfaces:subinterface/openconfig-if-ip:ipv6/openconfig-if-ip:unnumbered/openconfig-if-ip:interface-ref/openconfig-if-ip:state/openconfig-if-ip:interface" {
    deviate not-supported;
  }

  deviation "/openconfig-interfaces:interfaces/openconfig-interfaces:interface/openconfig-interfaces:subinterfaces/openconfig-interfaces:subinterface/openconfig-if-ip:ipv6/openconfig-if-ip:unnumbered/openconfig-if-ip:interface-ref/openconfig-if-ip:state/openconfig-if-ip:subinterface" {
    deviate not-supported;
  }

  deviation "/openconfig-interfaces:interfaces/openconfig-interfaces:interface/openconfig-interfaces:subinterfaces/openconfig-interfaces:subinterface/openconfig-if-ip:ipv6/openconfig-if-ip:unnumbered/openconfig-if-ip:state/openconfig-if-ip:enabled" {
    deviate not-supported;
  }

  deviation "/openconfig-interfaces:interfaces/openconfig-interfaces:interface/openconfig-interfaces:subinterfaces/openconfig-interfaces:subinterface/openconfig-interfaces:state/openconfig-interfaces:counters/openconfig-interfaces:carrier-transitions" {
    deviate not-supported;
  }

  deviation "/openconfig-interfaces:interfaces/openconfig-interfaces:interface/openconfig-interfaces:subinterfaces/openconfig-interfaces:subinterface/openconfig-interfaces:state/openconfig-interfaces:counters/openconfig-interfaces:in-broadcast-pkts" {
    deviate not-supported;
  }

  deviation "/openconfig-interfaces:interfaces/openconfig-interfaces:interface/openconfig-interfaces:subinterfaces/openconfig-interfaces:subinterface/openconfig-interfaces:state/openconfig-interfaces:counters/openconfig-interfaces:in-fcs-errors" {
    deviate not-supported;
  }

  deviation "/openconfig-interfaces:interfaces/openconfig-interfaces:interface/openconfig-interfaces:subinterfaces/openconfig-interfaces:subinterface/openconfig-interfaces:state/openconfig-interfaces:counters/openconfig-interfaces:in-multicast-pkts" {
    deviate not-supported;
  }

  deviation "/openconfig-interfaces:interfaces/openconfig-interfaces:interface/openconfig-interfaces:subinterfaces/openconfig-interfaces:subinterface/openconfig-interfaces:state/openconfig-interfaces:counters/openconfig-interfaces:in-unicast-pkts" {
    deviate not-supported;
  }

  deviation "/openconfig-interfaces:interfaces/openconfig-interfaces:interface/openconfig-interfaces:subinterfaces/openconfig-interfaces:subinterface/openconfig-interfaces:state/openconfig-interfaces:counters/openconfig-interfaces:in-unknown-protos" {
    deviate not-supported;
  }

  deviation "/openconfig-interfaces:interfaces/openconfig-interfaces:interface/openconfig-interfaces:subinterfaces/openconfig-interfaces:subinterface/openconfig-interfaces:state/openconfig-interfaces:counters/openconfig-interfaces:out-broadcast-pkts" {
    deviate not-supported;
  }

  deviation "/openconfig-interfaces:interfaces/openconfig-interfaces:interface/openconfig-interfaces:subinterfaces/openconfig-interfaces:subinterface/openconfig-interfaces:state/openconfig-interfaces:counters/openconfig-interfaces:out-multicast-pkts" {
    deviate not-supported;
  }

  deviation "/openconfig-interfaces:interfaces/openconfig-interfaces:interface/openconfig-interfaces:subinterfaces/openconfig-interfaces:subinterface/openconfig-interfaces:state/openconfig-interfaces:counters/openconfig-interfaces:out-unicast-pkts" {
    deviate not-supported;
  }

  deviation "/openconfig-interfaces:interfaces/openconfig-interfaces:interface/openconfig-interfaces:subinterfaces/openconfig-interfaces:subinterface/openconfig-interfaces:state/openconfig-interfaces:cpu" {
    deviate not-supported;
  }

  deviation "/openconfig-interfaces:interfaces/openconfig-interfaces:interface/openconfig-interfaces:subinterfaces/openconfig-interfaces:subinterface/openconfig-interfaces:state/openconfig-interfaces:logical" {
    deviate not-supported;
  }

  deviation "/openconfig-interfaces:interfaces/openconfig-interfaces:interface/openconfig-interfaces:subinterfaces/openconfig-interfaces:subinterface/openconfig-interfaces:state/openconfig-interfaces:management" {
    deviate not-supported;
  }

  deviation "/openconfig-interfaces:interfaces/openconfig-interfaces:interface/openconfig-interfaces:subinterfaces/openconfig-interfaces:subinterface/openconfig-vlan:vlan/openconfig-vlan:config/openconfig-vlan:vlan-id" {
    deviate not-supported;
  }

  deviation "/openconfig-interfaces:interfaces/openconfig-interfaces:interface/openconfig-interfaces:subinterfaces/openconfig-interfaces:subinterface/openconfig-vlan:vlan/openconfig-vlan:egress-mapping" {
    deviate not-supported;
  }

  deviation "/openconfig-interfaces:interfaces/openconfig-interfaces:interface/openconfig-interfaces:subinterfaces/openconfig-interfaces:subinterface/openconfig-vlan:vlan/openconfig-vlan:ingress-mapping" {
    deviate not-supported;
  }

  deviation "/openconfig-interfaces:interfaces/openconfig-interfaces:interface/openconfig-interfaces:subinterfaces/openconfig-interfaces:subinterface/openconfig-vlan:vlan/openconfig-vlan:match/openconfig-vlan:double-tagged" {
    deviate not-supported;
  }

  deviation "/openconfig-interfaces:interfaces/openconfig-interfaces:interface/openconfig-interfaces:subinterfaces/openconfig-interfaces:subinterface/openconfig-vlan:vlan/openconfig-vlan:match/openconfig-vlan:double-tagged-inner-list" {
    deviate not-supported;
  }

  deviation "/openconfig-interfaces:interfaces/openconfig-interfaces:interface/openconfig-interfaces:subinterfaces/openconfig-interfaces:subinterface/openconfig-vlan:vlan/openconfig-vlan:match/openconfig-vlan:double-tagged-inner-outer-range" {
    deviate not-supported;
  }

  deviation "/openconfig-interfaces:interfaces/openconfig-interfaces:interface/openconfig-interfaces:subinterfaces/openconfig-interfaces:subinterface/openconfig-vlan:vlan/openconfig-vlan:match/openconfig-vlan:double-tagged-inner-range" {
    deviate not-supported;
  }

  deviation "/openconfig-interfaces:interfaces/openconfig-interfaces:interface/openconfig-interfaces:subinterfaces/openconfig-interfaces:subinterface/openconfig-vlan:vlan/openconfig-vlan:match/openconfig-vlan:double-tagged-outer-list" {
    deviate not-supported;
  }

  deviation "/openconfig-interfaces:interfaces/openconfig-interfaces:interface/openconfig-interfaces:subinterfaces/openconfig-interfaces:subinterface/openconfig-vlan:vlan/openconfig-vlan:match/openconfig-vlan:double-tagged-outer-range" {
    deviate not-supported;
  }

  deviation "/openconfig-interfaces:interfaces/openconfig-interfaces:interface/openconfig-interfaces:subinterfaces/openconfig-interfaces:subinterface/openconfig-vlan:vlan/openconfig-vlan:match/openconfig-vlan:single-tagged-list" {
    deviate not-supported;
  }

  deviation "/openconfig-interfaces:interfaces/openconfig-interfaces:interface/openconfig-interfaces:subinterfaces/openconfig-interfaces:subinterface/openconfig-vlan:vlan/openconfig-vlan:match/openconfig-vlan:single-tagged-range" {
    deviate not-supported;
  }

  deviation "/openconfig-interfaces:interfaces/openconfig-interfaces:interface/openconfig-interfaces:subinterfaces/openconfig-interfaces:subinterface/openconfig-vlan:vlan/openconfig-vlan:state/openconfig-vlan:vlan-id" {
    deviate not-supported;
  }

  deviation "/openconfig-interfaces:interfaces/openconfig-interfaces:interface/openconfig-vlan:routed-vlan" {
    deviate not-supported;
  }

  deviation "/openconfig-lacp:lacp/openconfig-lacp:interfaces/openconfig-lacp:interface/openconfig-lacp:members/openconfig-lacp:member/openconfig-lacp:state/openconfig-lacp:counters/openconfig-lacp:lacp-timeout-transitions" {
    deviate not-supported;
  }

  deviation "/openconfig-lacp:lacp/openconfig-lacp:interfaces/openconfig-lacp:interface/openconfig-lacp:members/openconfig-lacp:member/openconfig-lacp:state/openconfig-lacp:last-change" {
    deviate not-supported;
  }

  deviation "/openconfig-lldp:lldp/openconfig-lldp:config/openconfig-lldp:chassis-id" {
    deviate not-supported;
  }

  deviation "/openconfig-lldp:lldp/openconfig-lldp:config/openconfig-lldp:chassis-id-type" {
    deviate not-supported;
  }

  deviation "/openconfig-lldp:lldp/openconfig-lldp:config/openconfig-lldp:suppress-tlv-advertisement" {
    deviate not-supported;
  }

  deviation "/openconfig-lldp:lldp/openconfig-lldp:config/openconfig-lldp:system-description" {
    deviate not-supported;
  }

  deviation "/openconfig-lldp:lldp/openconfig-lldp:config/openconfig-lldp:system-name" {
    deviate not-supported;
  }

  deviation "/openconfig-lldp:lldp/openconfig-lldp:interfaces/openconfig-lldp:interface/openconfig-lldp:neighbors/openconfig-lldp:neighbor/openconfig-lldp:state/openconfig-lldp:ttl" {
    deviate not-supported;
  }

  deviation "/openconfig-lldp:lldp/openconfig-lldp:state/openconfig-lldp:suppress-tlv-advertisement" {
    deviate not-supported;
  }

  deviation "/openconfig-network-instance:network-instances/openconfig-network-instance:network-instance/openconfig-flexalgo:flex-algorithm/openconfig-flexalgo:flex-algo-global-attributes/openconfig-flexalgo:srlgs" {
    deviate not-supported;
  }

  deviation "/openconfig-network-instance:network-instances/openconfig-network-instance:network-instance/openconfig-flexalgo:flex-algorithm/openconfig-flexalgo:flex-algo-interface-attributes/openconfig-flexalgo:interface/openconfig-flexalgo:config/openconfig-flexalgo:min-delay" {
    deviate not-supported;
  }

  deviation "/openconfig-network-instance:network-instances/openconfig-network-instance:network-instance/openconfig-flexalgo:flex-algorithm/openconfig-flexalgo:flex-algo-interface-attributes/openconfig-flexalgo:interface/openconfig-flexalgo:config/openconfig-flexalgo:srlg-membership" {
    deviate not-supported;
  }

  deviation "/openconfig-network-instance:network-instances/openconfig-network-instance:network-instance/openconfig-flexalgo:flex-algorithm/openconfig-flexalgo:flex-algo-interface-attributes/openconfig-flexalgo:interface/openconfig-flexalgo:state/openconfig-flexalgo:min-delay" {
    deviate not-supported;
  }

  deviation "/openconfig-network-instance:network-instances/openconfig-network-instance:network-instance/openconfig-flexalgo:flex-algorithm/openconfig-flexalgo:flex-algo-interface-attributes/openconfig-flexalgo:interface/openconfig-flexalgo:state/openconfig-flexalgo:srlg-membership" {
    deviate not-supported;
  }

  deviation "/openconfig-network-instance:network-instances/openconfig-network-instance:network-instance/openconfig-flexalgo:flex-algorithm/openconfig-flexalgo:flex-algorithm-definition/openconfig-flexalgo:algorithm/openconfig-flexalgo:config/openconfig-flexalgo:algo-flags" {
    deviate not-supported;
  }

  deviation "/openconfig-network-instance:network-instances/openconfig-network-instance:network-instance/openconfig-flexalgo:flex-algorithm/openconfig-flexalgo:flex-algorithm-definition/openconfig-flexalgo:algorithm/openconfig-flexalgo:config/openconfig-flexalgo:calc-type" {
    deviate not-supported;
  }

  deviation "/openconfig-network-instance:network-instances/openconfig-network-instance:network-instance/openconfig-flexalgo:flex-algorithm/openconfig-flexalgo:flex-algorithm-definition/openconfig-flexalgo:algorithm/openconfig-flexalgo:config/openconfig-flexalgo:flex-algo-name" {
    deviate not-supported;
  }

  deviation "/openconfig-network-instance:network-instances/openconfig-network-instance:network-instance/openconfig-flexalgo:flex-algorithm/openconfig-flexalgo:flex-algorithm-definition/openconfig-flexalgo:algorithm/openconfig-flexalgo:config/openconfig-flexalgo:srlg-exclude" {
    deviate not-supported;
  }

  deviation "/openconfig-network-instance:network-instances/openconfig-network-instance:network-instance/openconfig-flexalgo:flex-algorithm/openconfig-flexalgo:flex-algorithm-definition/openconfig-flexalgo:algorithm/openconfig-flexalgo:state/openconfig-flexalgo:algo-flags" {
    deviate not-supported;
  }

  deviation "/openconfig-network-instance:network-instances/openconfig-network-instance:network-instance/openconfig-flexalgo:flex-algorithm/openconfig-flexalgo:flex-algorithm-definition/openconfig-flexalgo:algorithm/openconfig-flexalgo:state/openconfig-flexalgo:srlg-exclude" {
    deviate not-supported;
  }

  deviation "/openconfig-network-instance:network-instances/openconfig-network-instance:network-instance/openconfig-network-instance:afts/openconfig-network-instance:ethernet" {
    deviate not-supported;
  }

  deviation "/openconfig-network-instance:network-instances/openconfig-network-instance:network-instance/openconfig-network-instance:afts/openconfig-network-instance:ipv4-unicast/openconfig-network-instance:ipv4-entry/openconfig-network-instance:state/openconfig-network-instance:decapsulate-header" {
    deviate not-supported;
  }

  deviation "/openconfig-network-instance:network-instances/openconfig-network-instance:network-instance/openconfig-network-instance:afts/openconfig-network-instance:ipv6-unicast/openconfig-network-instance:ipv6-entry/openconfig-network-instance:state/openconfig-network-instance:counters" {
    deviate not-supported;
  }

  deviation "/openconfig-network-instance:network-instances/openconfig-network-instance:network-instance/openconfig-network-instance:afts/openconfig-network-instance:ipv6-unicast/openconfig-network-instance:ipv6-entry/openconfig-network-instance:state/openconfig-network-instance:decapsulate-header" {
    deviate not-supported;
  }

  deviation "/openconfig-network-instance:network-instances/openconfig-network-instance:network-instance/openconfig-network-instance:afts/openconfig-network-instance:mpls" {
    deviate not-supported;
  }

  deviation "/openconfig-network-instance:network-instances/openconfig-network-instance:network-instance/openconfig-network-instance:afts/openconfig-network-instance:next-hop-groups/openconfig-network-instance:next-hop-group/openconfig-network-instance:conditional" {
    deviate not-supported;
  }

  deviation "/openconfig-network-instance:network-instances/openconfig-network-instance:network-instance/openconfig-network-instance:afts/openconfig-network-instance:next-hop-groups/openconfig-network-instance:next-hop-group/openconfig-network-instance:state/openconfig-network-instance:color" {
    deviate not-supported;
  }

  deviation "/openconfig-network-instance:network-instances/openconfig-network-instance:network-instance/openconfig-network-instance:afts/openconfig-network-instance:next-hop-groups/openconfig-network-instance:next-hop-group/openconfig-network-instance:state/openconfig-network-instance:next-hop-group-name" {
    deviate not-supported;
  }

  deviation "/openconfig-network-instance:network-instances/openconfig-network-instance:network-instance/openconfig-network-instance:afts/openconfig-network-instance:next-hops/openconfig-network-instance:next-hop/openconfig-network-instance:encap-headers/openconfig-network-instance:encap-header/openconfig-network-instance:vxlan/openconfig-network-instance:state/openconfig-network-instance:tunnel-src-ip-address" {
    deviate not-supported;
  }

  deviation "/openconfig-network-instance:network-instances/openconfig-network-instance:network-instance/openconfig-network-instance:afts/openconfig-network-instance:next-hops/openconfig-network-instance:next-hop/openconfig-network-instance:gre" {
    deviate not-supported;
  }

  deviation "/openconfig-network-instance:network-instances/openconfig-network-instance:network-instance/openconfig-network-instance:afts/openconfig-network-instance:next-hops/openconfig-network-instance:next-hop/openconfig-network-instance:ip-in-ip" {
    deviate not-supported;
  }

  deviation "/openconfig-network-instance:network-instances/openconfig-network-instance:network-instance/openconfig-network-instance:afts/openconfig-network-instance:next-hops/openconfig-network-instance:next-hop/openconfig-network-instance:state/openconfig-network-instance:decapsulate-header" {
    deviate not-supported;
  }

  deviation "/openconfig-network-instance:network-instances/openconfig-network-instance:network-instance/openconfig-network-instance:afts/openconfig-network-instance:next-hops/openconfig-network-instance:next-hop/openconfig-network-instance:state/openconfig-network-instance:encapsulate-header" {
    deviate not-supported;
  }

  deviation "/openconfig-network-instance:network-instances/openconfig-network-instance:network-instance/openconfig-network-instance:afts/openconfig-network-instance:next-hops/openconfig-network-instance:next-hop/openconfig-network-instance:state/openconfig-network-instance:lsp-name" {
    deviate not-supported;
  }

  deviation "/openconfig-network-instance:network-instances/openconfig-network-instance:network-instance/openconfig-network-instance:afts/openconfig-network-instance:next-hops/openconfig-network-instance:next-hop/openconfig-network-instance:state/openconfig-network-instance:pop-top-label" {
    deviate not-supported;
  }

  deviation "/openconfig-network-instance:network-instances/openconfig-network-instance:network-instance/openconfig-network-instance:afts/openconfig-network-instance:next-hops/openconfig-network-instance:next-hop/openconfig-network-instance:state/openconfig-network-instance:pushed-mpls-label-stack" {
    deviate not-supported;
  }

  deviation "/openconfig-network-instance:network-instances/openconfig-network-instance:network-instance/openconfig-network-instance:afts/openconfig-network-instance:next-hops/openconfig-network-instance:next-hop/openconfig-network-instance:state/openconfig-network-instance:tunnel-src-ip-address" {
    deviate not-supported;
  }

  deviation "/openconfig-network-instance:network-instances/openconfig-network-instance:network-instance/openconfig-network-instance:afts/openconfig-network-instance:next-hops/openconfig-network-instance:next-hop/openconfig-network-instance:state/openconfig-network-instance:vni-label" {
    deviate not-supported;
  }

  deviation "/openconfig-network-instance:network-instances/openconfig-network-instance:network-instance/openconfig-network-instance:afts/openconfig-network-instance:policy-forwarding" {
    deviate not-supported;
  }

  deviation "/openconfig-network-instance:network-instances/openconfig-network-instance:network-instance/openconfig-network-instance:afts/openconfig-network-instance:state-synced" {
    deviate not-supported;
  }

  deviation "/openconfig-network-instance:network-instances/openconfig-network-instance:network-instance/openconfig-network-instance:config/openconfig-network-instance:fallback-network-instance" {
    deviate not-supported;
  }

  deviation "/openconfig-network-instance:network-instances/openconfig-network-instance:network-instance/openconfig-network-instance:config/openconfig-network-instance:route-distinguisher" {
    deviate not-supported;
  }

  deviation "/openconfig-network-instance:network-instances/openconfig-network-instance:network-instance/openconfig-network-instance:connection-points" {
    deviate not-supported;
  }

  deviation "/openconfig-network-instance:network-instances/openconfig-network-instance:network-instance/openconfig-network-instance:encapsulation" {
    deviate not-supported;
  }

  deviation "/openconfig-network-instance:network-instances/openconfig-network-instance:network-instance/openconfig-network-instance:evpn" {
    deviate not-supported;
  }

  deviation "/openconfig-network-instance:network-instances/openconfig-network-instance:network-instance/openconfig-network-instance:fdb" {
    deviate not-supported;
  }

  deviation "/openconfig-network-instance:network-instances/openconfig-network-instance:network-instance/openconfig-network-instance:inter-instance-policies/openconfig-network-instance:apply-policy/openconfig-network-instance:config/openconfig-network-instance:default-export-policy" {
    deviate not-supported;
  }

  deviation "/openconfig-network-instance:network-instances/openconfig-network-instance:network-instance/openconfig-network-instance:inter-instance-policies/openconfig-network-instance:apply-policy/openconfig-network-instance:config/openconfig-network-instance:default-import-policy" {
    deviate not-supported;
  }

  deviation "/openconfig-network-instance:network-instances/openconfig-network-instance:network-instance/openconfig-network-instance:inter-instance-policies/openconfig-network-instance:apply-policy/openconfig-network-instance:state/openconfig-network-instance:default-export-policy" {
    deviate not-supported;
  }

  deviation "/openconfig-network-instance:network-instances/openconfig-network-instance:network-instance/openconfig-network-instance:inter-instance-policies/openconfig-network-instance:apply-policy/openconfig-network-instance:state/openconfig-network-instance:default-import-policy" {
    deviate not-supported;
  }

  deviation "/openconfig-network-instance:network-instances/openconfig-network-instance:network-instance/openconfig-network-instance:inter-instance-policies/openconfig-network-instance:import-export-policy" {
    deviate not-supported;
  }

  deviation "/openconfig-network-instance:network-instances/openconfig-network-instance:network-instance/openconfig-network-instance:interfaces/openconfig-network-instance:interface/openconfig-network-instance:config/openconfig-network-instance:associated-address-families" {
    deviate not-supported;
  }

  deviation "/openconfig-network-instance:network-instances/openconfig-network-instance:network-instance/openconfig-network-instance:interfaces/openconfig-network-instance:interface/openconfig-network-instance:config/openconfig-network-instance:irb-anycast-gateway" {
    deviate not-supported;
  }

  deviation "/openconfig-network-instance:network-instances/openconfig-network-instance:network-instance/openconfig-network-instance:interfaces/openconfig-network-instance:interface/openconfig-network-instance:config/openconfig-network-instance:mac-pinning" {
    deviate not-supported;
  }

  deviation "/openconfig-network-instance:network-instances/openconfig-network-instance:network-instance/openconfig-network-instance:interfaces/openconfig-network-instance:interface/openconfig-network-instance:state/openconfig-network-instance:associated-address-families" {
    deviate not-supported;
  }

  deviation "/openconfig-network-instance:network-instances/openconfig-network-instance:network-instance/openconfig-network-instance:interfaces/openconfig-network-instance:interface/openconfig-network-instance:state/openconfig-network-instance:irb-anycast-gateway" {
    deviate not-supported;
  }

  deviation "/openconfig-network-instance:network-instances/openconfig-network-instance:network-instance/openconfig-network-instance:interfaces/openconfig-network-instance:interface/openconfig-network-instance:state/openconfig-network-instance:mac-pinning" {
    deviate not-supported;
  }

  deviation "/openconfig-network-instance:network-instances/openconfig-network-instance:network-instance/openconfig-network-instance:mpls/openconfig-network-instance:global" {
    deviate not-supported;
  }

  deviation "/openconfig-network-instance:network-instances/openconfig-network-instance:network-instance/openconfig-network-instance:mpls/openconfig-network-instance:lsps/openconfig-network-instance:constrained-path" {
    deviate not-supported;
  }

  deviation "/openconfig-network-instance:network-instances/openconfig-network-instance:network-instance/openconfig-network-instance:mpls/openconfig-network-instance:lsps/openconfig-network-instance:static-lsps/openconfig-network-instance:static-lsp/openconfig-network-instance:egress/openconfig-network-instance:config/openconfig-network-instance:interface" {
    deviate not-supported;
  }

  deviation "/openconfig-network-instance:network-instances/openconfig-network-instance:network-instance/openconfig-network-instance:mpls/openconfig-network-instance:lsps/openconfig-network-instance:static-lsps/openconfig-network-instance:static-lsp/openconfig-network-instance:egress/openconfig-network-instance:config/openconfig-network-instance:metric" {
    deviate not-supported;
  }

  deviation "/openconfig-network-instance:network-instances/openconfig-network-instance:network-instance/openconfig-network-instance:mpls/openconfig-network-instance:lsps/openconfig-network-instance:static-lsps/openconfig-network-instance:static-lsp/openconfig-network-instance:egress/openconfig-network-instance:config/openconfig-network-instance:next-hop" {
    deviate not-supported;
  }

  deviation "/openconfig-network-instance:network-instances/openconfig-network-instance:network-instance/openconfig-network-instance:mpls/openconfig-network-instance:lsps/openconfig-network-instance:static-lsps/openconfig-network-instance:static-lsp/openconfig-network-instance:egress/openconfig-network-instance:config/openconfig-network-instance:push-label" {
    deviate not-supported;
  }

  deviation "/openconfig-network-instance:network-instances/openconfig-network-instance:network-instance/openconfig-network-instance:mpls/openconfig-network-instance:lsps/openconfig-network-instance:static-lsps/openconfig-network-instance:static-lsp/openconfig-network-instance:egress/openconfig-network-instance:config/openconfig-network-instance:subinterface" {
    deviate not-supported;
  }

  deviation "/openconfig-network-instance:network-instances/openconfig-network-instance:network-instance/openconfig-network-instance:mpls/openconfig-network-instance:lsps/openconfig-network-instance:static-lsps/openconfig-network-instance:static-lsp/openconfig-network-instance:egress/openconfig-network-instance:lsp-next-hops/openconfig-network-instance:lsp-next-hop/openconfig-network-instance:config/openconfig-network-instance:interface" {
    deviate not-supported;
  }

  deviation "/openconfig-network-instance:network-instances/openconfig-network-instance:network-instance/openconfig-network-instance:mpls/openconfig-network-instance:lsps/openconfig-network-instance:static-lsps/openconfig-network-instance:static-lsp/openconfig-network-instance:egress/openconfig-network-instance:lsp-next-hops/openconfig-network-instance:lsp-next-hop/openconfig-network-instance:config/openconfig-network-instance:push-label" {
    deviate not-supported;
  }

  deviation "/openconfig-network-instance:network-instances/openconfig-network-instance:network-instance/openconfig-network-instance:mpls/openconfig-network-instance:lsps/openconfig-network-instance:static-lsps/openconfig-network-instance:static-lsp/openconfig-network-instance:egress/openconfig-network-instance:lsp-next-hops/openconfig-network-instance:lsp-next-hop/openconfig-network-instance:config/openconfig-network-instance:subinterface" {
    deviate not-supported;
  }

  deviation "/openconfig-network-instance:network-instances/openconfig-network-instance:network-instance/openconfig-network-instance:mpls/openconfig-network-instance:lsps/openconfig-network-instance:static-lsps/openconfig-network-instance:static-lsp/openconfig-network-instance:egress/openconfig-network-instance:lsp-next-hops/openconfig-network-instance:lsp-next-hop/openconfig-network-instance:state/openconfig-network-instance:interface" {
    deviate not-supported;
  }

  deviation "/openconfig-network-instance:network-instances/openconfig-network-instance:network-instance/openconfig-network-instance:mpls/openconfig-network-instance:lsps/openconfig-network-instance:static-lsps/openconfig-network-instance:static-lsp/openconfig-network-instance:egress/openconfig-network-instance:lsp-next-hops/openconfig-network-instance:lsp-next-hop/openconfig-network-instance:state/openconfig-network-instance:push-label" {
    deviate not-supported;
  }

  deviation "/openconfig-network-instance:network-instances/openconfig-network-instance:network-instance/openconfig-network-instance:mpls/openconfig-network-instance:lsps/openconfig-network-instance:static-lsps/openconfig-network-instance:static-lsp/openconfig-network-instance:egress/openconfig-network-instance:lsp-next-hops/openconfig-network-instance:lsp-next-hop/openconfig-network-instance:state/openconfig-network-instance:subinterface" {
    deviate not-supported;
  }

  deviation "/openconfig-network-instance:network-instances/openconfig-network-instance:network-instance/openconfig-network-instance:mpls/openconfig-network-instance:lsps/openconfig-network-instance:static-lsps/openconfig-network-instance:static-lsp/openconfig-network-instance:egress/openconfig-network-instance:state/openconfig-network-instance:interface" {
    deviate not-supported;
  }

  deviation "/openconfig-network-instance:network-instances/openconfig-network-instance:network-instance/openconfig-network-instance:mpls/openconfig-network-instance:lsps/openconfig-network-instance:static-lsps/openconfig-network-instance:static-lsp/openconfig-network-instance:egress/openconfig-network-instance:state/openconfig-network-instance:metric" {
    deviate not-supported;
  }

  deviation "/openconfig-network-instance:network-instances/openconfig-network-instance:network-instance/openconfig-network-instance:mpls/openconfig-network-instance:lsps/openconfig-network-instance:static-lsps/openconfig-network-instance:static-lsp/openconfig-network-instance:egress/openconfig-network-instance:state/openconfig-network-instance:next-hop" {
    deviate not-supported;
  }

  deviation "/openconfig-network-instance:network-instances/openconfig-network-instance:network-instance/openconfig-network-instance:mpls/openconfig-network-instance:lsps/openconfig-network-instance:static-lsps/openconfig-network-instance:static-lsp/openconfig-network-instance:egress/openconfig-network-instance:state/openconfig-network-instance:push-label" {
    deviate not-supported;
  }

  deviation "/openconfig-network-instance:network-instances/openconfig-network-instance:network-instance/openconfig-network-instance:mpls/openconfig-network-instance:lsps/openconfig-network-instance:static-lsps/openconfig-network-instance:static-lsp/openconfig-network-instance:egress/openconfig-network-instance:state/openconfig-network-instance:subinterface" {
    deviate not-supported;
  }

  deviation "/openconfig-network-instance:network-instances/openconfig-network-instance:network-instance/openconfig-network-instance:mpls/openconfig-network-instance:lsps/openconfig-network-instance:static-lsps/openconfig-network-instance:static-lsp/openconfig-network-instance:ingress" {
    deviate not-supported;
  }

  deviation "/openconfig-network-instance:network-instances/openconfig-network-instance:network-instance/openconfig-network-instance:mpls/openconfig-network-instance:lsps/openconfig-network-instance:static-lsps/openconfig-network-instance:static-lsp/openconfig-network-instance:transit" {
    deviate not-supported;
  }

  deviation "/openconfig-network-instance:network-instances/openconfig-network-instance:network-instance/openconfig-network-instance:mpls/openconfig-network-instance:lsps/openconfig-network-instance:unconstrained-path" {
    deviate not-supported;
  }

  deviation "/openconfig-network-instance:network-instances/openconfig-network-instance:network-instance/openconfig-network-instance:mpls/openconfig-network-instance:signaling-protocols" {
    deviate not-supported;
  }

  deviation "/openconfig-network-instance:network-instances/openconfig-network-instance:network-instance/openconfig-network-instance:mpls/openconfig-network-instance:te-global-attributes" {
    deviate not-supported;
  }

  deviation "/openconfig-network-instance:network-instances/openconfig-network-instance:network-instance/openconfig-network-instance:mpls/openconfig-network-instance:te-interface-attributes" {
    deviate not-supported;
  }

  deviation "/openconfig-network-instance:network-instances/openconfig-network-instance:network-instance/openconfig-network-instance:policy-forwarding/openconfig-network-instance:interfaces/openconfig-network-instance:interface/openconfig-network-instance:config/openconfig-network-instance:apply-forwarding-policy" {
    deviate not-supported;
  }

  deviation "/openconfig-network-instance:network-instances/openconfig-network-instance:network-instance/openconfig-network-instance:policy-forwarding/openconfig-network-instance:interfaces/openconfig-network-instance:interface/openconfig-network-instance:state/openconfig-network-instance:apply-forwarding-policy" {
    deviate not-supported;
  }

  deviation "/openconfig-network-instance:network-instances/openconfig-network-instance:network-instance/openconfig-network-instance:policy-forwarding/openconfig-network-instance:path-selection-groups" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:action/openconfig-network-instance:config/openconfig-network-instance:discard" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:action/openconfig-network-instance:config/openconfig-network-instance:ip-ttl" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:action/openconfig-network-instance:config/openconfig-network-instance:log" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:action/openconfig-network-instance:config/openconfig-network-instance:path-selection-group" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:action/openconfig-network-instance:encapsulate-gre/openconfig-network-instance:config/openconfig-network-instance:identifying-prefix" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:action/openconfig-network-instance:encapsulate-gre/openconfig-network-instance:state/openconfig-network-instance:identifying-prefix" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:action/openconfig-network-instance:forwarding" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:action/openconfig-network-instance:ipv4" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:action/openconfig-network-instance:ipv6" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:action/openconfig-network-instance:mpls" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:action/openconfig-network-instance:state/openconfig-network-instance:discard" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:action/openconfig-network-instance:state/openconfig-network-instance:ip-ttl" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:action/openconfig-network-instance:state/openconfig-network-instance:log" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:action/openconfig-network-instance:state/openconfig-network-instance:path-selection-group" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:config/openconfig-network-instance:address-family" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:config/openconfig-network-instance:description" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:ipv4/openconfig-network-instance:config/openconfig-network-instance:dscp" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:ipv4/openconfig-network-instance:config/openconfig-network-instance:hop-limit" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:ipv4/openconfig-network-instance:config/openconfig-network-instance:length" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:ipv4/openconfig-network-instance:config/openconfig-network-instance:source-address-prefix-set" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:ipv4/openconfig-network-instance:icmpv4" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:ipv4/openconfig-network-instance:state/openconfig-network-instance:dscp" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:ipv4/openconfig-network-instance:state/openconfig-network-instance:hop-limit" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:ipv4/openconfig-network-instance:state/openconfig-network-instance:length" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:ipv4/openconfig-network-instance:state/openconfig-network-instance:source-address-prefix-set" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:ipv6/openconfig-network-instance:config/openconfig-network-instance:destination-flow-label" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:ipv6/openconfig-network-instance:config/openconfig-network-instance:dscp" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:ipv6/openconfig-network-instance:config/openconfig-network-instance:hop-limit" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:ipv6/openconfig-network-instance:config/openconfig-network-instance:length" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:ipv6/openconfig-network-instance:config/openconfig-network-instance:source-address-prefix-set" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:ipv6/openconfig-network-instance:config/openconfig-network-instance:source-flow-label" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:ipv6/openconfig-network-instance:icmpv6" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:ipv6/openconfig-network-instance:state/openconfig-network-instance:destination-flow-label" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:ipv6/openconfig-network-instance:state/openconfig-network-instance:dscp" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:ipv6/openconfig-network-instance:state/openconfig-network-instance:hop-limit" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:ipv6/openconfig-network-instance:state/openconfig-network-instance:length" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:ipv6/openconfig-network-instance:state/openconfig-network-instance:source-address-prefix-set" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:ipv6/openconfig-network-instance:state/openconfig-network-instance:source-flow-label" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:l2" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:state/openconfig-network-instance:address-family" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:state/openconfig-network-instance:description" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:state/openconfig-network-instance:matched-octets" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:state/openconfig-network-instance:matched-pkts" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:transport/openconfig-network-instance:config/openconfig-network-instance:builtin-detail" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:transport/openconfig-network-instance:config/openconfig-network-instance:destination-port-set" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:transport/openconfig-network-instance:config/openconfig-network-instance:detail-mode" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:transport/openconfig-network-instance:config/openconfig-network-instance:explicit-detail-match-mode" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:transport/openconfig-network-instance:config/openconfig-network-instance:explicit-tcp-flags" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:transport/openconfig-network-instance:config/openconfig-network-instance:source-port-set" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:transport/openconfig-network-instance:state/openconfig-network-instance:builtin-detail" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:transport/openconfig-network-instance:state/openconfig-network-instance:destination-port-set" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:transport/openconfig-network-instance:state/openconfig-network-instance:detail-mode" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:transport/openconfig-network-instance:state/openconfig-network-instance:explicit-detail-match-mode" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:transport/openconfig-network-instance:state/openconfig-network-instance:explicit-tcp-flags" {
    deviate not-supported;
  }

  deviation "/openconfig-network-instance:network-instances/openconfig-network-instance:network-instance/openconfig-network-instance:policy-forwarding/openconfig-network-instance:policies/openconfig-network-instance:policy/openconfig-network-instance:rules/openconfig-network-instance:rule/openconfig-network-instance:transport/openconfig-network-instance:state/openconfig-network-instance:source-port-set" {
    deviate not-supported;
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:apply-policy" {
    deviate not-supported;
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:graceful-restart" {
    deviate not-supported;
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:ipv4-labeled-unicast" {
    deviate not-supported;
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:ipv4-unicast/openconfig-network-instance:config/openconfig-network-instance:send-default-route" {
    deviate not-supported;
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:ipv4-unicast/openconfig-network-instance:prefix-limit" {
    deviate not-supported;
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:ipv4-unicast/openconfig-network-instance:prefix-limit-received" {
    deviate not-supported;
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:ipv4-unicast/openconfig-network-instance:state/openconfig-network-instance:send-default-route" {
    deviate not-supported;
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:ipv6-labeled-unicast" {
    deviate not-supported;
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:ipv6-unicast" {
    deviate not-supported;
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:l2vpn-evpn" {
    deviate not-supported;
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:l2vpn-vpls" {
    deviate not-supported;
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:l3vpn-ipv4-multicast" {
    deviate not-supported;
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:l3vpn-ipv4-unicast" {
    deviate not-supported;
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:l3vpn-ipv6-multicast" {
    deviate not-supported;
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:l3vpn-ipv6-unicast" {
    deviate not-supported;
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:route-selection-options/openconfig-network-instance:config/openconfig-network-instance:advertise-inactive-routes" {
    deviate not-supported;
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:route-selection-options/openconfig-network-instance:config/openconfig-network-instance:always-compare-med" {
    deviate not-supported;
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:route-selection-options/openconfig-network-instance:config/openconfig-network-instance:external-compare-router-id" {
    deviate not-supported;
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:route-selection-options/openconfig-network-instance:config/openconfig-network-instance:ignore-as-path-length" {
    deviate not-supported;
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:route-selection-options/openconfig-network-instance:config/openconfig-network-instance:ignore-next-hop-igp-metric" {
    deviate not-supported;
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:route-selection-options/openconfig-network-instance:state/openconfig-network-instance:advertise-inactive-routes" {
    deviate not-supported;
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:route-selection-options/openconfig-network-instance:state/openconfig-network-instance:always-compare-med" {
    deviate not-supported;
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:route-selection-options/openconfig-network-instance:state/openconfig-network-instance:external-compare-router-id" {
    deviate not-supported;
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:route-selection-options/openconfig-network-instance:state/openconfig-network-instance:ignore-as-path-length" {
    deviate not-supported;
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:route-selection-options/openconfig-network-instance:state/openconfig-network-instance:ignore-next-hop-igp-metric" {
    deviate not-supported;
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:srte-policy-ipv4" {
    deviate not-supported;
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:srte-policy-ipv6" {
    deviate not-supported;
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:use-multiple-paths/openconfig-network-instance:config" {
    deviate not-supported;
  }

  deviation "/openconfig-network-instance:network-instances/openconfig-network-instance:network-instance/openconfig-network-instance:protocols/openconfig-network-instance:protocol/openconfig-network-instance:bgp/openconfig-network-instance:global/openconfig-network-instance:afi-safis/openconfig-network-instance:afi-safi/openconfig-network-instance:use-multiple-paths/openconfig-network-instance:state" {
    deviate not-supported;
  }

  deviation "/openconfig-network-instance:network-instances/openconfig-network-instance:network-instance/openconfig-network-instance:protocols/openconfig-network-instance:protocol/openconfig-network-instance:bgp/openconfig-network-instance:global/openconfig-network-instance:apply-policy" {
    deviate not-supported;
  }

  deviation "/openconfig-network-instance:network-instances/openconfig-network-instance:network-instance/openconfig-network-instance:protocols/openconfig-network-instance:protocol/openconfig-network-instance:bgp/openconfig-network-instance:global/openconfig-network-instance:confederation" {
    deviate not-supported;
  }

  deviation "/openconfig-network-instance:network-instances/openconfig-network-instance:network-instance/openconfig-network-instance:protocols/openconfig-network-instance:protocol/openconfig-network-instance:bgp/openconfig-network-instance:global/openconfig-network-instance:graceful-restart/openconfig-network-instance:config/openconfig-network-instance:helper-only" {
    deviate not-supported;
  }

  deviation "/openconfig-network-instance:network-instances/openconfig-network-instance:network-instance/openconfig-network-instance:protocols/openconfig-network-instance:protocol/openconfig-network-instance:bgp/openconfig-network-instance:global/openconfig-network-instance:graceful-restart/openconfig-network-instance:state/openconfig-network-instance:helper-only" {
    deviate not-supported;
  }

  deviation "/openconfig-network-instance:network-instances/openconfig-network-instance:network-instance/openconfig-network-instance:protocols/openconfig-network-instance:protocol/openconfig-network-instance:bgp/openconfig-network-instance:global/openconfig-network-instance:route-selection-options/openconfig-network-instance:config/openconfig-network-instance:advertise-inactive-routes" {
    deviate not-supported;
  }

  deviation "/openconfig-network-instance:network-instances/openconfig-network-instance:network-instance/openconfig-network-instance:protocols/openconfig-network-instance:protocol/openconfig-network-instance:bgp/openconfig-network-instance:global/openconfig-network-instance:route-selection-options/openconfig-network-instance:config/openconfig-network-instance:enable-aigp" {
    deviate not-supported;
  }

  deviation "/openconfig-network-instance:network-instances/openconfig-network-instance:network-instance/openconfig-network-instance:protocols/openconfig-network-instance:protocol/openconfig-network-instance:bgp/openconfig-network-instance:global/openconfig-network-instance:route-selection-options/openconfig-network-instance:config/openconfig-network-instance:external-compare-router-id" {
    deviate not-supported;
  }

  deviation "/openconfig-network-instance:network-instances/openconfig-network-instance:network-instance/openconfig-network-instance:protocols/openconfig-network-instance:protocol/openconfig-network-instance:bgp/openconfig-network-instance:global/openconfig-network-instance:route-selection-options/openconfig-network-instance:config/openconfig-network-instance:ignore-as-path-length" {
    deviate not-supported;
  }

  deviation "/openconfig-network-instance:network-instances/openconfig-network-instance:network-instance/openconfig-network-instance:protocols/openconfig-network-instance:protocol/openconfig-network-instance:bgp/openconfig-network-instance:global/openconfig-network-instance:route-selection-options/openconfig-network-instance:config/openconfig-network-instance:ignore-next-hop-igp-metric" {
    deviate not-supported;
  }

  deviation "/openconfig-network-instance:network-instances/openconfig-network-instance:network-instance/openconfig-network-instance:protocols/openconfig-network-instance:protocol/openconfig-network-instance:bgp/openconfig-network-instance:global/openconfig-network-instance:route-selection-options/openconfig-network-instance:state/openconfig-network-instance:advertise-inactive-routes" {
    deviate not-supported;
  }

  deviation "/openconfig-network-instance:network-instances/openconfig-network-instance:network-instance/openconfig-network-instance:protocols/openconfig-network-instance:protocol/openconfig-network-instance:bgp/openconfig-network-instance:global/openconfig-network-instance:route-selection-options/openconfig-network-instance:state/openconfig-network-instance:enable-aigp" {
    deviate not-supported;
  }

  deviation "/openconfig-network-instance:network-instances/openconfig-network-instance:network-instance/openconfig-network-instance:protocols/openconfig-network-instance:protocol/openconfig-network-instance:bgp/openconfig-network-instance:global/openconfig-network-instance:route-selection-options/openconfig-network-instance:state/openconfig-network-instance:external-compare-router-id" {
    deviate not-supported;
  }

  deviation "/openconfig-network-instance:network-instances/openconfig-network-instance:network-instance/openconfig-network-instance:protocols/openconfig-network-instance:protocol/openconfig-network-instance:bgp/openconfig-network-instance:global/openconfig-network-instance:route-selection-options/openconfig-network-instance:state/openconfig-network-instance:ignore-as-path-length" {
    deviate not-supported;
  }

  deviation "/openconfig-network-instance:network-instances/openconfig-network-instance:network-instance/openconfig-network-instance:protocols/openconfig-network-instance:protocol/openconfig-network-instance:bgp/openconfig-network-instance:global/openconfig-network-instance:route-selection-options/openconfig-network-instance:state/openconfig-network-instance:ignore-next-hop-igp-metric" {
    deviate not-supported;
  }

  deviation "/openconfig-network-instance:network-instances/openconfig-network-instance:network-instance/openconfig-network-instance:protocols/openconfig-network-instance:protocol/openconfig-network-instance:bgp/openconfig-network-instance:global/openconfig-network-instance:use-multiple-paths" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:add-paths/openconfig-network-instance:config/openconfig-network-instance:eligible-prefix-policy" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:add-paths/openconfig-network-instance:state/openconfig-network-instance:eligible-prefix-policy" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:graceful-restart/openconfig-network-instance:config" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:graceful-restart/openconfig-network-instance:state/openconfig-network-instance:enabled" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:ipv4-labeled-unicast" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:ipv6-labeled-unicast" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:l2vpn-evpn" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:l2vpn-vpls" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:l3vpn-ipv4-multicast" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:l3vpn-ipv6-multicast" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:srte-policy-ipv4" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:srte-policy-ipv6" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:afi-safis/openconfig-network-instance:afi-safi/openconfig-network-instance:use-multiple-paths" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:apply-policy/openconfig-network-instance:config/openconfig-network-instance:default-export-policy" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:apply-policy/openconfig-network-instance:config/openconfig-network-instance:default-import-policy" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:apply-policy/openconfig-network-instance:state/openconfig-network-instance:default-export-policy" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:apply-policy/openconfig-network-instance:state/openconfig-network-instance:default-import-policy" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:as-path-options/openconfig-network-instance:config/openconfig-network-instance:disable-peer-as-filter" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:as-path-options/openconfig-network-instance:state/openconfig-network-instance:disable-peer-as-filter" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:config/openconfig-network-instance:neighbor-port" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:config/openconfig-network-instance:peer-type" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:config/openconfig-network-instance:route-flap-damping" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:config/openconfig-network-instance:send-community" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:config/openconfig-network-instance:send-community-type" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:enable-bfd/openconfig-network-instance:config/openconfig-network-instance:desired-minimum-tx-interval" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:enable-bfd/openconfig-network-instance:config/openconfig-network-instance:detection-multiplier" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:enable-bfd/openconfig-network-instance:config/openconfig-network-instance:required-minimum-receive" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:enable-bfd/openconfig-network-instance:state/openconfig-network-instance:desired-minimum-tx-interval" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:enable-bfd/openconfig-network-instance:state/openconfig-network-instance:detection-multiplier" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:enable-bfd/openconfig-network-instance:state/openconfig-network-instance:required-minimum-receive" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:error-handling/openconfig-network-instance:config/openconfig-network-instance:treat-as-withdraw" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:error-handling/openconfig-network-instance:state/openconfig-network-instance:treat-as-withdraw" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:graceful-restart/openconfig-network-instance:config/openconfig-network-instance:helper-only" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:graceful-restart/openconfig-network-instance:state/openconfig-network-instance:helper-only" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:logging-options" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:state/openconfig-network-instance:neighbor-port" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:state/openconfig-network-instance:route-flap-damping" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:state/openconfig-network-instance:send-community" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:state/openconfig-network-instance:send-community-type" {
    deviate not-supported;
  }

  deviation "/openconfig-network-instance:network-instances/openconfig-network-instance:network-instance/openconfig-network-instance:protocols/openconfig-network-instance:protocol/openconfig-network-instance:bgp/openconfig-network-instance:neighbors/openconfig-network-instance:neighbor/openconfig-network-instance:use-multiple-paths" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:add-paths/openconfig-network-instance:config/openconfig-network-instance:eligible-prefix-policy" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:add-paths/openconfig-network-instance:state/openconfig-network-instance:eligible-prefix-policy" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:graceful-restart" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:ipv4-labeled-unicast" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:ipv4-unicast/openconfig-network-instance:prefix-limit-received/openconfig-network-instance:state/openconfig-network-instance:prefix-limit-exceeded" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:ipv4-unicast/openconfig-network-instance:prefix-limit/openconfig-network-instance:state/openconfig-network-instance:prefix-limit-exceeded" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:ipv6-labeled-unicast" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:ipv6-unicast/openconfig-network-instance:prefix-limit-received/openconfig-network-instance:state/openconfig-network-instance:prefix-limit-exceeded" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:ipv6-unicast/openconfig-network-instance:prefix-limit/openconfig-network-instance:state/openconfig-network-instance:prefix-limit-exceeded" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:l2vpn-evpn" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:l2vpn-vpls" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:l3vpn-ipv4-multicast" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:l3vpn-ipv4-unicast/openconfig-network-instance:prefix-limit-received/openconfig-network-instance:state/openconfig-network-instance:prefix-limit-exceeded" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:l3vpn-ipv4-unicast/openconfig-network-instance:prefix-limit/openconfig-network-instance:state/openconfig-network-instance:prefix-limit-exceeded" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:l3vpn-ipv6-multicast" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:l3vpn-ipv6-unicast/openconfig-network-instance:prefix-limit-received/openconfig-network-instance:state/openconfig-network-instance:prefix-limit-exceeded" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:l3vpn-ipv6-unicast/openconfig-network-instance:prefix-limit/openconfig-network-instance:state/openconfig-network-instance:prefix-limit-exceeded" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:srte-policy-ipv4" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:srte-policy-ipv6" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:use-multiple-paths/openconfig-network-instance:config" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:use-multiple-paths/openconfig-network-instance:ebgp/openconfig-network-instance:config" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:use-multiple-paths/openconfig-network-instance:ebgp/openconfig-network-instance:state" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:use-multiple-paths/openconfig-network-instance:ibgp/openconfig-network-instance:config" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:use-multiple-paths/openconfig-network-instance:ibgp/openconfig-network-instance:state" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:afi-safis/openconfig-network-instance:afi-safi/openconfig-network-instance:use-multiple-paths/openconfig-network-instance:state" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:apply-policy/openconfig-network-instance:config/openconfig-network-instance:default-export-policy" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:apply-policy/openconfig-network-instance:config/openconfig-network-instance:default-import-policy" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:apply-policy/openconfig-network-instance:state/openconfig-network-instance:default-export-policy" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:apply-policy/openconfig-network-instance:state/openconfig-network-instance:default-import-policy" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:as-path-options/openconfig-network-instance:config/openconfig-network-instance:disable-peer-as-filter" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:as-path-options/openconfig-network-instance:state/openconfig-network-instance:disable-peer-as-filter" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:config/openconfig-network-instance:peer-type" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:config/openconfig-network-instance:route-flap-damping" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:config/openconfig-network-instance:send-community" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:config/openconfig-network-instance:send-community-type" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:enable-bfd/openconfig-network-instance:config/openconfig-network-instance:desired-minimum-tx-interval" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:enable-bfd/openconfig-network-instance:config/openconfig-network-instance:detection-multiplier" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:enable-bfd/openconfig-network-instance:config/openconfig-network-instance:required-minimum-receive" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:enable-bfd/openconfig-network-instance:state/openconfig-network-instance:desired-minimum-tx-interval" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:enable-bfd/openconfig-network-instance:state/openconfig-network-instance:detection-multiplier" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:enable-bfd/openconfig-network-instance:state/openconfig-network-instance:required-minimum-receive" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:error-handling/openconfig-network-instance:config" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:error-handling/openconfig-network-instance:state" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:graceful-restart/openconfig-network-instance:config/openconfig-network-instance:helper-only" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:graceful-restart/openconfig-network-instance:state/openconfig-network-instance:helper-only" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:logging-options" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:state/openconfig-network-instance:peer-type" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:state/openconfig-network-instance:route-flap-damping" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:state/openconfig-network-instance:send-community" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:state/openconfig-network-instance:send-community-type" {
    deviate not-supported;
  }

  deviation "/openconfig-network-instance:network-instances/openconfig-network-instance:network-instance/openconfig-network-instance:protocols/openconfig-network-instance:protocol/openconfig-network-instance:bgp/openconfig-network-instance:peer-groups/openconfig-network-instance:peer-group/openconfig-network-instance:use-multiple-paths" {
    deviate not-supported;
  }

  deviation "/openconfig-network-instance:network-instances/openconfig-network-instance:network-instance/openconfig-network-instance:protocols/openconfig-network-instance:protocol/openconfig-network-instance:bgp/openconfig-network-instance:rib/openconfig-network-instance:afi-safis/openconfig-network-instance:afi-safi/openconfig-network-instance:ipv4-srte-policy" {
    deviate not-supported;
  }

  deviation "/openconfig-network-instance:network-instances/openconfig-network-instance:network-instance/openconfig-network-instance:protocols/openconfig-network-instance:protocol/openconfig-network-instance:bgp/openconfig-network-instance:rib/openconfig-network-instance:afi-safis/openconfig-network-instance:afi-safi/openconfig-network-instance:ipv4-unicast/openconfig-network-instance:loc-rib/openconfig-network-instance:routes/openconfig-network-instance:route/openconfig-network-instance:state/openconfig-network-instance:community-index" {
    deviate not-supported;
  }

  deviation "/openconfig-network-instance:network-instances/openconfig-network-instance:network-instance/openconfig-network-instance:protocols/openconfig-network-instance:protocol/openconfig-network-instance:bgp/openconfig-network-instance:rib/openconfig-network-instance:afi-safis/openconfig-network-instance:afi-safi/openconfig-network-instance:ipv4-unicast/openconfig-network-instance:loc-rib/openconfig-network-instance:routes/openconfig-network-instance:route/openconfig-network-instance:state/openconfig-network-instance:ext-community-index" {
    deviate not-supported;
  }

  deviation "/openconfig-network-instance:network-instances/openconfig-network-instance:network-instance/openconfig-network-instance:protocols/openconfig-network-instance:protocol/openconfig-network-instance:bgp/openconfig-network-instance:rib/openconfig-network-instance:afi-safis/openconfig-network-instance:afi-safi/openconfig-network-instance:ipv4-unicast/openconfig-network-instance:loc-rib/openconfig-network-instance:routes/openconfig-network-instance:route/openconfig-network-instance:unknown-attributes" {
    deviate not-supported;
  }

  deviation "/openconfig-network-instance:network-instances/openconfig-network-instance:network-instance/openconfig-network-instance:protocols/openconfig-network-instance:protocol/openconfig-network-instance:bgp/openconfig-network-instance:rib/openconfig-network-instance:afi-safis/openconfig-network-instance:afi-safi/openconfig-network-instance:ipv4-unicast/openconfig-network-instance:neighbors" {
    deviate not-supported;
  }

  deviation "/openconfig-network-instance:network-instances/openconfig-network-instance:network-instance/openconfig-network-instance:protocols/openconfig-network-instance:protocol/openconfig-network-instance:bgp/openconfig-network-instance:rib/openconfig-network-instance:afi-safis/openconfig-network-instance:afi-safi/openconfig-network-instance:ipv6-srte-policy" {
    deviate not-supported;
  }

  deviation "/openconfig-network-instance:network-instances/openconfig-network-instance:network-instance/openconfig-network-instance:protocols/openconfig-network-instance:protocol/openconfig-network-instance:bgp/openconfig-network-instance:rib/openconfig-network-instance:afi-safis/openconfig-network-instance:afi-safi/openconfig-network-instance:ipv6-unicast/openconfig-network-instance:loc-rib/openconfig-network-instance:routes/openconfig-network-instance:route/openconfig-network-instance:state/openconfig-network-instance:community-index" {
    deviate not-supported;
  }

  deviation "/openconfig-network-instance:network-instances/openconfig-network-instance:network-instance/openconfig-network-instance:protocols/openconfig-network-instance:protocol/openconfig-network-instance:bgp/openconfig-network-instance:rib/openconfig-network-instance:afi-safis/openconfig-network-instance:afi-safi/openconfig-network-instance:ipv6-unicast/openconfig-network-instance:loc-rib/openconfig-network-instance:routes/openconfig-network-instance:route/openconfig-network-instance:state/openconfig-network-instance:ext-community-index" {
    deviate not-supported;
  }

  deviation "/openconfig-network-instance:network-instances/openconfig-network-instance:network-instance/openconfig-network-instance:protocols/openconfig-network-instance:protocol/openconfig-network-instance:bgp/openconfig-network-instance:rib/openconfig-network-instance:afi-safis/openconfig-network-instance:afi-safi/openconfig-network-instance:ipv6-unicast/openconfig-network-instance:loc-rib/openconfig-network-instance:routes/openconfig-network-instance:route/openconfig-network-instance:unknown-attributes" {
    deviate not-supported;
  }

  deviation "/openconfig-network-instance:network-instances/openconfig-network-instance:network-instance/openconfig-network-instance:protocols/openconfig-network-instance:protocol/openconfig-network-instance:bgp/openconfig-network-instance:rib/openconfig-network-instance:afi-safis/openconfig-network-instance:afi-safi/openconfig-network-instance:ipv6-unicast/openconfig-network-instance:neighbors" {
    deviate not-supported;
  }

  deviation "/openconfig-network-instance:network-instances/openconfig-network-instance:network-instance/openconfig-network-instance:protocols/openconfig-network-instance:protocol/openconfig-network-instance:bgp/openconfig-network-instance:rib/openconfig-network-instance:afi-safis/openconfig-network-instance:afi-safi/openconfig-network-instance:l2vpn-evpn" {
    deviate not-supported;
  }

  deviation "/openconfig-network-instance:network-instances/openconfig-network-instance:network-instance/openconfig-network-instance:protocols/openconfig-network-instance:protocol/openconfig-network-instance:bgp/openconfig-network-instance:rib/openconfig-network-instance:attr-sets/openconfig-network-instance:attr-set/openconfig-network-instance:aggregator/openconfig-network-instance:state/openconfig-network-instance:as4" {
    deviate not-supported;
  }

  deviation "/openconfig-network-instance:network-instances/openconfig-network-instance:network-instance/openconfig-network-instance:protocols/openconfig-network-instance:protocol/openconfig-network-instance:bgp/openconfig-network-instance:rib/openconfig-network-instance:attr-sets/openconfig-network-instance:attr-set/openconfig-network-instance:as4-path" {
    deviate not-supported;
  }

  deviation "/openconfig-network-instance:network-instances/openconfig-network-instance:network-instance/openconfig-network-instance:protocols/openconfig-network-instance:protocol/openconfig-network-instance:bgp/openconfig-network-instance:rib/openconfig-network-instance:attr-sets/openconfig-network-instance:attr-set/openconfig-network-instance:tunnel-encapsulation" {
    deviate not-supported;
  }

  deviation "/openconfig-network-instance:network-instances/openconfig-network-instance:network-instance/openconfig-network-instance:protocols/openconfig-network-instance:protocol/openconfig-network-instance:bgp/openconfig-network-instance:rib/openconfig-network-instance:communities" {
    deviate not-supported;
  }

  deviation "/openconfig-network-instance:network-instances/openconfig-network-instance:network-instance/openconfig-network-instance:protocols/openconfig-network-instance:protocol/openconfig-network-instance:bgp/openconfig-network-instance:rib/openconfig-network-instance:ext-communities" {
    deviate not-supported;
  }

  deviation "/openconfig-network-instance:network-instances/openconfig-network-instance:network-instance/openconfig-network-instance:protocols/openconfig-network-instance:protocol/openconfig-network-instance:config/openconfig-network-instance:default-metric" {
    deviate not-supported;
  }

  deviation "/openconfig-network-instance:network-instances/openconfig-network-instance:network-instance/openconfig-network-instance:protocols/openconfig-network-instance:protocol/openconfig-network-instance:igmp" {
    deviate not-supported;
  }

  deviation "/openconfig-network-instance:network-instances/openconfig-network-instance:network-instance/openconfig-network-instance:protocols/openconfig-network-instance:protocol/openconfig-network-instance:isis/openconfig-network-instance:global/openconfig-network-instance:afi-safi/openconfig-network-instance:af/openconfig-network-instance:config/openconfig-network-instance:max-ecmp-paths" {
    deviate not-supported;
  }

  deviation "/openconfig-network-instance:network-instances/openconfig-network-instance:network-instance/openconfig-network-instance:protocols/openconfig-network-instance:protocol/openconfig-network-instance:isis/openconfig-network-instance:global/openconfig-network-instance:afi-safi/openconfig-network-instance:af/openconfig-network-instance:config/openconfig-network-instance:metric" {
    deviate not-supported;
  }

  deviation "/openconfig-network-instance:network-instances/openconfig-network-instance:network-instance/openconfig-network-instance:protocols/openconfig-network-instance:protocol/openconfig-network-instance:isis/openconfig-network-instance:global/openconfig-network-instance:afi-safi/openconfig-network-instance:af/openconfig-network-instance:multi-topology" {
    deviate not-supported;
  }

  deviation "/openconfig-network-instance:network-instances/openconfig-network-instance:network-instance/openconfig-network-instance:protocols/openconfig-network-instance:protocol/openconfig-network-instance:isis/openconfig-network-instance:global/openconfig-network-instance:afi-safi/openconfig-network-instance:af/openconfig-network-instance:state/openconfig-network-instance:max-ecmp-paths" {
    deviate not-supported;
  }

  deviation "/openconfig-network-instance:network-instances/openconfig-network-instance:network-instance/openconfig-network-instance:protocols/openconfig-network-instance:protocol/openconfig-network-instance:isis/openconfig-network-instance:global/openconfig-network-instance:afi-safi/openconfig-network-instance:af/openconfig-network-instance:state/openconfig-network-instance:metric" {
    deviate not-supported;
  }

  deviation "/openconfig-network-instance:network-instances/openconfig-network-instance:network-instance/openconfig-network-instance:protocols/openconfig-network-instance:protocol/openconfig-network-instance:isis/openconfig-network-instance:global/openconfig-network-instance:config/openconfig-network-instance:authentication-check" {
    deviate not-supported;
  }

  deviation "/openconfig-network-instance:network-instances/openconfig-network-instance:network-instance/openconfig-network-instance:protocols/openconfig-network-instance:protocol/openconfig-network-instance:isis/openconfig-network-instance:global/openconfig-network-instance:config/openconfig-network-instance:fast-flooding" {
    deviate not-supported;
  }

  deviation "/openconfig-network-instance:network-instances/openconfig-network-instance:network-instance/openconfig-network-instance:protocols/openconfig-network-instance:protocol/openconfig-network-instance:isis/openconfig-network-instance:global/openconfig-network-instance:config/openconfig-network-instance:instance" {
    deviate not-supported;
  }

  deviation "/openconfig-network-instance:network-instances/openconfig-network-instance:network-instance/openconfig-network-instance:protocols/openconfig-network-instance:protocol/openconfig-network-instance:isis/openconfig-network-instance:global/openconfig-network-instance:config/openconfig-network-instance:maximum-area-addresses" {
    deviate not-supported;
  }

  deviation "/openconfig-network-instance:network-instances/openconfig-network-instance:network-instance/openconfig-network-instance:protocols/openconfig-network-instance:protocol/openconfig-network-instance:isis/openconfig-network-instance:global/openconfig-network-instance:graceful-restart/openconfig-network-instance:config/openconfig-network-instance:non-planned-only" {
    deviate not-supported;
  }

  deviation "/openconfig-network-instance:network-instances/openconfig-network-instance:network-instance/openconfig-network-instance:protocols/openconfig-network-instance:protocol/openconfig-network-instance:isis/openconfig-network-instance:global/openconfig-network-instance:graceful-restart/openconfig-network-instance:config/openconfig-network-instance:restart-time" {
    deviate not-supported;
  }

  deviation "/openconfig-network-instance:network-instances/openconfig-network-instance:network-instance/openconfig-network-instance:protocols/openconfig-network-instance:protocol/openconfig-network-instance:isis/openconfig-network-instance:global/openconfig-network-instance:graceful-restart/openconfig-network-instance:state/openconfig-network-instance:non-planned-only" {
    deviate not-supported;
  }

  deviation "/openconfig-network-instance:network-instances/openconfig-network-instance:network-instance/openconfig-network-instance:protocols/openconfig-network-instance:protocol/openconfig-network-instance:isis/openconfig-network-instance:global/openconfig-network-instance:graceful-restart/openconfig-network-instance:state/openconfig-network-instance:restart-time" {
    deviate not-supported;
  }

  deviation "/openconfig-network-instance:network-instances/openconfig-network-instance:network-instance/openconfig-network-instance:protocols/openconfig-network-instance:protocol/openconfig-network-instance:isis/openconfig-network-instance:global/openconfig-network-instance:igp-shortcuts" {
    deviate not-supported;
  }

  deviation "/openconfig-network-instance:network-instances/openconfig-network-instance:network-instance/openconfig-network-instance:protocols/openconfig-network-instance:protocol/openconfig-network-instance:isis/openconfig-network-instance:global/openconfig-network-instance:inter-level-propagation-policies" {
    deviate not-supported;
  }

  deviation "/openconfig-network-instance:network-instances/openconfig-network-instance:network-instance/openconfig-network-instance:protocols/openconfig-network-instance:protocol/openconfig-network-instance:isis/openconfig-network-instance:global/openconfig-network-instance:lsp-bit/openconfig-network-instance:overload-bit/openconfig-network-instance:reset-triggers/openconfig-network-instance:reset-trigger" {
    deviate not-supported;
  }

  deviation "/openconfig-network-instance:network-instances/openconfig-network-instance:network-instance/openconfig-network-instance:protocols/openconfig-network-instance:protocol/openconfig-network-instance:isis/openconfig-network-instance:global/openconfig-network-instance:mpls" {
    deviate not-supported;
  }

  deviation "/openconfig-network-instance:network-instances/openconfig-network-instance:network-instance/openconfig-network-instance:protocols/openconfig-network-instance:protocol/openconfig-network-instance:isis/openconfig-network-instance:global/openconfig-network-instance:nsr" {
    deviate not-supported;
  }

  deviation "/openconfig-network-instance:network-instances/openconfig-network-instance:network-instance/openconfig-network-instance:protocols/openconfig-network-instance:protocol/openconfig-network-instance:isis/openconfig-network-instance:global/openconfig-network-instance:segment-routing" {
    deviate not-supported;
  }

  deviation "/openconfig-network-instance:network-instances/openconfig-network-instance:network-instance/openconfig-network-instance:protocols/openconfig-network-instance:protocol/openconfig-network-instance:isis/openconfig-network-instance:global/openconfig-network-instance:state/openconfig-network-instance:authentication-check" {
    deviate not-supported;
  }

  deviation "/openconfig-network-instance:network-instances/openconfig-network-instance:network-instance/openconfig-network-instance:protocols/openconfig-network-instance:protocol/openconfig-network-instance:isis/openconfig-network-instance:global/openconfig-network-instance:state/openconfig-network-instance:fast-flooding" {
    deviate not-supported;
  }

  deviation "/openconfig-network-instance:network-instances/openconfig-network-instance:network-instance/openconfig-network-instance:protocols/openconfig-network-instance:protocol/openconfig-network-instance:isis/openconfig-network-instance:global/openconfig-network-instance:state/openconfig-network-instance:instance" {
    deviate not-supported;
  }

  deviation "/openconfig-network-instance:network-instances/openconfig-network-instance:network-instance/openconfig-network-instance:protocols/openconfig-network-instance:protocol/openconfig-network-instance:isis/openconfig-network-instance:global/openconfig-network-instance:state/openconfig-network-instance:maximum-area-addresses" {
    deviate not-supported;
  }

  deviation "/openconfig-network-instance:network-instances/openconfig-network-instance:network-instance/openconfig-network-instance:protocols/openconfig-network-instance:protocol/openconfig-network-instance:isis/openconfig-network-instance:global/openconfig-network-instance:timers/openconfig-network-instance:lsp-generation/openconfig-network-instance:state/openconfig-network-instance:adaptive-timer" {
    deviate not-supported;
  }

  deviation "/openconfig-network-instance:network-instances/openconfig-network-instance:network-instance/openconfig-network-instance:protocols/openconfig-network-instance:protocol/openconfig-network-instance:isis/openconfig-network-instance:global/openconfig-network-instance:timers/openconfig-network-instance:spf/openconfig-network-instance:state/openconfig-network-instance:adaptive-timer" {
    deviate not-supported;
  }

  deviation "/openconfig-network-instance:network-instances/openconfig-network-instance:network-instance/openconfig-network-instance:protocols/openconfig-network-instance:protocol/openconfig-network-instance:isis/openconfig-network-instance:interfaces/openconfig-network-instance:interface/openconfig-network-instance:authentication/openconfig-network-instance:config/openconfig-network-instance:keychain" {
    deviate not-supported;
  }

  deviation "/openconfig-network-instance:network-instances/openconfig-network-instance:network-instance/openconfig-network-instance:protocols/openconfig-network-instance:protocol/openconfig-network-instance:isis/openconfig-network-instance:interfaces/openconfig-network-instance:interface/openconfig-network-instance:authentication/openconfig-network-instance:state/openconfig-network-instance:keychain" {
    deviate not-supported;
  }

  deviation "/openconfig-network-instance:network-instances/openconfig-network-instance:network-instance/openconfig-network-instance:protocols/openconfig-network-instance:protocol/openconfig-network-instance:isis/openconfig-network-instance:interfaces/openconfig-network-instance:interface/openconfig-network-instance:bfd" {
    deviate not-supported;
  }

  deviation "/openconfig-network-instance:network-instances/openconfig-network-instance:network-instance/openconfig-network-instance:protocols/openconfig-network-instance:protocol/openconfig-network-instance:isis/openconfig-network-instance:interfaces/openconfig-network-instance:interface/openconfig-network-instance:circuit-counters/openconfig-network-instance:state/openconfig-network-instance:init-fails" {
    deviate not-supported;
  }

  deviation "/openconfig-network-instance:network-instances/openconfig-network-instance:network-instance/openconfig-network-instance:protocols/openconfig-network-instance:protocol/openconfig-network-instance:isis/openconfig-network-instance:interfaces/openconfig-network-instance:interface/openconfig-network-instance:enable-bfd" {
    deviate not-supported;
  }

  deviation "/openconfig-network-instance:network-instances/openconfig-network-instance:network-instance/openconfig-network-instance:protocols/openconfig-network-instance:protocol/openconfig-network-instance:isis/openconfig-network-instance:interfaces/openconfig-network-instance:interface/openconfig-network-instance:graceful-restart" {
    deviate not-supported;
  }

  deviation "/openconfig-network-instance:network-instances/openconfig-network-instance:network-instance/openconfig-network-instance:protocols/openconfig-network-instance:protocol/openconfig-network-instance:isis/openconfig-network-instance:interfaces/openconfig-network-instance:interface/openconfig-network-instance:levels/openconfig-network-instance:level/openconfig-network-instance:adjacencies/openconfig-network-instance:adjacency/openconfig-network-instance:state/openconfig-network-instance:adjacency-type" {
    deviate not-supported;
  }

  deviation "/openconfig-network-instance:network-instances/openconfig-network-instance:network-instance/openconfig-network-instance:protocols/openconfig-network-instance:protocol/openconfig-network-instance:isis/openconfig-network-instance:interfaces/openconfig-network-instance:interface/openconfig-network-instance:levels/openconfig-network-instance:level/openconfig-network-instance:adjacencies/openconfig-network-instance:adjacency/openconfig-network-instance:state/openconfig-network-instance:multi-topology" {
    deviate not-supported;
  }

  deviation "/openconfig-network-instance:network-instances/openconfig-network-instance:network-instance/openconfig-network-instance:protocols/openconfig-network-instance:protocol/openconfig-network-instance:isis/openconfig-network-instance:interfaces/openconfig-network-instance:interface/openconfig-network-instance:levels/openconfig-network-instance:level/openconfig-network-instance:adjacencies/openconfig-network-instance:adjacency/openconfig-network-instance:state/openconfig-network-instance:restart-suppress" {
    deviate not-supported;
  }

  deviation "/openconfig-network-instance:network-instances/openconfig-network-instance:network-instance/openconfig-network-instance:protocols/openconfig-network-instance:protocol/openconfig-network-instance:isis/openconfig-network-instance:interfaces/openconfig-network-instance:interface/openconfig-network-instance:levels/openconfig-network-instance:level/openconfig-network-instance:adjacencies/openconfig-network-instance:adjacency/openconfig-network-instance:state/openconfig-network-instance:topology" {
    deviate not-supported;
  }

  deviation "/openconfig-network-instance:network-instances/openconfig-network-instance:network-instance/openconfig-network-instance:protocols/openconfig-network-instance:protocol/openconfig-network-instance:isis/openconfig-network-instance:interfaces/openconfig-network-instance:interface/openconfig-network-instance:levels/openconfig-network-instance:level/openconfig-network-instance:afi-safi/openconfig-network-instance:af/openconfig-network-instance:segment-routing" {
    deviate not-supported;
  }

  deviation "/openconfig-network-instance:network-instances/openconfig-network-instance:network-instance/openconfig-network-instance:protocols/openconfig-network-instance:protocol/openconfig-network-instance:isis/openconfig-network-instance:interfaces/openconfig-network-instance:interface/openconfig-network-instance:levels/openconfig-network-instance:level/openconfig-network-instance:hello-authentication/openconfig-network-instance:config/openconfig-network-instance:keychain" {
    deviate not-supported;
  }

  deviation "/openconfig-network-instance:network-instances/openconfig-network-instance:network-instance/openconfig-network-instance:protocols/openconfig-network-instance:protocol/openconfig-network-instance:isis/openconfig-network-instance:interfaces/openconfig-network-instance:interface/openconfig-network-instance:levels/openconfig-network-instance:level/openconfig-network-instance:hello-authentication/openconfig-network-instance:state/openconfig-network-instance:keychain" {
    deviate not-supported;
  }

  deviation "/openconfig-network-instance:network-instances/openconfig-network-instance:network-instance/openconfig-network-instance:protocols/openconfig-network-instance:protocol/openconfig-network-instance:isis/openconfig-network-instance:interfaces/openconfig-network-instance:interface/openconfig-network-instance:levels/openconfig-network-instance:level/openconfig-network-instance:packet-counters/openconfig-network-instance:csnp/openconfig-network-instance:state/openconfig-network-instance:retransmit" {
    deviate not-supported;
  }

  deviation "/openconfig-network-instance:network-instances/openconfig-network-instance:network-instance/openconfig-network-instance:protocols/openconfig-network-instance:protocol/openconfig-network-instance:isis/openconfig-network-instance:interfaces/openconfig-network-instance:interface/openconfig-network-instance:levels/openconfig-network-instance:level/openconfig-network-instance:packet-counters/openconfig-network-instance:esh" {
    deviate not-supported;
  }

  deviation "/openconfig-network-instance:network-instances/openconfig-network-instance:network-instance/openconfig-network-instance:protocols/openconfig-network-instance:protocol/openconfig-network-instance:isis/openconfig-network-instance:interfaces/openconfig-network-instance:interface/openconfig-network-instance:levels/openconfig-network-instance:level/openconfig-network-instance:packet-counters/openconfig-network-instance:iih/openconfig-network-instance:state/openconfig-network-instance:retransmit" {
    deviate not-supported;
  }

  deviation "/openconfig-network-instance:network-instances/openconfig-network-instance:network-instance/openconfig-network-instance:protocols/openconfig-network-instance:protocol/openconfig-network-instance:isis/openconfig-network-instance:interfaces/openconfig-network-instance:interface/openconfig-network-instance:levels/openconfig-network-instance:level/openconfig-network-instance:packet-counters/openconfig-network-instance:ish" {
    deviate not-supported;
  }

  deviation "/openconfig-network-instance:network-instances/openconfig-network-instance:network-instance/openconfig-network-instance:protocols/openconfig-network-instance:protocol/openconfig-network-instance:isis/openconfig-network-instance:interfaces/openconfig-network-instance:interface/openconfig-network-instance:levels/openconfig-network-instance:level/openconfig-network-instance:packet-counters/openconfig-network-instance:lsp/openconfig-network-instance:state/openconfig-network-instance:retransmit" {
    deviate not-supported;
  }

  deviation "/openconfig-network-instance:network-instances/openconfig-network-instance:network-instance/openconfig-network-instance:protocols/openconfig-network-instance:protocol/openconfig-network-instance:isis/openconfig-network-instance:interfaces/openconfig-network-instance:interface/openconfig-network-instance:levels/openconfig-network-instance:level/openconfig-network-instance:packet-counters/openconfig-network-instance:psnp/openconfig-network-instance:state/openconfig-network-instance:retransmit" {
    deviate not-supported;
  }

  deviation "/openconfig-network-instance:network-instances/openconfig-network-instance:network-instance/openconfig-network-instance:protocols/openconfig-network-instance:protocol/openconfig-network-instance:isis/openconfig-network-instance:interfaces/openconfig-network-instance:interface/openconfig-network-instance:mpls" {
    deviate not-supported;
  }

  deviation "/openconfig-network-instance:network-instances/openconfig-network-instance:network-instance/openconfig-network-instance:protocols/openconfig-network-instance:protocol/openconfig-network-instance:isis/openconfig-network-instance:levels/openconfig-network-instance:level/openconfig-network-instance:authentication/openconfig-network-instance:config/openconfig-network-instance:keychain" {
    deviate not-supported;
  }

  deviation "/openconfig-network-instance:network-instances/openconfig-network-instance:network-instance/openconfig-network-instance:protocols/openconfig-network-instance:protocol/openconfig-network-instance:isis/openconfig-network-instance:levels/openconfig-network-instance:level/openconfig-network-instance:authentication/openconfig-network-instance:state/openconfig-network-instance:keychain" {
    deviate not-supported;
  }

  deviation "/openconfig-network-instance:network-instances/openconfig-network-instance:network-instance/openconfig-network-instance:protocols/openconfig-network-instance:protocol/openconfig-network-instance:isis/openconfig-network-instance:levels/openconfig-network-instance:level/openconfig-network-instance:config/openconfig-network-instance:authentication-check" {
    deviate not-supported;
  }

  deviation "/openconfig-network-instance:network-instances/openconfig-network-instance:network-instance/openconfig-network-instance:protocols/openconfig-network-instance:protocol/openconfig-network-instance:isis/openconfig-network-instance:levels/openconfig-network-instance:level/openconfig-network-instance:config/openconfig-network-instance:enabled" {
    deviate not-supported;
  }

  deviation "/openconfig-network-instance:network-instances/openconfig-network-instance:network-instance/openconfig-network-instance:protocols/openconfig-network-instance:protocol/openconfig-network-instance:isis/openconfig-network-instance:levels/openconfig-network-instance:level/openconfig-network-instance:graceful-restart" {
    deviate not-supported;
  }

  deviation "/openconfig-network-instance:network-instances/openconfig-network-instance:network-instance/openconfig-network-instance:protocols/openconfig-network-instance:protocol/openconfig-network-instance:isis/openconfig-network-instance:levels/openconfig-network-instance:level/openconfig-network-instance:link-state-database/openconfig-network-instance:lsp/openconfig-network-instance:state/openconfig-network-instance:is-type" {
    deviate not-supported;
  }

  deviation "/openconfig-network-instance:network-instances/openconfig-network-instance:network-instance/openconfig-network-instance:protocols/openconfig-network-instance:protocol/openconfig-network-instance:isis/openconfig-network-instance:levels/openconfig-network-instance:level/openconfig-network-instance:link-state-database/openconfig-network-instance:lsp/openconfig-network-instance:tlvs/openconfig-network-instance:tlv/openconfig-network-instance:extended-is-reachability/openconfig-network-instance:neighbors/openconfig-network-instance:neighbor/openconfig-network-instance:instances/openconfig-network-instance:instance/openconfig-network-instance:subtlvs/openconfig-network-instance:subtlv/openconfig-network-instance:link-protection-type" {
    deviate not-supported;
  }

  deviation "/openconfig-network-instance:network-instances/openconfig-network-instance:network-instance/openconfig-network-instance:protocols/openconfig-network-instance:protocol/openconfig-network-instance:isis/openconfig-network-instance:levels/openconfig-network-instance:level/openconfig-network-instance:link-state-database/openconfig-network-instance:lsp/openconfig-network-instance:tlvs/openconfig-network-instance:tlv/openconfig-network-instance:is-alias-id" {
    deviate not-supported;
  }

  deviation "/openconfig-network-instance:network-instances/openconfig-network-instance:network-instance/openconfig-network-instance:protocols/openconfig-network-instance:protocol/openconfig-network-instance:isis/openconfig-network-instance:levels/openconfig-network-instance:level/openconfig-network-instance:link-state-database/openconfig-network-instance:lsp/openconfig-network-instance:tlvs/openconfig-network-instance:tlv/openconfig-network-instance:isis-neighbor-attribute" {
    deviate not-supported;
  }

  deviation "/openconfig-network-instance:network-instances/openconfig-network-instance:network-instance/openconfig-network-instance:protocols/openconfig-network-instance:protocol/openconfig-network-instance:isis/openconfig-network-instance:levels/openconfig-network-instance:level/openconfig-network-instance:link-state-database/openconfig-network-instance:lsp/openconfig-network-instance:tlvs/openconfig-network-instance:tlv/openconfig-network-instance:lsp-buffer-size" {
    deviate not-supported;
  }

  deviation "/openconfig-network-instance:network-instances/openconfig-network-instance:network-instance/openconfig-network-instance:protocols/openconfig-network-instance:protocol/openconfig-network-instance:isis/openconfig-network-instance:levels/openconfig-network-instance:level/openconfig-network-instance:link-state-database/openconfig-network-instance:lsp/openconfig-network-instance:tlvs/openconfig-network-instance:tlv/openconfig-network-instance:mt-isis-neighbor-attribute" {
    deviate not-supported;
  }

  deviation "/openconfig-network-instance:network-instances/openconfig-network-instance:network-instance/openconfig-network-instance:protocols/openconfig-network-instance:protocol/openconfig-network-instance:isis/openconfig-network-instance:levels/openconfig-network-instance:level/openconfig-network-instance:link-state-database/openconfig-network-instance:lsp/openconfig-network-instance:tlvs/openconfig-network-instance:tlv/openconfig-network-instance:mt-isn/openconfig-network-instance:neighbors/openconfig-network-instance:neighbor/openconfig-network-instance:instances/openconfig-network-instance:instance/openconfig-network-instance:subtlvs/openconfig-network-instance:subtlv/openconfig-network-instance:link-attributes/openconfig-network-instance:state/openconfig-network-instance:local-protection" {
    deviate not-supported;
  }

  deviation "/openconfig-network-instance:network-instances/openconfig-network-instance:network-instance/openconfig-network-instance:protocols/openconfig-network-instance:protocol/openconfig-network-instance:isis/openconfig-network-instance:levels/openconfig-network-instance:level/openconfig-network-instance:link-state-database/openconfig-network-instance:lsp/openconfig-network-instance:tlvs/openconfig-network-instance:tlv/openconfig-network-instance:mt-isn/openconfig-network-instance:neighbors/openconfig-network-instance:neighbor/openconfig-network-instance:instances/openconfig-network-instance:instance/openconfig-network-instance:subtlvs/openconfig-network-instance:subtlv/openconfig-network-instance:link-protection-type" {
    deviate not-supported;
  }

  deviation "/openconfig-network-instance:network-instances/openconfig-network-instance:network-instance/openconfig-network-instance:protocols/openconfig-network-instance:protocol/openconfig-network-instance:isis/openconfig-network-instance:levels/openconfig-network-instance:level/openconfig-network-instance:link-state-database/openconfig-network-instance:lsp/openconfig-network-instance:tlvs/openconfig-network-instance:tlv/openconfig-network-instance:router-capabilities/openconfig-network-instance:capability/openconfig-network-instance:undefined-subtlvs" {
    deviate not-supported;
  }

  deviation "/openconfig-network-instance:network-instances/openconfig-network-instance:network-instance/openconfig-network-instance:protocols/openconfig-network-instance:protocol/openconfig-network-instance:isis/openconfig-network-instance:levels/openconfig-network-instance:level/openconfig-network-instance:link-state-database/openconfig-network-instance:lsp/openconfig-network-instance:undefined-tlvs" {
    deviate not-supported;
  }

  deviation "/openconfig-network-instance:network-instances/openconfig-network-instance:network-instance/openconfig-network-instance:protocols/openconfig-network-instance:protocol/openconfig-network-instance:isis/openconfig-network-instance:levels/openconfig-network-instance:level/openconfig-network-instance:state/openconfig-network-instance:authentication-check" {
    deviate not-supported;
  }

  deviation "/openconfig-network-instance:network-instances/openconfig-network-instance:network-instance/openconfig-network-instance:protocols/openconfig-network-instance:protocol/openconfig-network-instance:isis/openconfig-network-instance:levels/openconfig-network-instance:level/openconfig-network-instance:state/openconfig-network-instance:enabled" {
    deviate not-supported;
  }

  deviation "/openconfig-network-instance:network-instances/openconfig-network-instance:network-instance/openconfig-network-instance:protocols/openconfig-network-instance:protocol/openconfig-network-instance:isis/openconfig-network-instance:levels/openconfig-network-instance:level/openconfig-network-instance:system-level-counters/openconfig-network-instance:state/openconfig-network-instance:part-changes" {
    deviate not-supported;
  }

  deviation "/openconfig-network-instance:network-instances/openconfig-network-instance:network-instance/openconfig-network-instance:protocols/openconfig-network-instance:protocol/openconfig-network-instance:isis/openconfig-network-instance:levels/openconfig-network-instance:level/openconfig-network-instance:traffic-engineering" {
    deviate not-supported;
  }

  deviation "/openconfig-network-instance:network-instances/openconfig-network-instance:network-instance/openconfig-network-instance:protocols/openconfig-network-instance:protocol/openconfig-network-instance:local-aggregates/openconfig-network-instance:aggregate/openconfig-network-instance:config/openconfig-network-instance:description" {
    deviate not-supported;
  }

  deviation "/openconfig-network-instance:network-instances/openconfig-network-instance:network-instance/openconfig-network-instance:protocols/openconfig-network-instance:protocol/openconfig-network-instance:local-aggregates/openconfig-network-instance:aggregate/openconfig-network-instance:config/openconfig-network-instance:discard" {
    deviate not-supported;
  }

  deviation "/openconfig-network-instance:network-instances/openconfig-network-instance:network-instance/openconfig-network-instance:protocols/openconfig-network-instance:protocol/openconfig-network-instance:local-aggregates/openconfig-network-instance:aggregate/openconfig-network-instance:config/openconfig-network-instance:metric" {
    deviate not-supported;
  }

  deviation "/openconfig-network-instance:network-instances/openconfig-network-instance:network-instance/openconfig-network-instance:protocols/openconfig-network-instance:protocol/openconfig-network-instance:local-aggregates/openconfig-network-instance:aggregate/openconfig-network-instance:config/openconfig-network-instance:preference" {
    deviate not-supported;
  }

  deviation "/openconfig-network-instance:network-instances/openconfig-network-instance:network-instance/openconfig-network-instance:protocols/openconfig-network-instance:protocol/openconfig-network-instance:local-aggregates/openconfig-network-instance:aggregate/openconfig-network-instance:config/openconfig-network-instance:set-tag" {
    deviate not-supported;
  }

  deviation "/openconfig-network-instance:network-instances/openconfig-network-instance:network-instance/openconfig-network-instance:protocols/openconfig-network-instance:protocol/openconfig-network-instance:local-aggregates/openconfig-network-instance:aggregate/openconfig-network-instance:state/openconfig-network-instance:description" {
    deviate not-supported;
  }

  deviation "/openconfig-network-instance:network-instances/openconfig-network-instance:network-instance/openconfig-network-instance:protocols/openconfig-network-instance:protocol/openconfig-network-instance:local-aggregates/openconfig-network-instance:aggregate/openconfig-network-instance:state/openconfig-network-instance:discard" {
    deviate not-supported;
  }

  deviation "/openconfig-network-instance:network-instances/openconfig-network-instance:network-instance/openconfig-network-instance:protocols/openconfig-network-instance:protocol/openconfig-network-instance:local-aggregates/openconfig-network-instance:aggregate/openconfig-network-instance:state/openconfig-network-instance:metric" {
    deviate not-supported;
  }

  deviation "/openconfig-network-instance:network-instances/openconfig-network-instance:network-instance/openconfig-network-instance:protocols/openconfig-network-instance:protocol/openconfig-network-instance:local-aggregates/openconfig-network-instance:aggregate/openconfig-network-instance:state/openconfig-network-instance:preference" {
    deviate not-supported;
  }

  deviation "/openconfig-network-instance:network-instances/openconfig-network-instance:network-instance/openconfig-network-instance:protocols/openconfig-network-instance:protocol/openconfig-network-instance:local-aggregates/openconfig-network-instance:aggregate/openconfig-network-instance:state/openconfig-network-instance:set-tag" {
    deviate not-supported;
  }

  deviation "/openconfig-network-instance:network-instances/openconfig-network-instance:network-instance/openconfig-network-instance:protocols/openconfig-network-instance:protocol/openconfig-network-instance:ospfv2" {
    deviate not-supported;
  }

  deviation "/openconfig-network-instance:network-instances/openconfig-network-instance:network-instance/openconfig-network-instance:protocols/openconfig-network-instance:protocol/openconfig-network-instance:ospfv3" {
    deviate not-supported;
  }

  deviation "/openconfig-network-instance:network-instances/openconfig-network-instance:network-instance/openconfig-network-instance:protocols/openconfig-network-instance:protocol/openconfig-network-instance:pcep" {
    deviate not-supported;
  }

  deviation "/openconfig-network-instance:network-instances/openconfig-network-instance:network-instance/openconfig-network-instance:protocols/openconfig-network-instance:protocol/openconfig-network-instance:pim" {
    deviate not-supported;
  }

  deviation "/openconfig-network-instance:network-instances/openconfig-network-instance:network-instance/openconfig-network-instance:protocols/openconfig-network-instance:protocol/openconfig-network-instance:state/openconfig-network-instance:default-metric" {
    deviate not-supported;
  }

  deviation "/openconfig-network-instance:network-instances/openconfig-network-instance:network-instance/openconfig-network-instance:protocols/openconfig-network-instance:protocol/openconfig-network-instance:static-routes/openconfig-network-instance:static/openconfig-network-instance:config/openconfig-network-instance:description" {
    deviate not-supported;
  }

  deviation "/openconfig-network-instance:network-instances/openconfig-network-instance:network-instance/openconfig-network-instance:protocols/openconfig-network-instance:protocol/openconfig-network-instance:static-routes/openconfig-network-instance:static/openconfig-network-instance:next-hops/openconfig-network-instance:next-hop/openconfig-network-instance:config/openconfig-local-routing-network-instance:next-network-instance" {
    deviate not-supported;
  }

  deviation "/openconfig-network-instance:network-instances/openconfig-network-instance:network-instance/openconfig-network-instance:protocols/openconfig-network-instance:protocol/openconfig-network-instance:static-routes/openconfig-network-instance:static/openconfig-network-instance:next-hops/openconfig-network-instance:next-hop/openconfig-network-instance:config/openconfig-local-routing-network-instance:nh-network-instance" {
    deviate not-supported;
  }

  deviation "/openconfig-network-instance:network-instances/openconfig-network-instance:network-instance/openconfig-network-instance:protocols/openconfig-network-instance:protocol/openconfig-network-instance:static-routes/openconfig-network-instance:static/openconfig-network-instance:next-hops/openconfig-network-instance:next-hop/openconfig-network-instance:enable-bfd" {
    deviate not-supported;
  }

  deviation "/openconfig-network-instance:network-instances/openconfig-network-instance:network-instance/openconfig-network-instance:protocols/openconfig-network-instance:protocol/openconfig-network-instance:static-routes/openconfig-network-instance:static/openconfig-network-instance:next-hops/openconfig-network-instance:next-hop/openconfig-network-instance:interface-ref" {
    deviate not-supported;
  }

  deviation "/openconfig-network-instance:network-instances/openconfig-network-instance:network-instance/openconfig-network-instance:protocols/openconfig-network-instance:protocol/openconfig-network-instance:static-routes/openconfig-network-instance:static/openconfig-network-instance:next-hops/openconfig-network-instance:next-hop/openconfig-network-instance:state/openconfig-local-routing-network-instance:next-network-instance" {
    deviate not-supported;
  }

  deviation "/openconfig-network-instance:network-instances/openconfig-network-instance:network-instance/openconfig-network-instance:protocols/openconfig-network-instance:protocol/openconfig-network-instance:static-routes/openconfig-network-instance:static/openconfig-network-instance:next-hops/openconfig-network-instance:next-hop/openconfig-network-instance:state/openconfig-local-routing-network-instance:nh-network-instance" {
    deviate not-supported;
  }

  deviation "/openconfig-network-instance:network-instances/openconfig-network-instance:network-instance/openconfig-network-instance:protocols/openconfig-network-instance:protocol/openconfig-network-instance:static-routes/openconfig-network-instance:static/openconfig-network-instance:state/openconfig-network-instance:description" {
    deviate not-supported;
  }

  deviation "/openconfig-network-instance:network-instances/openconfig-network-instance:network-instance/openconfig-network-instance:route-limits" {
    deviate not-supported;
  }

  deviation "/openconfig-network-instance:network-instances/openconfig-network-instance:network-instance/openconfig-network-instance:segment-routing" {
    deviate not-supported;
  }

  deviation "/openconfig-network-instance:network-instances/openconfig-network-instance:network-instance/openconfig-network-instance:state/openconfig-network-instance:fallback-network-instance" {
    deviate not-supported;
  }

  deviation "/openconfig-network-instance:network-instances/openconfig-network-instance:network-instance/openconfig-network-instance:state/openconfig-network-instance:route-distinguisher" {
    deviate not-supported;
  }

  deviation "/openconfig-network-instance:network-instances/openconfig-network-instance:network-instance/openconfig-network-instance:static/openconfig-network-instance:next-hops/openconfig-network-instance:next-hop/openconfig-network-instance:config/openconfig-local-routing-network-instance:next-network-instance" {
    deviate not-supported;
  }

  deviation "/openconfig-network-instance:network-instances/openconfig-network-instance:network-instance/openconfig-network-instance:static/openconfig-network-instance:next-hops/openconfig-network-instance:next-hop/openconfig-network-instance:config/openconfig-local-routing-network-instance:nh-network-instance" {
    deviate not-supported;
  }

  deviation "/openconfig-network-instance:network-instances/openconfig-network-instance:network-instance/openconfig-network-instance:static/openconfig-network-instance:next-hops/openconfig-network-instance:next-hop/openconfig-network-instance:config/openconfig-network-instance:metric" {
    deviate not-supported;
  }

  deviation "/openconfig-network-instance:network-instances/openconfig-network-instance:network-instance/openconfig-network-instance:static/openconfig-network-instance:next-hops/openconfig-network-instance:next-hop/openconfig-network-instance:config/openconfig-network-instance:preference" {
    deviate not-supported;
  }

  deviation "/openconfig-network-instance:network-instances/openconfig-network-instance:network-instance/openconfig-network-instance:static/openconfig-network-instance:next-hops/openconfig-network-instance:next-hop/openconfig-network-instance:encap-headers/openconfig-network-instance:encap-header/openconfig-network-instance:udp-v4/openconfig-network-instance:config/openconfig-network-instance:dscp" {
    deviate not-supported;
  }

  deviation "/openconfig-network-instance:network-instances/openconfig-network-instance:network-instance/openconfig-network-instance:static/openconfig-network-instance:next-hops/openconfig-network-instance:next-hop/openconfig-network-instance:encap-headers/openconfig-network-instance:encap-header/openconfig-network-instance:udp-v4/openconfig-network-instance:config/openconfig-network-instance:src-udp-port" {
    deviate not-supported;
  }

  deviation "/openconfig-network-instance:network-instances/openconfig-network-instance:network-instance/openconfig-network-instance:static/openconfig-network-instance:next-hops/openconfig-network-instance:next-hop/openconfig-network-instance:encap-headers/openconfig-network-instance:encap-header/openconfig-network-instance:udp-v4/openconfig-network-instance:state/openconfig-network-instance:dscp" {
    deviate not-supported;
  }

  deviation "/openconfig-network-instance:network-instances/openconfig-network-instance:network-instance/openconfig-network-instance:static/openconfig-network-instance:next-hops/openconfig-network-instance:next-hop/openconfig-network-instance:encap-headers/openconfig-network-instance:encap-header/openconfig-network-instance:udp-v4/openconfig-network-instance:state/openconfig-network-instance:src-udp-port" {
    deviate not-supported;
  }

  deviation "/openconfig-network-instance:network-instances/openconfig-network-instance:network-instance/openconfig-network-instance:static/openconfig-network-instance:next-hops/openconfig-network-instance:next-hop/openconfig-network-instance:state/openconfig-local-routing-network-instance:next-network-instance" {
    deviate not-supported;
  }

  deviation "/openconfig-network-instance:network-instances/openconfig-network-instance:network-instance/openconfig-network-instance:static/openconfig-network-instance:next-hops/openconfig-network-instance:next-hop/openconfig-network-instance:state/openconfig-local-routing-network-instance:nh-network-instance" {
    deviate not-supported;
  }

  deviation "/openconfig-network-instance:network-instances/openconfig-network-instance:network-instance/openconfig-network-instance:static/openconfig-network-instance:next-hops/openconfig-network-instance:next-hop/openconfig-network-instance:state/openconfig-network-instance:metric" {
    deviate not-supported;
  }

  deviation "/openconfig-network-instance:network-instances/openconfig-network-instance:network-instance/openconfig-network-instance:static/openconfig-network-instance:next-hops/openconfig-network-instance:next-hop/openconfig-network-instance:state/openconfig-network-instance:preference" {
    deviate not-supported;
  }

  deviation "/openconfig-network-instance:network-instances/openconfig-network-instance:network-instance/openconfig-network-instance:tables" {
    deviate not-supported;
  }

  deviation "/openconfig-network-instance:network-instances/openconfig-network-instance:network-instance/openconfig-network-instance:vlans" {
    deviate not-supported;
  }

  deviation "/openconfig-platform:components/openconfig-platform:component/openconfig-platform-linecard:linecard/openconfig-platform-linecard:utilization" {
    deviate not-supported;
  }

  deviation "/openconfig-platform:components/openconfig-platform:component/openconfig-platform-transceiver:transceiver/openconfig-platform-transceiver:config/openconfig-platform-transceiver:enabled" {
    deviate not-supported;
  }

  deviation "/openconfig-platform:components/openconfig-platform:component/openconfig-platform-transceiver:transceiver/openconfig-platform-transceiver:config/openconfig-platform-transceiver:ethernet-pmd-preconf" {
    deviate not-supported;
  }

  deviation "/openconfig-platform:components/openconfig-platform:component/openconfig-platform-transceiver:transceiver/openconfig-platform-transceiver:config/openconfig-platform-transceiver:fec-mode" {
    deviate not-supported;
  }

  deviation "/openconfig-platform:components/openconfig-platform:component/openconfig-platform-transceiver:transceiver/openconfig-platform-transceiver:config/openconfig-platform-transceiver:form-factor-preconf" {
    deviate not-supported;
  }

  deviation "/openconfig-platform:components/openconfig-platform:component/openconfig-platform-transceiver:transceiver/openconfig-platform-transceiver:host-lanes" {
    deviate not-supported;
  }

  deviation "/openconfig-platform:components/openconfig-platform:component/openconfig-platform-transceiver:transceiver/openconfig-platform-transceiver:physical-channels/openconfig-platform-transceiver:channel/openconfig-platform-transceiver:config/openconfig-platform-transceiver:associated-optical-channel" {
    deviate not-supported;
  }

  deviation "/openconfig-platform:components/openconfig-platform:component/openconfig-platform-transceiver:transceiver/openconfig-platform-transceiver:physical-channels/openconfig-platform-transceiver:channel/openconfig-platform-transceiver:config/openconfig-platform-transceiver:description" {
    deviate not-supported;
  }

  deviation "/openconfig-platform:components/openconfig-platform:component/openconfig-platform-transceiver:transceiver/openconfig-platform-transceiver:physical-channels/openconfig-platform-transceiver:channel/openconfig-platform-transceiver:config/openconfig-platform-transceiver:target-output-power" {
    deviate not-supported;
  }

  deviation "/openconfig-platform:components/openconfig-platform:component/openconfig-platform-transceiver:transceiver/openconfig-platform-transceiver:physical-channels/openconfig-platform-transceiver:channel/openconfig-platform-transceiver:config/openconfig-platform-transceiver:tx-laser" {
    deviate not-supported;
  }

  deviation "/openconfig-platform:components/openconfig-platform:component/openconfig-platform-transceiver:transceiver/openconfig-platform-transceiver:physical-channels/openconfig-platform-transceiver:channel/openconfig-platform-transceiver:state/openconfig-platform-transceiver:description" {
    deviate not-supported;
  }

  deviation "/openconfig-platform:components/openconfig-platform:component/openconfig-platform-transceiver:transceiver/openconfig-platform-transceiver:physical-channels/openconfig-platform-transceiver:channel/openconfig-platform-transceiver:state/openconfig-platform-transceiver:input-power/openconfig-platform-transceiver:interval" {
    deviate not-supported;
  }

  deviation "/openconfig-platform:components/openconfig-platform:component/openconfig-platform-transceiver:transceiver/openconfig-platform-transceiver:physical-channels/openconfig-platform-transceiver:channel/openconfig-platform-transceiver:state/openconfig-platform-transceiver:input-power/openconfig-platform-transceiver:max-time" {
    deviate not-supported;
  }

  deviation "/openconfig-platform:components/openconfig-platform:component/openconfig-platform-transceiver:transceiver/openconfig-platform-transceiver:physical-channels/openconfig-platform-transceiver:channel/openconfig-platform-transceiver:state/openconfig-platform-transceiver:input-power/openconfig-platform-transceiver:min-time" {
    deviate not-supported;
  }

  deviation "/openconfig-platform:components/openconfig-platform:component/openconfig-platform-transceiver:transceiver/openconfig-platform-transceiver:physical-channels/openconfig-platform-transceiver:channel/openconfig-platform-transceiver:state/openconfig-platform-transceiver:laser-age" {
    deviate not-supported;
  }

  deviation "/openconfig-platform:components/openconfig-platform:component/openconfig-platform-transceiver:transceiver/openconfig-platform-transceiver:physical-channels/openconfig-platform-transceiver:channel/openconfig-platform-transceiver:state/openconfig-platform-transceiver:laser-bias-current/openconfig-platform-transceiver:avg" {
    deviate not-supported;
  }

  deviation "/openconfig-platform:components/openconfig-platform:component/openconfig-platform-transceiver:transceiver/openconfig-platform-transceiver:physical-channels/openconfig-platform-transceiver:channel/openconfig-platform-transceiver:state/openconfig-platform-transceiver:laser-bias-current/openconfig-platform-transceiver:interval" {
    deviate not-supported;
  }

  deviation "/openconfig-platform:components/openconfig-platform:component/openconfig-platform-transceiver:transceiver/openconfig-platform-transceiver:physical-channels/openconfig-platform-transceiver:channel/openconfig-platform-transceiver:state/openconfig-platform-transceiver:laser-bias-current/openconfig-platform-transceiver:max" {
    deviate not-supported;
  }

  deviation "/openconfig-platform:components/openconfig-platform:component/openconfig-platform-transceiver:transceiver/openconfig-platform-transceiver:physical-channels/openconfig-platform-transceiver:channel/openconfig-platform-transceiver:state/openconfig-platform-transceiver:laser-bias-current/openconfig-platform-transceiver:max-time" {
    deviate not-supported;
  }

  deviation "/openconfig-platform:components/openconfig-platform:component/openconfig-platform-transceiver:transceiver/openconfig-platform-transceiver:physical-channels/openconfig-platform-transceiver:channel/openconfig-platform-transceiver:state/openconfig-platform-transceiver:laser-bias-current/openconfig-platform-transceiver:min" {
    deviate not-supported;
  }

  deviation "/openconfig-platform:components/openconfig-platform:component/openconfig-platform-transceiver:transceiver/openconfig-platform-transceiver:physical-channels/openconfig-platform-transceiver:channel/openconfig-platform-transceiver:state/openconfig-platform-transceiver:laser-bias-current/openconfig-platform-transceiver:min-time" {
    deviate not-supported;
  }

  deviation "/openconfig-platform:components/openconfig-platform:component/openconfig-platform-transceiver:transceiver/openconfig-platform-transceiver:physical-channels/openconfig-platform-transceiver:channel/openconfig-platform-transceiver:state/openconfig-platform-transceiver:laser-temperature" {
    deviate not-supported;
  }

  deviation "/openconfig-platform:components/openconfig-platform:component/openconfig-platform-transceiver:transceiver/openconfig-platform-transceiver:physical-channels/openconfig-platform-transceiver:channel/openconfig-platform-transceiver:state/openconfig-platform-transceiver:output-frequency" {
    deviate not-supported;
  }

  deviation "/openconfig-platform:components/openconfig-platform:component/openconfig-platform-transceiver:transceiver/openconfig-platform-transceiver:physical-channels/openconfig-platform-transceiver:channel/openconfig-platform-transceiver:state/openconfig-platform-transceiver:output-power/openconfig-platform-transceiver:avg" {
    deviate not-supported;
  }

  deviation "/openconfig-platform:components/openconfig-platform:component/openconfig-platform-transceiver:transceiver/openconfig-platform-transceiver:physical-channels/openconfig-platform-transceiver:channel/openconfig-platform-transceiver:state/openconfig-platform-transceiver:output-power/openconfig-platform-transceiver:interval" {
    deviate not-supported;
  }

  deviation "/openconfig-platform:components/openconfig-platform:component/openconfig-platform-transceiver:transceiver/openconfig-platform-transceiver:physical-channels/openconfig-platform-transceiver:channel/openconfig-platform-transceiver:state/openconfig-platform-transceiver:output-power/openconfig-platform-transceiver:max" {
    deviate not-supported;
  }

  deviation "/openconfig-platform:components/openconfig-platform:component/openconfig-platform-transceiver:transceiver/openconfig-platform-transceiver:physical-channels/openconfig-platform-transceiver:channel/openconfig-platform-transceiver:state/openconfig-platform-transceiver:output-power/openconfig-platform-transceiver:max-time" {
    deviate not-supported;
  }

  deviation "/openconfig-platform:components/openconfig-platform:component/openconfig-platform-transceiver:transceiver/openconfig-platform-transceiver:physical-channels/openconfig-platform-transceiver:channel/openconfig-platform-transceiver:state/openconfig-platform-transceiver:output-power/openconfig-platform-transceiver:min" {
    deviate not-supported;
  }

  deviation "/openconfig-platform:components/openconfig-platform:component/openconfig-platform-transceiver:transceiver/openconfig-platform-transceiver:physical-channels/openconfig-platform-transceiver:channel/openconfig-platform-transceiver:state/openconfig-platform-transceiver:output-power/openconfig-platform-transceiver:min-time" {
    deviate not-supported;
  }

  deviation "/openconfig-platform:components/openconfig-platform:component/openconfig-platform-transceiver:transceiver/openconfig-platform-transceiver:physical-channels/openconfig-platform-transceiver:channel/openconfig-platform-transceiver:state/openconfig-platform-transceiver:rx-cdr-lol" {
    deviate not-supported;
  }

  deviation "/openconfig-platform:components/openconfig-platform:component/openconfig-platform-transceiver:transceiver/openconfig-platform-transceiver:physical-channels/openconfig-platform-transceiver:channel/openconfig-platform-transceiver:state/openconfig-platform-transceiver:rx-los" {
    deviate not-supported;
  }

  deviation "/openconfig-platform:components/openconfig-platform:component/openconfig-platform-transceiver:transceiver/openconfig-platform-transceiver:physical-channels/openconfig-platform-transceiver:channel/openconfig-platform-transceiver:state/openconfig-platform-transceiver:target-frequency-deviation" {
    deviate not-supported;
  }

  deviation "/openconfig-platform:components/openconfig-platform:component/openconfig-platform-transceiver:transceiver/openconfig-platform-transceiver:physical-channels/openconfig-platform-transceiver:channel/openconfig-platform-transceiver:state/openconfig-platform-transceiver:target-output-power" {
    deviate not-supported;
  }

  deviation "/openconfig-platform:components/openconfig-platform:component/openconfig-platform-transceiver:transceiver/openconfig-platform-transceiver:physical-channels/openconfig-platform-transceiver:channel/openconfig-platform-transceiver:state/openconfig-platform-transceiver:tec-current" {
    deviate not-supported;
  }

  deviation "/openconfig-platform:components/openconfig-platform:component/openconfig-platform-transceiver:transceiver/openconfig-platform-transceiver:physical-channels/openconfig-platform-transceiver:channel/openconfig-platform-transceiver:state/openconfig-platform-transceiver:tx-failure" {
    deviate not-supported;
  }

  deviation "/openconfig-platform:components/openconfig-platform:component/openconfig-platform-transceiver:transceiver/openconfig-platform-transceiver:physical-channels/openconfig-platform-transceiver:channel/openconfig-platform-transceiver:state/openconfig-platform-transceiver:tx-laser" {
    deviate not-supported;
  }

  deviation "/openconfig-platform:components/openconfig-platform:component/openconfig-platform-transceiver:transceiver/openconfig-platform-transceiver:state/openconfig-platform-transceiver:connector-type" {
    deviate not-supported;
  }

  deviation "/openconfig-platform:components/openconfig-platform:component/openconfig-platform-transceiver:transceiver/openconfig-platform-transceiver:state/openconfig-platform-transceiver:date-code" {
    deviate not-supported;
  }

  deviation "/openconfig-platform:components/openconfig-platform:component/openconfig-platform-transceiver:transceiver/openconfig-platform-transceiver:state/openconfig-platform-transceiver:enabled" {
    deviate not-supported;
  }

  deviation "/openconfig-platform:components/openconfig-platform:component/openconfig-platform-transceiver:transceiver/openconfig-platform-transceiver:state/openconfig-platform-transceiver:ethernet-pmd" {
    deviate not-supported;
  }

  deviation "/openconfig-platform:components/openconfig-platform:component/openconfig-platform-transceiver:transceiver/openconfig-platform-transceiver:state/openconfig-platform-transceiver:ethernet-pmd-preconf" {
    deviate not-supported;
  }

  deviation "/openconfig-platform:components/openconfig-platform:component/openconfig-platform-transceiver:transceiver/openconfig-platform-transceiver:state/openconfig-platform-transceiver:fault-condition" {
    deviate not-supported;
  }

  deviation "/openconfig-platform:components/openconfig-platform:component/openconfig-platform-transceiver:transceiver/openconfig-platform-transceiver:state/openconfig-platform-transceiver:fec-corrected-bits" {
    deviate not-supported;
  }

  deviation "/openconfig-platform:components/openconfig-platform:component/openconfig-platform-transceiver:transceiver/openconfig-platform-transceiver:state/openconfig-platform-transceiver:fec-corrected-bytes" {
    deviate not-supported;
  }

  deviation "/openconfig-platform:components/openconfig-platform:component/openconfig-platform-transceiver:transceiver/openconfig-platform-transceiver:state/openconfig-platform-transceiver:fec-mode" {
    deviate not-supported;
  }

  deviation "/openconfig-platform:components/openconfig-platform:component/openconfig-platform-transceiver:transceiver/openconfig-platform-transceiver:state/openconfig-platform-transceiver:fec-status" {
    deviate not-supported;
  }

  deviation "/openconfig-platform:components/openconfig-platform:component/openconfig-platform-transceiver:transceiver/openconfig-platform-transceiver:state/openconfig-platform-transceiver:fec-uncorrectable-blocks" {
    deviate not-supported;
  }

  deviation "/openconfig-platform:components/openconfig-platform:component/openconfig-platform-transceiver:transceiver/openconfig-platform-transceiver:state/openconfig-platform-transceiver:fec-uncorrectable-words" {
    deviate not-supported;
  }

  deviation "/openconfig-platform:components/openconfig-platform:component/openconfig-platform-transceiver:transceiver/openconfig-platform-transceiver:state/openconfig-platform-transceiver:form-factor-preconf" {
    deviate not-supported;
  }

  deviation "/openconfig-platform:components/openconfig-platform:component/openconfig-platform-transceiver:transceiver/openconfig-platform-transceiver:state/openconfig-platform-transceiver:input-power" {
    deviate not-supported;
  }

  deviation "/openconfig-platform:components/openconfig-platform:component/openconfig-platform-transceiver:transceiver/openconfig-platform-transceiver:state/openconfig-platform-transceiver:laser-bias-current" {
    deviate not-supported;
  }

  deviation "/openconfig-platform:components/openconfig-platform:component/openconfig-platform-transceiver:transceiver/openconfig-platform-transceiver:state/openconfig-platform-transceiver:otn-compliance-code" {
    deviate not-supported;
  }

  deviation "/openconfig-platform:components/openconfig-platform:component/openconfig-platform-transceiver:transceiver/openconfig-platform-transceiver:state/openconfig-platform-transceiver:output-power" {
    deviate not-supported;
  }

  deviation "/openconfig-platform:components/openconfig-platform:component/openconfig-platform-transceiver:transceiver/openconfig-platform-transceiver:state/openconfig-platform-transceiver:post-fec-ber" {
    deviate not-supported;
  }

  deviation "/openconfig-platform:components/openconfig-platform:component/openconfig-platform-transceiver:transceiver/openconfig-platform-transceiver:state/openconfig-platform-transceiver:pre-fec-ber" {
    deviate not-supported;
  }

  deviation "/openconfig-platform:components/openconfig-platform:component/openconfig-platform-transceiver:transceiver/openconfig-platform-transceiver:state/openconfig-platform-transceiver:present" {
    deviate not-supported;
  }

  deviation "/openconfig-platform:components/openconfig-platform:component/openconfig-platform-transceiver:transceiver/openconfig-platform-transceiver:state/openconfig-platform-transceiver:serial-no" {
    deviate not-supported;
  }

  deviation "/openconfig-platform:components/openconfig-platform:component/openconfig-platform-transceiver:transceiver/openconfig-platform-transceiver:state/openconfig-platform-transceiver:sonet-sdh-compliance-code" {
    deviate not-supported;
  }

  deviation "/openconfig-platform:components/openconfig-platform:component/openconfig-platform-transceiver:transceiver/openconfig-platform-transceiver:state/openconfig-platform-transceiver:supply-voltage/openconfig-platform-transceiver:avg" {
    deviate not-supported;
  }

  deviation "/openconfig-platform:components/openconfig-platform:component/openconfig-platform-transceiver:transceiver/openconfig-platform-transceiver:state/openconfig-platform-transceiver:supply-voltage/openconfig-platform-transceiver:interval" {
    deviate not-supported;
  }

  deviation "/openconfig-platform:components/openconfig-platform:component/openconfig-platform-transceiver:transceiver/openconfig-platform-transceiver:state/openconfig-platform-transceiver:supply-voltage/openconfig-platform-transceiver:max" {
    deviate not-supported;
  }

  deviation "/openconfig-platform:components/openconfig-platform:component/openconfig-platform-transceiver:transceiver/openconfig-platform-transceiver:state/openconfig-platform-transceiver:supply-voltage/openconfig-platform-transceiver:max-time" {
    deviate not-supported;
  }

  deviation "/openconfig-platform:components/openconfig-platform:component/openconfig-platform-transceiver:transceiver/openconfig-platform-transceiver:state/openconfig-platform-transceiver:supply-voltage/openconfig-platform-transceiver:min" {
    deviate not-supported;
  }

  deviation "/openconfig-platform:components/openconfig-platform:component/openconfig-platform-transceiver:transceiver/openconfig-platform-transceiver:state/openconfig-platform-transceiver:supply-voltage/openconfig-platform-transceiver:min-time" {
    deviate not-supported;
  }

  deviation "/openconfig-platform:components/openconfig-platform:component/openconfig-platform-transceiver:transceiver/openconfig-platform-transceiver:state/openconfig-platform-transceiver:vendor" {
    deviate not-supported;
  }

  deviation "/openconfig-platform:components/openconfig-platform:component/openconfig-platform-transceiver:transceiver/openconfig-platform-transceiver:state/openconfig-platform-transceiver:vendor-part" {
    deviate not-supported;
  }

  deviation "/openconfig-platform:components/openconfig-platform:component/openconfig-platform-transceiver:transceiver/openconfig-platform-transceiver:state/openconfig-platform-transceiver:vendor-rev" {
    deviate not-supported;
  }

  deviation "/openconfig-platform:components/openconfig-platform:component/openconfig-platform-transceiver:transceiver/openconfig-platform-transceiver:thresholds/openconfig-platform-transceiver:threshold/openconfig-platform-transceiver:state/openconfig-platform-transceiver:laser-bias-current-lower" {
    deviate not-supported;
  }

  deviation "/openconfig-platform:components/openconfig-platform:component/openconfig-platform-transceiver:transceiver/openconfig-platform-transceiver:thresholds/openconfig-platform-transceiver:threshold/openconfig-platform-transceiver:state/openconfig-platform-transceiver:laser-bias-current-upper" {
    deviate not-supported;
  }

  deviation "/openconfig-platform:components/openconfig-platform:component/openconfig-platform-transceiver:transceiver/openconfig-platform-transceiver:thresholds/openconfig-platform-transceiver:threshold/openconfig-platform-transceiver:state/openconfig-platform-transceiver:laser-temperature-lower" {
    deviate not-supported;
  }

  deviation "/openconfig-platform:components/openconfig-platform:component/openconfig-platform-transceiver:transceiver/openconfig-platform-transceiver:thresholds/openconfig-platform-transceiver:threshold/openconfig-platform-transceiver:state/openconfig-platform-transceiver:laser-temperature-upper" {
    deviate not-supported;
  }

  deviation "/openconfig-platform:components/openconfig-platform:component/openconfig-platform-transceiver:transceiver/openconfig-platform-transceiver:thresholds/openconfig-platform-transceiver:threshold/openconfig-platform-transceiver:state/openconfig-platform-transceiver:supply-voltage-lower" {
    deviate not-supported;
  }

  deviation "/openconfig-platform:components/openconfig-platform:component/openconfig-platform-transceiver:transceiver/openconfig-platform-transceiver:thresholds/openconfig-platform-transceiver:threshold/openconfig-platform-transceiver:state/openconfig-platform-transceiver:supply-voltage-upper" {
    deviate not-supported;
  }

  deviation "/openconfig-platform:components/openconfig-platform:component/openconfig-platform:backplane" {
    deviate not-supported;
  }

  deviation "/openconfig-platform:components/openconfig-platform:component/openconfig-platform:chassis/openconfig-platform:utilization" {
    deviate not-supported;
  }

  deviation "/openconfig-platform:components/openconfig-platform:component/openconfig-platform:controller-card/openconfig-platform:config/openconfig-platform-controller-card:power-admin-state" {
    deviate not-supported;
  }

  deviation "/openconfig-platform:components/openconfig-platform:component/openconfig-platform:controller-card/openconfig-platform:state/openconfig-platform-controller-card:power-admin-state" {
    deviate not-supported;
  }

  deviation "/openconfig-platform:components/openconfig-platform:component/openconfig-platform:cpu/openconfig-platform-cpu:utilization/openconfig-platform-cpu:state/openconfig-platform-cpu:max" {
    deviate not-supported;
  }

  deviation "/openconfig-platform:components/openconfig-platform:component/openconfig-platform:cpu/openconfig-platform-cpu:utilization/openconfig-platform-cpu:state/openconfig-platform-cpu:max-time" {
    deviate not-supported;
  }

  deviation "/openconfig-platform:components/openconfig-platform:component/openconfig-platform:cpu/openconfig-platform-cpu:utilization/openconfig-platform-cpu:state/openconfig-platform-cpu:min" {
    deviate not-supported;
  }

  deviation "/openconfig-platform:components/openconfig-platform:component/openconfig-platform:cpu/openconfig-platform-cpu:utilization/openconfig-platform-cpu:state/openconfig-platform-cpu:min-time" {
    deviate not-supported;
  }

  deviation "/openconfig-platform:components/openconfig-platform:component/openconfig-platform:integrated-circuit/openconfig-platform-integrated-circuit:memory" {
    deviate not-supported;
  }

  deviation "/openconfig-platform:components/openconfig-platform:component/openconfig-platform:integrated-circuit/openconfig-platform-pipeline-counters:pipeline-counters/openconfig-platform-pipeline-counters:control-plane-traffic/openconfig-platform-pipeline-counters:vendor" {
    deviate not-supported;
  }

  deviation "/openconfig-platform:components/openconfig-platform:component/openconfig-platform:integrated-circuit/openconfig-platform-pipeline-counters:pipeline-counters/openconfig-platform-pipeline-counters:drop/openconfig-platform-pipeline-counters:fabric-block" {
    deviate not-supported;
  }

  deviation "/openconfig-platform:components/openconfig-platform:component/openconfig-platform:integrated-circuit/openconfig-platform-pipeline-counters:pipeline-counters/openconfig-platform-pipeline-counters:drop/openconfig-platform-pipeline-counters:host-interface-block" {
    deviate not-supported;
  }

  deviation "/openconfig-platform:components/openconfig-platform:component/openconfig-platform:integrated-circuit/openconfig-platform-pipeline-counters:pipeline-counters/openconfig-platform-pipeline-counters:drop/openconfig-platform-pipeline-counters:interface-block" {
    deviate not-supported;
  }

  deviation "/openconfig-platform:components/openconfig-platform:component/openconfig-platform:integrated-circuit/openconfig-platform-pipeline-counters:pipeline-counters/openconfig-platform-pipeline-counters:drop/openconfig-platform-pipeline-counters:lookup-block" {
    deviate not-supported;
  }

  deviation "/openconfig-platform:components/openconfig-platform:component/openconfig-platform:integrated-circuit/openconfig-platform-pipeline-counters:pipeline-counters/openconfig-platform-pipeline-counters:drop/openconfig-platform-pipeline-counters:queueing-block" {
    deviate not-supported;
  }

  deviation "/openconfig-platform:components/openconfig-platform:component/openconfig-platform:integrated-circuit/openconfig-platform-pipeline-counters:pipeline-counters/openconfig-platform-pipeline-counters:drop/openconfig-platform-pipeline-counters:state/openconfig-platform-pipeline-counters:urpf-aggregate" {
    deviate not-supported;
  }

  deviation "/openconfig-platform:components/openconfig-platform:component/openconfig-platform:integrated-circuit/openconfig-platform-pipeline-counters:pipeline-counters/openconfig-platform-pipeline-counters:drop/openconfig-platform-pipeline-counters:vendor" {
    deviate not-supported;
  }

  deviation "/openconfig-platform:components/openconfig-platform:component/openconfig-platform:integrated-circuit/openconfig-platform-pipeline-counters:pipeline-counters/openconfig-platform-pipeline-counters:errors" {
    deviate not-supported;
  }

  deviation "/openconfig-platform:components/openconfig-platform:component/openconfig-platform:integrated-circuit/openconfig-platform-pipeline-counters:pipeline-counters/openconfig-platform-pipeline-counters:packet" {
    deviate not-supported;
  }

  deviation "/openconfig-platform:components/openconfig-platform:component/openconfig-platform:integrated-circuit/openconfig-platform:utilization/openconfig-platform:resources/openconfig-platform:resource/openconfig-platform:config/openconfig-platform:used-threshold-upper" {
    deviate not-supported;
  }

  deviation "/openconfig-platform:components/openconfig-platform:component/openconfig-platform:integrated-circuit/openconfig-platform:utilization/openconfig-platform:resources/openconfig-platform:resource/openconfig-platform:config/openconfig-platform:used-threshold-upper-clear" {
    deviate not-supported;
  }

  deviation "/openconfig-platform:components/openconfig-platform:component/openconfig-platform:integrated-circuit/openconfig-platform:utilization/openconfig-platform:resources/openconfig-platform:resource/openconfig-platform:state/openconfig-platform:max-limit" {
    deviate not-supported;
  }

  deviation "/openconfig-platform:components/openconfig-platform:component/openconfig-platform:power-supply/openconfig-platform:config/openconfig-platform-psu:enabled" {
    deviate not-supported;
  }

  deviation "/openconfig-platform:components/openconfig-platform:component/openconfig-platform:power-supply/openconfig-platform:state/openconfig-platform-psu:enabled" {
    deviate not-supported;
  }

  deviation "/openconfig-platform:components/openconfig-platform:component/openconfig-platform:properties" {
    deviate not-supported;
  }

  deviation "/openconfig-platform:components/openconfig-platform:component/openconfig-platform:state/openconfig-alarms:equipment-failure" {
    deviate not-supported;
  }

  deviation "/openconfig-platform:components/openconfig-platform:component/openconfig-platform:state/openconfig-alarms:equipment-mismatch" {
    deviate not-supported;
  }

  deviation "/openconfig-platform:components/openconfig-platform:component/openconfig-platform:state/openconfig-platform:allocated-power" {
    deviate not-supported;
  }

  deviation "/openconfig-platform:components/openconfig-platform:component/openconfig-platform:state/openconfig-platform:boot-time" {
    deviate not-supported;
  }

  deviation "/openconfig-platform:components/openconfig-platform:component/openconfig-platform:state/openconfig-platform:clei-code" {
    deviate not-supported;
  }

  deviation "/openconfig-platform:components/openconfig-platform:component/openconfig-platform:state/openconfig-platform:last-poweroff-reason" {
    deviate not-supported;
  }

  deviation "/openconfig-platform:components/openconfig-platform:component/openconfig-platform:state/openconfig-platform:last-poweroff-time" {
    deviate not-supported;
  }

  deviation "/openconfig-platform:components/openconfig-platform:component/openconfig-platform:state/openconfig-platform:pcie" {
    deviate not-supported;
  }

  deviation "/openconfig-platform:components/openconfig-platform:component/openconfig-platform:state/openconfig-platform:temperature/openconfig-platform:alarm-threshold" {
    deviate not-supported;
  }

  deviation "/openconfig-platform:components/openconfig-platform:component/openconfig-platform:state/openconfig-platform:temperature/openconfig-platform:avg" {
    deviate not-supported;
  }

  deviation "/openconfig-platform:components/openconfig-platform:component/openconfig-platform:state/openconfig-platform:temperature/openconfig-platform:interval" {
    deviate not-supported;
  }

  deviation "/openconfig-platform:components/openconfig-platform:component/openconfig-platform:state/openconfig-platform:temperature/openconfig-platform:min" {
    deviate not-supported;
  }

  deviation "/openconfig-platform:components/openconfig-platform:component/openconfig-platform:state/openconfig-platform:temperature/openconfig-platform:min-time" {
    deviate not-supported;
  }

  deviation "/openconfig-platform:components/openconfig-platform:component/openconfig-platform:state/openconfig-platform:used-power" {
    deviate not-supported;
  }

  deviation "/openconfig-platform:components/openconfig-platform:component/openconfig-terminal-device:optical-channel/openconfig-terminal-device:config/openconfig-terminal-device:line-port" {
    deviate not-supported;
  }

  deviation "/openconfig-platform:components/openconfig-platform:component/openconfig-terminal-device:optical-channel/openconfig-terminal-device:state/openconfig-terminal-device:carrier-frequency-offset/openconfig-terminal-device:interval" {
    deviate not-supported;
  }

  deviation "/openconfig-platform:components/openconfig-platform:component/openconfig-terminal-device:optical-channel/openconfig-terminal-device:state/openconfig-terminal-device:carrier-frequency-offset/openconfig-terminal-device:max-time" {
    deviate not-supported;
  }

  deviation "/openconfig-platform:components/openconfig-platform:component/openconfig-terminal-device:optical-channel/openconfig-terminal-device:state/openconfig-terminal-device:carrier-frequency-offset/openconfig-terminal-device:min-time" {
    deviate not-supported;
  }

  deviation "/openconfig-platform:components/openconfig-platform:component/openconfig-terminal-device:optical-channel/openconfig-terminal-device:state/openconfig-terminal-device:chromatic-dispersion/openconfig-terminal-device:interval" {
    deviate not-supported;
  }

  deviation "/openconfig-platform:components/openconfig-platform:component/openconfig-terminal-device:optical-channel/openconfig-terminal-device:state/openconfig-terminal-device:chromatic-dispersion/openconfig-terminal-device:max-time" {
    deviate not-supported;
  }

  deviation "/openconfig-platform:components/openconfig-platform:component/openconfig-terminal-device:optical-channel/openconfig-terminal-device:state/openconfig-terminal-device:chromatic-dispersion/openconfig-terminal-device:min-time" {
    deviate not-supported;
  }

  deviation "/openconfig-platform:components/openconfig-platform:component/openconfig-terminal-device:optical-channel/openconfig-terminal-device:state/openconfig-terminal-device:esnr" {
    deviate not-supported;
  }

  deviation "/openconfig-platform:components/openconfig-platform:component/openconfig-terminal-device:optical-channel/openconfig-terminal-device:state/openconfig-terminal-device:fec-uncorrectable-blocks" {
    deviate not-supported;
  }

  deviation "/openconfig-platform:components/openconfig-platform:component/openconfig-terminal-device:optical-channel/openconfig-terminal-device:state/openconfig-terminal-device:group-id" {
    deviate not-supported;
  }

  deviation "/openconfig-platform:components/openconfig-platform:component/openconfig-terminal-device:optical-channel/openconfig-terminal-device:state/openconfig-terminal-device:input-power/openconfig-terminal-device:interval" {
    deviate not-supported;
  }

  deviation "/openconfig-platform:components/openconfig-platform:component/openconfig-terminal-device:optical-channel/openconfig-terminal-device:state/openconfig-terminal-device:input-power/openconfig-terminal-device:max-time" {
    deviate not-supported;
  }

  deviation "/openconfig-platform:components/openconfig-platform:component/openconfig-terminal-device:optical-channel/openconfig-terminal-device:state/openconfig-terminal-device:input-power/openconfig-terminal-device:min-time" {
    deviate not-supported;
  }

  deviation "/openconfig-platform:components/openconfig-platform:component/openconfig-terminal-device:optical-channel/openconfig-terminal-device:state/openconfig-terminal-device:laser-bias-current/openconfig-terminal-device:avg" {
    deviate not-supported;
  }

  deviation "/openconfig-platform:components/openconfig-platform:component/openconfig-terminal-device:optical-channel/openconfig-terminal-device:state/openconfig-terminal-device:laser-bias-current/openconfig-terminal-device:interval" {
    deviate not-supported;
  }

  deviation "/openconfig-platform:components/openconfig-platform:component/openconfig-terminal-device:optical-channel/openconfig-terminal-device:state/openconfig-terminal-device:laser-bias-current/openconfig-terminal-device:max" {
    deviate not-supported;
  }

  deviation "/openconfig-platform:components/openconfig-platform:component/openconfig-terminal-device:optical-channel/openconfig-terminal-device:state/openconfig-terminal-device:laser-bias-current/openconfig-terminal-device:max-time" {
    deviate not-supported;
  }

  deviation "/openconfig-platform:components/openconfig-platform:component/openconfig-terminal-device:optical-channel/openconfig-terminal-device:state/openconfig-terminal-device:laser-bias-current/openconfig-terminal-device:min" {
    deviate not-supported;
  }

  deviation "/openconfig-platform:components/openconfig-platform:component/openconfig-terminal-device:optical-channel/openconfig-terminal-device:state/openconfig-terminal-device:laser-bias-current/openconfig-terminal-device:min-time" {
    deviate not-supported;
  }

  deviation "/openconfig-platform:components/openconfig-platform:component/openconfig-terminal-device:optical-channel/openconfig-terminal-device:state/openconfig-terminal-device:logical-channel-assignment" {
    deviate not-supported;
  }

  deviation "/openconfig-platform:components/openconfig-platform:component/openconfig-terminal-device:optical-channel/openconfig-terminal-device:state/openconfig-terminal-device:modulation-error-ratio" {
    deviate not-supported;
  }

  deviation "/openconfig-platform:components/openconfig-platform:component/openconfig-terminal-device:optical-channel/openconfig-terminal-device:state/openconfig-terminal-device:modulator-bias-x-phase" {
    deviate not-supported;
  }

  deviation "/openconfig-platform:components/openconfig-platform:component/openconfig-terminal-device:optical-channel/openconfig-terminal-device:state/openconfig-terminal-device:modulator-bias-xi" {
    deviate not-supported;
  }

  deviation "/openconfig-platform:components/openconfig-platform:component/openconfig-terminal-device:optical-channel/openconfig-terminal-device:state/openconfig-terminal-device:modulator-bias-xq" {
    deviate not-supported;
  }

  deviation "/openconfig-platform:components/openconfig-platform:component/openconfig-terminal-device:optical-channel/openconfig-terminal-device:state/openconfig-terminal-device:modulator-bias-y-phase" {
    deviate not-supported;
  }

  deviation "/openconfig-platform:components/openconfig-platform:component/openconfig-terminal-device:optical-channel/openconfig-terminal-device:state/openconfig-terminal-device:modulator-bias-yi" {
    deviate not-supported;
  }

  deviation "/openconfig-platform:components/openconfig-platform:component/openconfig-terminal-device:optical-channel/openconfig-terminal-device:state/openconfig-terminal-device:modulator-bias-yq" {
    deviate not-supported;
  }

  deviation "/openconfig-platform:components/openconfig-platform:component/openconfig-terminal-device:optical-channel/openconfig-terminal-device:state/openconfig-terminal-device:osnr/openconfig-terminal-device:interval" {
    deviate not-supported;
  }

  deviation "/openconfig-platform:components/openconfig-platform:component/openconfig-terminal-device:optical-channel/openconfig-terminal-device:state/openconfig-terminal-device:osnr/openconfig-terminal-device:max-time" {
    deviate not-supported;
  }

  deviation "/openconfig-platform:components/openconfig-platform:component/openconfig-terminal-device:optical-channel/openconfig-terminal-device:state/openconfig-terminal-device:osnr/openconfig-terminal-device:min-time" {
    deviate not-supported;
  }

  deviation "/openconfig-platform:components/openconfig-platform:component/openconfig-terminal-device:optical-channel/openconfig-terminal-device:state/openconfig-terminal-device:output-power/openconfig-terminal-device:interval" {
    deviate not-supported;
  }

  deviation "/openconfig-platform:components/openconfig-platform:component/openconfig-terminal-device:optical-channel/openconfig-terminal-device:state/openconfig-terminal-device:output-power/openconfig-terminal-device:max-time" {
    deviate not-supported;
  }

  deviation "/openconfig-platform:components/openconfig-platform:component/openconfig-terminal-device:optical-channel/openconfig-terminal-device:state/openconfig-terminal-device:output-power/openconfig-terminal-device:min-time" {
    deviate not-supported;
  }

  deviation "/openconfig-platform:components/openconfig-platform:component/openconfig-terminal-device:optical-channel/openconfig-terminal-device:state/openconfig-terminal-device:polarization-dependent-loss" {
    deviate not-supported;
  }

  deviation "/openconfig-platform:components/openconfig-platform:component/openconfig-terminal-device:optical-channel/openconfig-terminal-device:state/openconfig-terminal-device:polarization-mode-dispersion" {
    deviate not-supported;
  }

  deviation "/openconfig-platform:components/openconfig-platform:component/openconfig-terminal-device:optical-channel/openconfig-terminal-device:state/openconfig-terminal-device:post-fec-ber" {
    deviate not-supported;
  }

  deviation "/openconfig-platform:components/openconfig-platform:component/openconfig-terminal-device:optical-channel/openconfig-terminal-device:state/openconfig-terminal-device:pre-fec-ber" {
    deviate not-supported;
  }

  deviation "/openconfig-platform:components/openconfig-platform:component/openconfig-terminal-device:optical-channel/openconfig-terminal-device:state/openconfig-terminal-device:q-value" {
    deviate not-supported;
  }

  deviation "/openconfig-platform:components/openconfig-platform:component/openconfig-terminal-device:optical-channel/openconfig-terminal-device:state/openconfig-terminal-device:second-order-polarization-mode-dispersion" {
    deviate not-supported;
  }

  deviation "/openconfig-platform:components/openconfig-platform:component/openconfig-terminal-device:optical-channel/openconfig-terminal-device:state/openconfig-terminal-device:sop-roc" {
    deviate not-supported;
  }

  deviation "/openconfig-qos:qos/openconfig-qos:buffer-allocation-profiles/openconfig-qos:buffer-allocation-profile/openconfig-qos:queues/openconfig-qos:queue/openconfig-qos:config/openconfig-qos:dedicated-buffer" {
    deviate not-supported;
  }

  deviation "/openconfig-qos:qos/openconfig-qos:buffer-allocation-profiles/openconfig-qos:buffer-allocation-profile/openconfig-qos:queues/openconfig-qos:queue/openconfig-qos:config/openconfig-qos:dedicated-buffer-temporal" {
    deviate not-supported;
  }

  deviation "/openconfig-qos:qos/openconfig-qos:buffer-allocation-profiles/openconfig-qos:buffer-allocation-profile/openconfig-qos:queues/openconfig-qos:queue/openconfig-qos:config/openconfig-qos:dynamic-limit-scaling-factor" {
    deviate not-supported;
  }

  deviation "/openconfig-qos:qos/openconfig-qos:buffer-allocation-profiles/openconfig-qos:buffer-allocation-profile/openconfig-qos:queues/openconfig-qos:queue/openconfig-qos:config/openconfig-qos:shared-buffer-limit-type" {
    deviate not-supported;
  }

  deviation "/openconfig-qos:qos/openconfig-qos:buffer-allocation-profiles/openconfig-qos:buffer-allocation-profile/openconfig-qos:queues/openconfig-qos:queue/openconfig-qos:config/openconfig-qos:use-shared-buffer" {
    deviate not-supported;
  }

  deviation "/openconfig-qos:qos/openconfig-qos:buffer-allocation-profiles/openconfig-qos:buffer-allocation-profile/openconfig-qos:queues/openconfig-qos:queue/openconfig-qos:state/openconfig-qos:dedicated-buffer" {
    deviate not-supported;
  }

  deviation "/openconfig-qos:qos/openconfig-qos:buffer-allocation-profiles/openconfig-qos:buffer-allocation-profile/openconfig-qos:queues/openconfig-qos:queue/openconfig-qos:state/openconfig-qos:dedicated-buffer-temporal" {
    deviate not-supported;
  }

  deviation "/openconfig-qos:qos/openconfig-qos:buffer-allocation-profiles/openconfig-qos:buffer-allocation-profile/openconfig-qos:queues/openconfig-qos:queue/openconfig-qos:state/openconfig-qos:dynamic-limit-scaling-factor" {
    deviate not-supported;
  }

  deviation "/openconfig-qos:qos/openconfig-qos:buffer-allocation-profiles/openconfig-qos:buffer-allocation-profile/openconfig-qos:queues/openconfig-qos:queue/openconfig-qos:state/openconfig-qos:shared-buffer-limit-type" {
    deviate not-supported;
  }

  deviation "/openconfig-qos:qos/openconfig-qos:buffer-allocation-profiles/openconfig-qos:buffer-allocation-profile/openconfig-qos:queues/openconfig-qos:queue/openconfig-qos:state/openconfig-qos:use-shared-buffer" {
    deviate not-supported;
  }

  deviation "/openconfig-qos:qos/openconfig-qos:classifiers/openconfig-qos:classifier/openconfig-qos:terms/openconfig-qos:term/openconfig-qos:actions/openconfig-qos:remark/openconfig-qos:config/openconfig-qos:set-dot1p" {
    deviate not-supported;
  }

  deviation "/openconfig-qos:qos/openconfig-qos:classifiers/openconfig-qos:classifier/openconfig-qos:terms/openconfig-qos:term/openconfig-qos:actions/openconfig-qos:remark/openconfig-qos:config/openconfig-qos:set-mpls-tc" {
    deviate not-supported;
  }

  deviation "/openconfig-qos:qos/openconfig-qos:classifiers/openconfig-qos:classifier/openconfig-qos:terms/openconfig-qos:term/openconfig-qos:actions/openconfig-qos:remark/openconfig-qos:state/openconfig-qos:set-dot1p" {
    deviate not-supported;
  }

  deviation "/openconfig-qos:qos/openconfig-qos:classifiers/openconfig-qos:classifier/openconfig-qos:terms/openconfig-qos:term/openconfig-qos:actions/openconfig-qos:remark/openconfig-qos:state/openconfig-qos:set-mpls-tc" {
    deviate not-supported;
  }

  deviation "/openconfig-qos:qos/openconfig-qos:classifiers/openconfig-qos:classifier/openconfig-qos:terms/openconfig-qos:term/openconfig-qos:conditions/openconfig-qos:ipv4/openconfig-qos:config/openconfig-qos:destination-address-prefix-set" {
    deviate not-supported;
  }

  deviation "/openconfig-qos:qos/openconfig-qos:classifiers/openconfig-qos:classifier/openconfig-qos:terms/openconfig-qos:term/openconfig-qos:conditions/openconfig-qos:ipv4/openconfig-qos:config/openconfig-qos:dscp" {
    deviate not-supported;
  }

  deviation "/openconfig-qos:qos/openconfig-qos:classifiers/openconfig-qos:classifier/openconfig-qos:terms/openconfig-qos:term/openconfig-qos:conditions/openconfig-qos:ipv4/openconfig-qos:config/openconfig-qos:hop-limit" {
    deviate not-supported;
  }

  deviation "/openconfig-qos:qos/openconfig-qos:classifiers/openconfig-qos:classifier/openconfig-qos:terms/openconfig-qos:term/openconfig-qos:conditions/openconfig-qos:ipv4/openconfig-qos:config/openconfig-qos:length" {
    deviate not-supported;
  }

  deviation "/openconfig-qos:qos/openconfig-qos:classifiers/openconfig-qos:classifier/openconfig-qos:terms/openconfig-qos:term/openconfig-qos:conditions/openconfig-qos:ipv4/openconfig-qos:config/openconfig-qos:source-address-prefix-set" {
    deviate not-supported;
  }

  deviation "/openconfig-qos:qos/openconfig-qos:classifiers/openconfig-qos:classifier/openconfig-qos:terms/openconfig-qos:term/openconfig-qos:conditions/openconfig-qos:ipv4/openconfig-qos:icmpv4" {
    deviate not-supported;
  }

  deviation "/openconfig-qos:qos/openconfig-qos:classifiers/openconfig-qos:classifier/openconfig-qos:terms/openconfig-qos:term/openconfig-qos:conditions/openconfig-qos:ipv4/openconfig-qos:state/openconfig-qos:destination-address-prefix-set" {
    deviate not-supported;
  }

  deviation "/openconfig-qos:qos/openconfig-qos:classifiers/openconfig-qos:classifier/openconfig-qos:terms/openconfig-qos:term/openconfig-qos:conditions/openconfig-qos:ipv4/openconfig-qos:state/openconfig-qos:dscp" {
    deviate not-supported;
  }

  deviation "/openconfig-qos:qos/openconfig-qos:classifiers/openconfig-qos:classifier/openconfig-qos:terms/openconfig-qos:term/openconfig-qos:conditions/openconfig-qos:ipv4/openconfig-qos:state/openconfig-qos:hop-limit" {
    deviate not-supported;
  }

  deviation "/openconfig-qos:qos/openconfig-qos:classifiers/openconfig-qos:classifier/openconfig-qos:terms/openconfig-qos:term/openconfig-qos:conditions/openconfig-qos:ipv4/openconfig-qos:state/openconfig-qos:length" {
    deviate not-supported;
  }

  deviation "/openconfig-qos:qos/openconfig-qos:classifiers/openconfig-qos:classifier/openconfig-qos:terms/openconfig-qos:term/openconfig-qos:conditions/openconfig-qos:ipv4/openconfig-qos:state/openconfig-qos:source-address-prefix-set" {
    deviate not-supported;
  }

  deviation "/openconfig-qos:qos/openconfig-qos:classifiers/openconfig-qos:classifier/openconfig-qos:terms/openconfig-qos:term/openconfig-qos:conditions/openconfig-qos:ipv6/openconfig-qos:config/openconfig-qos:destination-address-prefix-set" {
    deviate not-supported;
  }

  deviation "/openconfig-qos:qos/openconfig-qos:classifiers/openconfig-qos:classifier/openconfig-qos:terms/openconfig-qos:term/openconfig-qos:conditions/openconfig-qos:ipv6/openconfig-qos:config/openconfig-qos:destination-flow-label" {
    deviate not-supported;
  }

  deviation "/openconfig-qos:qos/openconfig-qos:classifiers/openconfig-qos:classifier/openconfig-qos:terms/openconfig-qos:term/openconfig-qos:conditions/openconfig-qos:ipv6/openconfig-qos:config/openconfig-qos:dscp" {
    deviate not-supported;
  }

  deviation "/openconfig-qos:qos/openconfig-qos:classifiers/openconfig-qos:classifier/openconfig-qos:terms/openconfig-qos:term/openconfig-qos:conditions/openconfig-qos:ipv6/openconfig-qos:config/openconfig-qos:hop-limit" {
    deviate not-supported;
  }

  deviation "/openconfig-qos:qos/openconfig-qos:classifiers/openconfig-qos:classifier/openconfig-qos:terms/openconfig-qos:term/openconfig-qos:conditions/openconfig-qos:ipv6/openconfig-qos:config/openconfig-qos:length" {
    deviate not-supported;
  }

  deviation "/openconfig-qos:qos/openconfig-qos:classifiers/openconfig-qos:classifier/openconfig-qos:terms/openconfig-qos:term/openconfig-qos:conditions/openconfig-qos:ipv6/openconfig-qos:config/openconfig-qos:source-address-prefix-set" {
    deviate not-supported;
  }

  deviation "/openconfig-qos:qos/openconfig-qos:classifiers/openconfig-qos:classifier/openconfig-qos:terms/openconfig-qos:term/openconfig-qos:conditions/openconfig-qos:ipv6/openconfig-qos:config/openconfig-qos:source-flow-label" {
    deviate not-supported;
  }

  deviation "/openconfig-qos:qos/openconfig-qos:classifiers/openconfig-qos:classifier/openconfig-qos:terms/openconfig-qos:term/openconfig-qos:conditions/openconfig-qos:ipv6/openconfig-qos:icmpv6" {
    deviate not-supported;
  }

  deviation "/openconfig-qos:qos/openconfig-qos:classifiers/openconfig-qos:classifier/openconfig-qos:terms/openconfig-qos:term/openconfig-qos:conditions/openconfig-qos:ipv6/openconfig-qos:state/openconfig-qos:destination-address-prefix-set" {
    deviate not-supported;
  }

  deviation "/openconfig-qos:qos/openconfig-qos:classifiers/openconfig-qos:classifier/openconfig-qos:terms/openconfig-qos:term/openconfig-qos:conditions/openconfig-qos:ipv6/openconfig-qos:state/openconfig-qos:destination-flow-label" {
    deviate not-supported;
  }

  deviation "/openconfig-qos:qos/openconfig-qos:classifiers/openconfig-qos:classifier/openconfig-qos:terms/openconfig-qos:term/openconfig-qos:conditions/openconfig-qos:ipv6/openconfig-qos:state/openconfig-qos:dscp" {
    deviate not-supported;
  }

  deviation "/openconfig-qos:qos/openconfig-qos:classifiers/openconfig-qos:classifier/openconfig-qos:terms/openconfig-qos:term/openconfig-qos:conditions/openconfig-qos:ipv6/openconfig-qos:state/openconfig-qos:hop-limit" {
    deviate not-supported;
  }

  deviation "/openconfig-qos:qos/openconfig-qos:classifiers/openconfig-qos:classifier/openconfig-qos:terms/openconfig-qos:term/openconfig-qos:conditions/openconfig-qos:ipv6/openconfig-qos:state/openconfig-qos:length" {
    deviate not-supported;
  }

  deviation "/openconfig-qos:qos/openconfig-qos:classifiers/openconfig-qos:classifier/openconfig-qos:terms/openconfig-qos:term/openconfig-qos:conditions/openconfig-qos:ipv6/openconfig-qos:state/openconfig-qos:source-address-prefix-set" {
    deviate not-supported;
  }

  deviation "/openconfig-qos:qos/openconfig-qos:classifiers/openconfig-qos:classifier/openconfig-qos:terms/openconfig-qos:term/openconfig-qos:conditions/openconfig-qos:ipv6/openconfig-qos:state/openconfig-qos:source-flow-label" {
    deviate not-supported;
  }

  deviation "/openconfig-qos:qos/openconfig-qos:classifiers/openconfig-qos:classifier/openconfig-qos:terms/openconfig-qos:term/openconfig-qos:conditions/openconfig-qos:l2" {
    deviate not-supported;
  }

  deviation "/openconfig-qos:qos/openconfig-qos:classifiers/openconfig-qos:classifier/openconfig-qos:terms/openconfig-qos:term/openconfig-qos:conditions/openconfig-qos:mpls" {
    deviate not-supported;
  }

  deviation "/openconfig-qos:qos/openconfig-qos:classifiers/openconfig-qos:classifier/openconfig-qos:terms/openconfig-qos:term/openconfig-qos:conditions/openconfig-qos:transport/openconfig-qos:config/openconfig-qos:builtin-detail" {
    deviate not-supported;
  }

  deviation "/openconfig-qos:qos/openconfig-qos:classifiers/openconfig-qos:classifier/openconfig-qos:terms/openconfig-qos:term/openconfig-qos:conditions/openconfig-qos:transport/openconfig-qos:config/openconfig-qos:destination-port-set" {
    deviate not-supported;
  }

  deviation "/openconfig-qos:qos/openconfig-qos:classifiers/openconfig-qos:classifier/openconfig-qos:terms/openconfig-qos:term/openconfig-qos:conditions/openconfig-qos:transport/openconfig-qos:config/openconfig-qos:detail-mode" {
    deviate not-supported;
  }

  deviation "/openconfig-qos:qos/openconfig-qos:classifiers/openconfig-qos:classifier/openconfig-qos:terms/openconfig-qos:term/openconfig-qos:conditions/openconfig-qos:transport/openconfig-qos:config/openconfig-qos:explicit-detail-match-mode" {
    deviate not-supported;
  }

  deviation "/openconfig-qos:qos/openconfig-qos:classifiers/openconfig-qos:classifier/openconfig-qos:terms/openconfig-qos:term/openconfig-qos:conditions/openconfig-qos:transport/openconfig-qos:config/openconfig-qos:explicit-tcp-flags" {
    deviate not-supported;
  }

  deviation "/openconfig-qos:qos/openconfig-qos:classifiers/openconfig-qos:classifier/openconfig-qos:terms/openconfig-qos:term/openconfig-qos:conditions/openconfig-qos:transport/openconfig-qos:config/openconfig-qos:source-port-set" {
    deviate not-supported;
  }

  deviation "/openconfig-qos:qos/openconfig-qos:classifiers/openconfig-qos:classifier/openconfig-qos:terms/openconfig-qos:term/openconfig-qos:conditions/openconfig-qos:transport/openconfig-qos:state/openconfig-qos:builtin-detail" {
    deviate not-supported;
  }

  deviation "/openconfig-qos:qos/openconfig-qos:classifiers/openconfig-qos:classifier/openconfig-qos:terms/openconfig-qos:term/openconfig-qos:conditions/openconfig-qos:transport/openconfig-qos:state/openconfig-qos:destination-port-set" {
    deviate not-supported;
  }

  deviation "/openconfig-qos:qos/openconfig-qos:classifiers/openconfig-qos:classifier/openconfig-qos:terms/openconfig-qos:term/openconfig-qos:conditions/openconfig-qos:transport/openconfig-qos:state/openconfig-qos:detail-mode" {
    deviate not-supported;
  }

  deviation "/openconfig-qos:qos/openconfig-qos:classifiers/openconfig-qos:classifier/openconfig-qos:terms/openconfig-qos:term/openconfig-qos:conditions/openconfig-qos:transport/openconfig-qos:state/openconfig-qos:explicit-detail-match-mode" {
    deviate not-supported;
  }

  deviation "/openconfig-qos:qos/openconfig-qos:classifiers/openconfig-qos:classifier/openconfig-qos:terms/openconfig-qos:term/openconfig-qos:conditions/openconfig-qos:transport/openconfig-qos:state/openconfig-qos:explicit-tcp-flags" {
    deviate not-supported;
  }

  deviation "/openconfig-qos:qos/openconfig-qos:classifiers/openconfig-qos:classifier/openconfig-qos:terms/openconfig-qos:term/openconfig-qos:conditions/openconfig-qos:transport/openconfig-qos:state/openconfig-qos:source-port-set" {
    deviate not-supported;
  }

  deviation "/openconfig-qos:qos/openconfig-qos:forwarding-groups/openconfig-qos:forwarding-group/openconfig-qos:config/openconfig-qos:fabric-priority" {
    deviate not-supported;
  }

  deviation "/openconfig-qos:qos/openconfig-qos:forwarding-groups/openconfig-qos:forwarding-group/openconfig-qos:state/openconfig-qos:fabric-priority" {
    deviate not-supported;
  }

  deviation "/openconfig-qos:qos/openconfig-qos:interfaces/openconfig-qos:interface/openconfig-qos:input/openconfig-qos:classifiers/openconfig-qos:classifier/openconfig-qos:terms" {
    deviate not-supported;
  }

  deviation "/openconfig-qos:qos/openconfig-qos:interfaces/openconfig-qos:interface/openconfig-qos:input/openconfig-qos:config/openconfig-qos:buffer-allocation-profile" {
    deviate not-supported;
  }

  deviation "/openconfig-qos:qos/openconfig-qos:interfaces/openconfig-qos:interface/openconfig-qos:input/openconfig-qos:config/openconfig-qos:multicast-buffer-allocation-profile" {
    deviate not-supported;
  }

  deviation "/openconfig-qos:qos/openconfig-qos:interfaces/openconfig-qos:interface/openconfig-qos:input/openconfig-qos:config/openconfig-qos:unicast-buffer-allocation-profile" {
    deviate not-supported;
  }

  deviation "/openconfig-qos:qos/openconfig-qos:interfaces/openconfig-qos:interface/openconfig-qos:input/openconfig-qos:queues" {
    deviate not-supported;
  }

  deviation "/openconfig-qos:qos/openconfig-qos:interfaces/openconfig-qos:interface/openconfig-qos:input/openconfig-qos:scheduler-policy" {
    deviate not-supported;
  }

  deviation "/openconfig-qos:qos/openconfig-qos:interfaces/openconfig-qos:interface/openconfig-qos:input/openconfig-qos:state/openconfig-qos:buffer-allocation-profile" {
    deviate not-supported;
  }

  deviation "/openconfig-qos:qos/openconfig-qos:interfaces/openconfig-qos:interface/openconfig-qos:input/openconfig-qos:state/openconfig-qos:multicast-buffer-allocation-profile" {
    deviate not-supported;
  }

  deviation "/openconfig-qos:qos/openconfig-qos:interfaces/openconfig-qos:interface/openconfig-qos:input/openconfig-qos:state/openconfig-qos:unicast-buffer-allocation-profile" {
    deviate not-supported;
  }

  deviation "/openconfig-qos:qos/openconfig-qos:interfaces/openconfig-qos:interface/openconfig-qos:input/openconfig-qos:virtual-output-queues" {
    deviate not-supported;
  }

  deviation "/openconfig-qos:qos/openconfig-qos:interfaces/openconfig-qos:interface/openconfig-qos:output/openconfig-qos:classifiers" {
    deviate not-supported;
  }

  deviation "/openconfig-qos:qos/openconfig-qos:interfaces/openconfig-qos:interface/openconfig-qos:output/openconfig-qos:config/openconfig-qos:multicast-buffer-allocation-profile" {
    deviate not-supported;
  }

  deviation "/openconfig-qos:qos/openconfig-qos:interfaces/openconfig-qos:interface/openconfig-qos:output/openconfig-qos:config/openconfig-qos:unicast-buffer-allocation-profile" {
    deviate not-supported;
  }

  deviation "/openconfig-qos:qos/openconfig-qos:interfaces/openconfig-qos:interface/openconfig-qos:output/openconfig-qos:queues/openconfig-qos:queue/openconfig-qos:state/openconfig-qos:avg-queue-len" {
    deviate not-supported;
  }

  deviation "/openconfig-qos:qos/openconfig-qos:interfaces/openconfig-qos:interface/openconfig-qos:output/openconfig-qos:queues/openconfig-qos:queue/openconfig-qos:state/openconfig-qos:ecn-selected-octets" {
    deviate not-supported;
  }

  deviation "/openconfig-qos:qos/openconfig-qos:interfaces/openconfig-qos:interface/openconfig-qos:output/openconfig-qos:queues/openconfig-qos:queue/openconfig-qos:state/openconfig-qos:ecn-selected-pkts" {
    deviate not-supported;
  }

  deviation "/openconfig-qos:qos/openconfig-qos:interfaces/openconfig-qos:interface/openconfig-qos:output/openconfig-qos:scheduler-policy/openconfig-qos:schedulers" {
    deviate not-supported;
  }

  deviation "/openconfig-qos:qos/openconfig-qos:interfaces/openconfig-qos:interface/openconfig-qos:output/openconfig-qos:state/openconfig-qos:multicast-buffer-allocation-profile" {
    deviate not-supported;
  }

  deviation "/openconfig-qos:qos/openconfig-qos:interfaces/openconfig-qos:interface/openconfig-qos:output/openconfig-qos:state/openconfig-qos:unicast-buffer-allocation-profile" {
    deviate not-supported;
  }

  deviation "/openconfig-qos:qos/openconfig-qos:queue-management-profiles/openconfig-qos:queue-management-profile/openconfig-qos:red" {
    deviate not-supported;
  }

  deviation "/openconfig-qos:qos/openconfig-qos:scheduler-policies/openconfig-qos:scheduler-policy/openconfig-qos:schedulers/openconfig-qos:scheduler/openconfig-qos:config/openconfig-qos:type" {
    deviate not-supported;
  }

  deviation "/openconfig-qos:qos/openconfig-qos:scheduler-policies/openconfig-qos:scheduler-policy/openconfig-qos:schedulers/openconfig-qos:scheduler/openconfig-qos:one-rate-two-color" {
    deviate not-supported;
  }

  deviation "/openconfig-qos:qos/openconfig-qos:scheduler-policies/openconfig-qos:scheduler-policy/openconfig-qos:schedulers/openconfig-qos:scheduler/openconfig-qos:output" {
    deviate not-supported;
  }

  deviation "/openconfig-qos:qos/openconfig-qos:scheduler-policies/openconfig-qos:scheduler-policy/openconfig-qos:schedulers/openconfig-qos:scheduler/openconfig-qos:state/openconfig-qos:type" {
    deviate not-supported;
  }

  deviation "/openconfig-qos:qos/openconfig-qos:scheduler-policies/openconfig-qos:scheduler-policy/openconfig-qos:schedulers/openconfig-qos:scheduler/openconfig-qos:two-rate-three-color" {
    deviate not-supported;
  }

  deviation "/openconfig-routing-policy:routing-policy/openconfig-routing-policy:defined-sets/openconfig-bgp-policy:bgp-defined-sets/openconfig-bgp-policy:community-sets/openconfig-bgp-policy:community-set/openconfig-bgp-policy:config/openconfig-bgp-policy:match-set-options" {
    deviate not-supported;
  }

  deviation "/openconfig-routing-policy:routing-policy/openconfig-routing-policy:defined-sets/openconfig-bgp-policy:bgp-defined-sets/openconfig-bgp-policy:community-sets/openconfig-bgp-policy:community-set/openconfig-bgp-policy:state/openconfig-bgp-policy:match-set-options" {
    deviate not-supported;
  }

  deviation "/openconfig-routing-policy:routing-policy/openconfig-routing-policy:defined-sets/openconfig-bgp-policy:bgp-defined-sets/openconfig-bgp-policy:ext-community-sets/openconfig-bgp-policy:ext-community-set/openconfig-bgp-policy:config/openconfig-bgp-policy:match-set-options" {
    deviate not-supported;
  }

  deviation "/openconfig-routing-policy:routing-policy/openconfig-routing-policy:defined-sets/openconfig-bgp-policy:bgp-defined-sets/openconfig-bgp-policy:ext-community-sets/openconfig-bgp-policy:ext-community-set/openconfig-bgp-policy:state/openconfig-bgp-policy:match-set-options" {
    deviate not-supported;
  }

  deviation "/openconfig-routing-policy:routing-policy/openconfig-routing-policy:defined-sets/openconfig-routing-policy:neighbor-sets" {
    deviate not-supported;
  }

  deviation "/openconfig-routing-policy:routing-policy/openconfig-routing-policy:defined-sets/openconfig-routing-policy:prefix-sets/openconfig-routing-policy:prefix-set/openconfig-routing-policy:config/openconfig-routing-policy:mode" {
    deviate not-supported;
  }

  deviation "/openconfig-routing-policy:routing-policy/openconfig-routing-policy:defined-sets/openconfig-routing-policy:prefix-sets/openconfig-routing-policy:prefix-set/openconfig-routing-policy:state/openconfig-routing-policy:mode" {
    deviate not-supported;
  }

  deviation "/openconfig-routing-policy:routing-policy/openconfig-routing-policy:policy-definitions/openconfig-routing-policy:policy-definition/openconfig-routing-policy:statements/openconfig-routing-policy:statement/openconfig-routing-policy:actions/openconfig-bgp-policy:bgp-actions/openconfig-bgp-policy:set-as-path-prepend/openconfig-bgp-policy:config/openconfig-bgp-policy:use-last-as" {
    deviate not-supported;
  }

  deviation "/openconfig-routing-policy:routing-policy/openconfig-routing-policy:policy-definitions/openconfig-routing-policy:policy-definition/openconfig-routing-policy:statements/openconfig-routing-policy:statement/openconfig-routing-policy:actions/openconfig-bgp-policy:bgp-actions/openconfig-bgp-policy:set-as-path-prepend/openconfig-bgp-policy:state/openconfig-bgp-policy:use-last-as" {
    deviate not-supported;
  }

  deviation "/openconfig-routing-policy:routing-policy/openconfig-routing-policy:policy-definitions/openconfig-routing-policy:policy-definition/openconfig-routing-policy:statements/openconfig-routing-policy:statement/openconfig-routing-policy:actions/openconfig-bgp-policy:bgp-actions/openconfig-bgp-policy:set-community/openconfig-bgp-policy:inline" {
    deviate not-supported;
  }

  deviation "/openconfig-routing-policy:routing-policy/openconfig-routing-policy:policy-definitions/openconfig-routing-policy:policy-definition/openconfig-routing-policy:statements/openconfig-routing-policy:statement/openconfig-routing-policy:actions/openconfig-bgp-policy:bgp-actions/openconfig-bgp-policy:set-community/openconfig-bgp-policy:reference/openconfig-bgp-policy:config/openconfig-bgp-policy:community-set-ref" {
    deviate not-supported;
  }

  deviation "/openconfig-routing-policy:routing-policy/openconfig-routing-policy:policy-definitions/openconfig-routing-policy:policy-definition/openconfig-routing-policy:statements/openconfig-routing-policy:statement/openconfig-routing-policy:actions/openconfig-bgp-policy:bgp-actions/openconfig-bgp-policy:set-community/openconfig-bgp-policy:reference/openconfig-bgp-policy:state/openconfig-bgp-policy:community-set-ref" {
    deviate not-supported;
  }

  deviation "/openconfig-routing-policy:routing-policy/openconfig-routing-policy:policy-definitions/openconfig-routing-policy:policy-definition/openconfig-routing-policy:statements/openconfig-routing-policy:statement/openconfig-routing-policy:actions/openconfig-bgp-policy:bgp-actions/openconfig-bgp-policy:set-ext-community/openconfig-bgp-policy:inline" {
    deviate not-supported;
  }

  deviation "/openconfig-routing-policy:routing-policy/openconfig-routing-policy:policy-definitions/openconfig-routing-policy:policy-definition/openconfig-routing-policy:statements/openconfig-routing-policy:statement/openconfig-routing-policy:actions/openconfig-bgp-policy:bgp-actions/openconfig-bgp-policy:set-ext-community/openconfig-bgp-policy:reference/openconfig-bgp-policy:config/openconfig-bgp-policy:ext-community-set-ref" {
    deviate not-supported;
  }

  deviation "/openconfig-routing-policy:routing-policy/openconfig-routing-policy:policy-definitions/openconfig-routing-policy:policy-definition/openconfig-routing-policy:statements/openconfig-routing-policy:statement/openconfig-routing-policy:actions/openconfig-bgp-policy:bgp-actions/openconfig-bgp-policy:set-ext-community/openconfig-bgp-policy:reference/openconfig-bgp-policy:state/openconfig-bgp-policy:ext-community-set-ref" {
    deviate not-supported;
  }

  deviation "/openconfig-routing-policy:routing-policy/openconfig-routing-policy:policy-definitions/openconfig-routing-policy:policy-definition/openconfig-routing-policy:statements/openconfig-routing-policy:statement/openconfig-routing-policy:actions/openconfig-isis-policy:isis-actions/openconfig-isis-policy:config/openconfig-isis-policy:set-metric-type" {
    deviate not-supported;
  }

  deviation "/openconfig-routing-policy:routing-policy/openconfig-routing-policy:policy-definitions/openconfig-routing-policy:policy-definition/openconfig-routing-policy:statements/openconfig-routing-policy:statement/openconfig-routing-policy:actions/openconfig-isis-policy:isis-actions/openconfig-isis-policy:state/openconfig-isis-policy:set-metric-type" {
    deviate not-supported;
  }

  deviation "/openconfig-routing-policy:routing-policy/openconfig-routing-policy:policy-definitions/openconfig-routing-policy:policy-definition/openconfig-routing-policy:statements/openconfig-routing-policy:statement/openconfig-routing-policy:actions/openconfig-routing-policy:set-tag/openconfig-routing-policy:config/openconfig-routing-policy:mode" {
    deviate not-supported;
  }

  deviation "/openconfig-routing-policy:routing-policy/openconfig-routing-policy:policy-definitions/openconfig-routing-policy:policy-definition/openconfig-routing-policy:statements/openconfig-routing-policy:statement/openconfig-routing-policy:actions/openconfig-routing-policy:set-tag/openconfig-routing-policy:inline" {
    deviate not-supported;
  }

  deviation "/openconfig-routing-policy:routing-policy/openconfig-routing-policy:policy-definitions/openconfig-routing-policy:policy-definition/openconfig-routing-policy:statements/openconfig-routing-policy:statement/openconfig-routing-policy:actions/openconfig-routing-policy:set-tag/openconfig-routing-policy:state/openconfig-routing-policy:mode" {
    deviate not-supported;
  }

  deviation "/openconfig-routing-policy:routing-policy/openconfig-routing-policy:policy-definitions/openconfig-routing-policy:policy-definition/openconfig-routing-policy:statements/openconfig-routing-policy:statement/openconfig-routing-policy:conditions/openconfig-bgp-policy:bgp-conditions/openconfig-bgp-policy:community-count" {
    deviate not-supported;
  }

  deviation "/openconfig-routing-policy:routing-policy/openconfig-routing-policy:policy-definitions/openconfig-routing-policy:policy-definition/openconfig-routing-policy:statements/openconfig-routing-policy:statement/openconfig-routing-policy:conditions/openconfig-bgp-policy:bgp-conditions/openconfig-bgp-policy:config/openconfig-bgp-policy:community-set" {
    deviate not-supported;
  }

  deviation "/openconfig-routing-policy:routing-policy/openconfig-routing-policy:policy-definitions/openconfig-routing-policy:policy-definition/openconfig-routing-policy:statements/openconfig-routing-policy:statement/openconfig-routing-policy:conditions/openconfig-bgp-policy:bgp-conditions/openconfig-bgp-policy:config/openconfig-bgp-policy:ext-community-set" {
    deviate not-supported;
  }

  deviation "/openconfig-routing-policy:routing-policy/openconfig-routing-policy:policy-definitions/openconfig-routing-policy:policy-definition/openconfig-routing-policy:statements/openconfig-routing-policy:statement/openconfig-routing-policy:conditions/openconfig-bgp-policy:bgp-conditions/openconfig-bgp-policy:config/openconfig-bgp-policy:local-pref-eq" {
    deviate not-supported;
  }

  deviation "/openconfig-routing-policy:routing-policy/openconfig-routing-policy:policy-definitions/openconfig-routing-policy:policy-definition/openconfig-routing-policy:statements/openconfig-routing-policy:statement/openconfig-routing-policy:conditions/openconfig-bgp-policy:bgp-conditions/openconfig-bgp-policy:config/openconfig-bgp-policy:med-eq" {
    deviate not-supported;
  }

  deviation "/openconfig-routing-policy:routing-policy/openconfig-routing-policy:policy-definitions/openconfig-routing-policy:policy-definition/openconfig-routing-policy:statements/openconfig-routing-policy:statement/openconfig-routing-policy:conditions/openconfig-bgp-policy:bgp-conditions/openconfig-bgp-policy:config/openconfig-bgp-policy:next-hop-in" {
    deviate not-supported;
  }

  deviation "/openconfig-routing-policy:routing-policy/openconfig-routing-policy:policy-definitions/openconfig-routing-policy:policy-definition/openconfig-routing-policy:statements/openconfig-routing-policy:statement/openconfig-routing-policy:conditions/openconfig-bgp-policy:bgp-conditions/openconfig-bgp-policy:config/openconfig-bgp-policy:origin-eq" {
    deviate not-supported;
  }

  deviation "/openconfig-routing-policy:routing-policy/openconfig-routing-policy:policy-definitions/openconfig-routing-policy:policy-definition/openconfig-routing-policy:statements/openconfig-routing-policy:statement/openconfig-routing-policy:conditions/openconfig-bgp-policy:bgp-conditions/openconfig-bgp-policy:config/openconfig-bgp-policy:route-type" {
    deviate not-supported;
  }

  deviation "/openconfig-routing-policy:routing-policy/openconfig-routing-policy:policy-definitions/openconfig-routing-policy:policy-definition/openconfig-routing-policy:statements/openconfig-routing-policy:statement/openconfig-routing-policy:conditions/openconfig-bgp-policy:bgp-conditions/openconfig-bgp-policy:ext-community-count" {
    deviate not-supported;
  }

  deviation "/openconfig-routing-policy:routing-policy/openconfig-routing-policy:policy-definitions/openconfig-routing-policy:policy-definition/openconfig-routing-policy:statements/openconfig-routing-policy:statement/openconfig-routing-policy:conditions/openconfig-bgp-policy:bgp-conditions/openconfig-bgp-policy:state/openconfig-bgp-policy:community-set" {
    deviate not-supported;
  }

  deviation "/openconfig-routing-policy:routing-policy/openconfig-routing-policy:policy-definitions/openconfig-routing-policy:policy-definition/openconfig-routing-policy:statements/openconfig-routing-policy:statement/openconfig-routing-policy:conditions/openconfig-bgp-policy:bgp-conditions/openconfig-bgp-policy:state/openconfig-bgp-policy:ext-community-set" {
    deviate not-supported;
  }

  deviation "/openconfig-routing-policy:routing-policy/openconfig-routing-policy:policy-definitions/openconfig-routing-policy:policy-definition/openconfig-routing-policy:statements/openconfig-routing-policy:statement/openconfig-routing-policy:conditions/openconfig-bgp-policy:bgp-conditions/openconfig-bgp-policy:state/openconfig-bgp-policy:local-pref-eq" {
    deviate not-supported;
  }

  deviation "/openconfig-routing-policy:routing-policy/openconfig-routing-policy:policy-definitions/openconfig-routing-policy:policy-definition/openconfig-routing-policy:statements/openconfig-routing-policy:statement/openconfig-routing-policy:conditions/openconfig-bgp-policy:bgp-conditions/openconfig-bgp-policy:state/openconfig-bgp-policy:med-eq" {
    deviate not-supported;
  }

  deviation "/openconfig-routing-policy:routing-policy/openconfig-routing-policy:policy-definitions/openconfig-routing-policy:policy-definition/openconfig-routing-policy:statements/openconfig-routing-policy:statement/openconfig-routing-policy:conditions/openconfig-bgp-policy:bgp-conditions/openconfig-bgp-policy:state/openconfig-bgp-policy:next-hop-in" {
    deviate not-supported;
  }

  deviation "/openconfig-routing-policy:routing-policy/openconfig-routing-policy:policy-definitions/openconfig-routing-policy:policy-definition/openconfig-routing-policy:statements/openconfig-routing-policy:statement/openconfig-routing-policy:conditions/openconfig-bgp-policy:bgp-conditions/openconfig-bgp-policy:state/openconfig-bgp-policy:origin-eq" {
    deviate not-supported;
  }

  deviation "/openconfig-routing-policy:routing-policy/openconfig-routing-policy:policy-definitions/openconfig-routing-policy:policy-definition/openconfig-routing-policy:statements/openconfig-routing-policy:statement/openconfig-routing-policy:conditions/openconfig-bgp-policy:bgp-conditions/openconfig-bgp-policy:state/openconfig-bgp-policy:route-type" {
    deviate not-supported;
  }

  deviation "/openconfig-routing-policy:routing-policy/openconfig-routing-policy:policy-definitions/openconfig-routing-policy:policy-definition/openconfig-routing-policy:statements/openconfig-routing-policy:statement/openconfig-routing-policy:conditions/openconfig-routing-policy:match-interface" {
    deviate not-supported;
  }

  deviation "/openconfig-routing-policy:routing-policy/openconfig-routing-policy:policy-definitions/openconfig-routing-policy:policy-definition/openconfig-routing-policy:statements/openconfig-routing-policy:statement/openconfig-routing-policy:conditions/openconfig-routing-policy:match-neighbor-set" {
    deviate not-supported;
  }

  deviation "/openconfig-sampling:sampling/openconfig-sampling-sflow:sflow/openconfig-sampling-sflow:collectors/openconfig-sampling-sflow:collector/openconfig-sampling-sflow:config/openconfig-sampling-sflow:max-datagram-size" {
    deviate not-supported;
  }

  deviation "/openconfig-sampling:sampling/openconfig-sampling-sflow:sflow/openconfig-sampling-sflow:collectors/openconfig-sampling-sflow:collector/openconfig-sampling-sflow:state/openconfig-sampling-sflow:max-datagram-size" {
    deviate not-supported;
  }

  deviation "/openconfig-sampling:sampling/openconfig-sampling-sflow:sflow/openconfig-sampling-sflow:collectors/openconfig-sampling-sflow:collector/openconfig-sampling-sflow:state/openconfig-sampling-sflow:packets-sent" {
    deviate not-supported;
  }

  deviation "/openconfig-sampling:sampling/openconfig-sampling-sflow:sflow/openconfig-sampling-sflow:config/openconfig-sampling-sflow:agent-id-ipv4" {
    deviate not-supported;
  }

  deviation "/openconfig-sampling:sampling/openconfig-sampling-sflow:sflow/openconfig-sampling-sflow:config/openconfig-sampling-sflow:agent-id-ipv6" {
    deviate not-supported;
  }

  deviation "/openconfig-sampling:sampling/openconfig-sampling-sflow:sflow/openconfig-sampling-sflow:config/openconfig-sampling-sflow:polling-interval" {
    deviate not-supported;
  }

  deviation "/openconfig-sampling:sampling/openconfig-sampling-sflow:sflow/openconfig-sampling-sflow:interfaces/openconfig-sampling-sflow:interface/openconfig-sampling-sflow:config/openconfig-sampling-sflow:polling-interval" {
    deviate not-supported;
  }

  deviation "/openconfig-sampling:sampling/openconfig-sampling-sflow:sflow/openconfig-sampling-sflow:interfaces/openconfig-sampling-sflow:interface/openconfig-sampling-sflow:state/openconfig-sampling-sflow:packets-sampled" {
    deviate not-supported;
  }

  deviation "/openconfig-sampling:sampling/openconfig-sampling-sflow:sflow/openconfig-sampling-sflow:interfaces/openconfig-sampling-sflow:interface/openconfig-sampling-sflow:state/openconfig-sampling-sflow:polling-interval" {
    deviate not-supported;
  }

  deviation "/openconfig-sampling:sampling/openconfig-sampling-sflow:sflow/openconfig-sampling-sflow:state/openconfig-sampling-sflow:agent-id-ipv4" {
    deviate not-supported;
  }

  deviation "/openconfig-sampling:sampling/openconfig-sampling-sflow:sflow/openconfig-sampling-sflow:state/openconfig-sampling-sflow:agent-id-ipv6" {
    deviate not-supported;
  }

  deviation "/openconfig-sampling:sampling/openconfig-sampling-sflow:sflow/openconfig-sampling-sflow:state/openconfig-sampling-sflow:polling-interval" {
    deviate not-supported;
  }

  deviation "/openconfig-system:system/openconfig-gnsi-credentialz:console" {
    deviate not-supported;
  }

  deviation "/openconfig-system:system/openconfig-system-bootz:bootz/openconfig-system-bootz:state/openconfig-system-bootz:checksum" {
    deviate not-supported;
  }

  deviation "/openconfig-system:system/openconfig-system-bootz:bootz/openconfig-system-bootz:state/openconfig-system-bootz:error-count" {
    deviate not-supported;
  }

  deviation "/openconfig-system:system/openconfig-system-controlplane:control-plane-traffic/openconfig-system-controlplane:egress" {
    deviate not-supported;
  }

  deviation "/openconfig-system:system/openconfig-system-controlplane:control-plane-traffic/openconfig-system-controlplane:ingress/openconfig-system-controlplane:acl/openconfig-system-controlplane:acl-set/openconfig-system-controlplane:acl-entries" {
    deviate not-supported;
  }

  deviation "/openconfig-system:system/openconfig-system-controlplane:control-plane-traffic/openconfig-system-controlplane:ingress/openconfig-system-controlplane:qos" {
    deviate not-supported;
  }

  deviation "/openconfig-system:system/openconfig-system-grpc:grpc-servers/openconfig-system-grpc:grpc-server/openconfig-gnsi-acctz:acctz" {
    deviate not-supported;
  }

  deviation "/openconfig-system:system/openconfig-system-grpc:grpc-servers/openconfig-system-grpc:grpc-server/openconfig-system-grpc:config/openconfig-system-grpc:transport-security" {
    deviate not-supported;
  }

  deviation "/openconfig-system:system/openconfig-system-grpc:grpc-servers/openconfig-system-grpc:grpc-server/openconfig-system-grpc:connections" {
    deviate not-supported;
  }

  deviation "/openconfig-system:system/openconfig-system-grpc:grpc-servers/openconfig-system-grpc:grpc-server/openconfig-system-grpc:state/openconfig-gnsi-certz:authentication-policy-created-on" {
    deviate not-supported;
  }

  deviation "/openconfig-system:system/openconfig-system-grpc:grpc-servers/openconfig-system-grpc:grpc-server/openconfig-system-grpc:state/openconfig-gnsi-certz:authentication-policy-version" {
    deviate not-supported;
  }

  deviation "/openconfig-system:system/openconfig-system-grpc:grpc-servers/openconfig-system-grpc:grpc-server/openconfig-system-grpc:state/openconfig-system-grpc:transport-security" {
    deviate not-supported;
  }

  deviation "/openconfig-system:system/openconfig-system-utilization:utilization/openconfig-system-utilization:resources/openconfig-system-utilization:resource/openconfig-system-utilization:state/openconfig-system-utilization:active-component-list" {
    deviate not-supported;
  }

  deviation "/openconfig-system:system/openconfig-system:aaa/openconfig-system:accounting/openconfig-gnsi-acctz:acctz" {
    deviate not-supported;
  }

  deviation "/openconfig-system:system/openconfig-system:aaa/openconfig-system:authentication/openconfig-system:admin-user/openconfig-system:config/openconfig-system:admin-password-hashed" {
    deviate not-supported;
  }

  deviation "/openconfig-system:system/openconfig-system:aaa/openconfig-system:authentication/openconfig-system:admin-user/openconfig-system:state/openconfig-system:admin-password-hashed" {
    deviate not-supported;
  }

  deviation "/openconfig-system:system/openconfig-system:aaa/openconfig-system:authentication/openconfig-system:users/openconfig-system:user/openconfig-system:config/openconfig-system:password" {
    deviate not-supported;
  }

  deviation "/openconfig-system:system/openconfig-system:aaa/openconfig-system:authentication/openconfig-system:users/openconfig-system:user/openconfig-system:config/openconfig-system:password-hashed" {
    deviate not-supported;
  }

  deviation "/openconfig-system:system/openconfig-system:aaa/openconfig-system:authentication/openconfig-system:users/openconfig-system:user/openconfig-system:config/openconfig-system:ssh-key" {
    deviate not-supported;
  }

  deviation "/openconfig-system:system/openconfig-system:aaa/openconfig-system:authentication/openconfig-system:users/openconfig-system:user/openconfig-system:state/openconfig-system:password-hashed" {
    deviate not-supported;
  }

  deviation "/openconfig-system:system/openconfig-system:aaa/openconfig-system:authentication/openconfig-system:users/openconfig-system:user/openconfig-system:state/openconfig-system:ssh-key" {
    deviate not-supported;
  }

  deviation "/openconfig-system:system/openconfig-system:aaa/openconfig-system:authorization/openconfig-system:config/openconfig-system:authorization-method" {
    deviate not-supported;
  }

  deviation "/openconfig-system:system/openconfig-system:aaa/openconfig-system:authorization/openconfig-system:events" {
    deviate not-supported;
  }

  deviation "/openconfig-system:system/openconfig-system:aaa/openconfig-system:authorization/openconfig-system:state/openconfig-system:authorization-method" {
    deviate not-supported;
  }

  deviation "/openconfig-system:system/openconfig-system:aaa/openconfig-system:server-groups/openconfig-system:server-group/openconfig-system:servers/openconfig-system:server/openconfig-system:radius" {
    deviate not-supported;
  }

  deviation "/openconfig-system:system/openconfig-system:aaa/openconfig-system:server-groups/openconfig-system:server-group/openconfig-system:servers/openconfig-system:server/openconfig-system:state/openconfig-system:connection-aborts" {
    deviate not-supported;
  }

  deviation "/openconfig-system:system/openconfig-system:aaa/openconfig-system:server-groups/openconfig-system:server-group/openconfig-system:servers/openconfig-system:server/openconfig-system:state/openconfig-system:connection-closes" {
    deviate not-supported;
  }

  deviation "/openconfig-system:system/openconfig-system:aaa/openconfig-system:server-groups/openconfig-system:server-group/openconfig-system:servers/openconfig-system:server/openconfig-system:state/openconfig-system:connection-failures" {
    deviate not-supported;
  }

  deviation "/openconfig-system:system/openconfig-system:aaa/openconfig-system:server-groups/openconfig-system:server-group/openconfig-system:servers/openconfig-system:server/openconfig-system:state/openconfig-system:connection-opens" {
    deviate not-supported;
  }

  deviation "/openconfig-system:system/openconfig-system:aaa/openconfig-system:server-groups/openconfig-system:server-group/openconfig-system:servers/openconfig-system:server/openconfig-system:state/openconfig-system:connection-timeouts" {
    deviate not-supported;
  }

  deviation "/openconfig-system:system/openconfig-system:aaa/openconfig-system:server-groups/openconfig-system:server-group/openconfig-system:servers/openconfig-system:server/openconfig-system:state/openconfig-system:errors-received" {
    deviate not-supported;
  }

  deviation "/openconfig-system:system/openconfig-system:aaa/openconfig-system:server-groups/openconfig-system:server-group/openconfig-system:servers/openconfig-system:server/openconfig-system:state/openconfig-system:messages-received" {
    deviate not-supported;
  }

  deviation "/openconfig-system:system/openconfig-system:aaa/openconfig-system:server-groups/openconfig-system:server-group/openconfig-system:servers/openconfig-system:server/openconfig-system:state/openconfig-system:messages-sent" {
    deviate not-supported;
  }

  deviation "/openconfig-system:system/openconfig-system:aaa/openconfig-system:server-groups/openconfig-system:server-group/openconfig-system:servers/openconfig-system:server/openconfig-system:tacacs/openconfig-system:config/openconfig-system:secret-key-hashed" {
    deviate not-supported;
  }

  deviation "/openconfig-system:system/openconfig-system:aaa/openconfig-system:server-groups/openconfig-system:server-group/openconfig-system:servers/openconfig-system:server/openconfig-system:tacacs/openconfig-system:state/openconfig-system:secret-key-hashed" {
    deviate not-supported;
  }

  deviation "/openconfig-system:system/openconfig-system:alarms/openconfig-system:alarm/openconfig-system:config" {
    deviate not-supported;
  }

  deviation "/openconfig-system:system/openconfig-system:cpus/openconfig-system:cpu/openconfig-system:state/openconfig-system:hardware-interrupt/openconfig-system:max" {
    deviate not-supported;
  }

  deviation "/openconfig-system:system/openconfig-system:cpus/openconfig-system:cpu/openconfig-system:state/openconfig-system:hardware-interrupt/openconfig-system:max-time" {
    deviate not-supported;
  }

  deviation "/openconfig-system:system/openconfig-system:cpus/openconfig-system:cpu/openconfig-system:state/openconfig-system:hardware-interrupt/openconfig-system:min" {
    deviate not-supported;
  }

  deviation "/openconfig-system:system/openconfig-system:cpus/openconfig-system:cpu/openconfig-system:state/openconfig-system:hardware-interrupt/openconfig-system:min-time" {
    deviate not-supported;
  }

  deviation "/openconfig-system:system/openconfig-system:cpus/openconfig-system:cpu/openconfig-system:state/openconfig-system:idle/openconfig-system:max" {
    deviate not-supported;
  }

  deviation "/openconfig-system:system/openconfig-system:cpus/openconfig-system:cpu/openconfig-system:state/openconfig-system:idle/openconfig-system:max-time" {
    deviate not-supported;
  }

  deviation "/openconfig-system:system/openconfig-system:cpus/openconfig-system:cpu/openconfig-system:state/openconfig-system:idle/openconfig-system:min" {
    deviate not-supported;
  }

  deviation "/openconfig-system:system/openconfig-system:cpus/openconfig-system:cpu/openconfig-system:state/openconfig-system:idle/openconfig-system:min-time" {
    deviate not-supported;
  }

  deviation "/openconfig-system:system/openconfig-system:cpus/openconfig-system:cpu/openconfig-system:state/openconfig-system:kernel/openconfig-system:max" {
    deviate not-supported;
  }

  deviation "/openconfig-system:system/openconfig-system:cpus/openconfig-system:cpu/openconfig-system:state/openconfig-system:kernel/openconfig-system:max-time" {
    deviate not-supported;
  }

  deviation "/openconfig-system:system/openconfig-system:cpus/openconfig-system:cpu/openconfig-system:state/openconfig-system:kernel/openconfig-system:min" {
    deviate not-supported;
  }

  deviation "/openconfig-system:system/openconfig-system:cpus/openconfig-system:cpu/openconfig-system:state/openconfig-system:kernel/openconfig-system:min-time" {
    deviate not-supported;
  }

  deviation "/openconfig-system:system/openconfig-system:cpus/openconfig-system:cpu/openconfig-system:state/openconfig-system:nice/openconfig-system:max" {
    deviate not-supported;
  }

  deviation "/openconfig-system:system/openconfig-system:cpus/openconfig-system:cpu/openconfig-system:state/openconfig-system:nice/openconfig-system:max-time" {
    deviate not-supported;
  }

  deviation "/openconfig-system:system/openconfig-system:cpus/openconfig-system:cpu/openconfig-system:state/openconfig-system:nice/openconfig-system:min" {
    deviate not-supported;
  }

  deviation "/openconfig-system:system/openconfig-system:cpus/openconfig-system:cpu/openconfig-system:state/openconfig-system:nice/openconfig-system:min-time" {
    deviate not-supported;
  }

  deviation "/openconfig-system:system/openconfig-system:cpus/openconfig-system:cpu/openconfig-system:state/openconfig-system:software-interrupt/openconfig-system:max" {
    deviate not-supported;
  }

  deviation "/openconfig-system:system/openconfig-system:cpus/openconfig-system:cpu/openconfig-system:state/openconfig-system:software-interrupt/openconfig-system:max-time" {
    deviate not-supported;
  }

  deviation "/openconfig-system:system/openconfig-system:cpus/openconfig-system:cpu/openconfig-system:state/openconfig-system:software-interrupt/openconfig-system:min" {
    deviate not-supported;
  }

  deviation "/openconfig-system:system/openconfig-system:cpus/openconfig-system:cpu/openconfig-system:state/openconfig-system:software-interrupt/openconfig-system:min-time" {
    deviate not-supported;
  }

  deviation "/openconfig-system:system/openconfig-system:cpus/openconfig-system:cpu/openconfig-system:state/openconfig-system:total/openconfig-system:max" {
    deviate not-supported;
  }

  deviation "/openconfig-system:system/openconfig-system:cpus/openconfig-system:cpu/openconfig-system:state/openconfig-system:total/openconfig-system:max-time" {
    deviate not-supported;
  }

  deviation "/openconfig-system:system/openconfig-system:cpus/openconfig-system:cpu/openconfig-system:state/openconfig-system:total/openconfig-system:min" {
    deviate not-supported;
  }

  deviation "/openconfig-system:system/openconfig-system:cpus/openconfig-system:cpu/openconfig-system:state/openconfig-system:total/openconfig-system:min-time" {
    deviate not-supported;
  }

  deviation "/openconfig-system:system/openconfig-system:cpus/openconfig-system:cpu/openconfig-system:state/openconfig-system:user/openconfig-system:max" {
    deviate not-supported;
  }

  deviation "/openconfig-system:system/openconfig-system:cpus/openconfig-system:cpu/openconfig-system:state/openconfig-system:user/openconfig-system:max-time" {
    deviate not-supported;
  }

  deviation "/openconfig-system:system/openconfig-system:cpus/openconfig-system:cpu/openconfig-system:state/openconfig-system:user/openconfig-system:min" {
    deviate not-supported;
  }

  deviation "/openconfig-system:system/openconfig-system:cpus/openconfig-system:cpu/openconfig-system:state/openconfig-system:user/openconfig-system:min-time" {
    deviate not-supported;
  }

  deviation "/openconfig-system:system/openconfig-system:cpus/openconfig-system:cpu/openconfig-system:state/openconfig-system:wait/openconfig-system:max" {
    deviate not-supported;
  }

  deviation "/openconfig-system:system/openconfig-system:cpus/openconfig-system:cpu/openconfig-system:state/openconfig-system:wait/openconfig-system:max-time" {
    deviate not-supported;
  }

  deviation "/openconfig-system:system/openconfig-system:cpus/openconfig-system:cpu/openconfig-system:state/openconfig-system:wait/openconfig-system:min" {
    deviate not-supported;
  }

  deviation "/openconfig-system:system/openconfig-system:cpus/openconfig-system:cpu/openconfig-system:state/openconfig-system:wait/openconfig-system:min-time" {
    deviate not-supported;
  }

  deviation "/openconfig-system:system/openconfig-system:dns/openconfig-system:host-entries/openconfig-system:host-entry/openconfig-system:config/openconfig-system:alias" {
    deviate not-supported;
  }

  deviation "/openconfig-system:system/openconfig-system:dns/openconfig-system:host-entries/openconfig-system:host-entry/openconfig-system:state/openconfig-system:alias" {
    deviate not-supported;
  }

  deviation "/openconfig-system:system/openconfig-system:dns/openconfig-system:servers/openconfig-system:server/openconfig-system:config/openconfig-system:port" {
    deviate not-supported;
  }

  deviation "/openconfig-system:system/openconfig-system:dns/openconfig-system:servers/openconfig-system:server/openconfig-system:state/openconfig-system:port" {
    deviate not-supported;
  }

  deviation "/openconfig-system:system/openconfig-system:license" {
    deviate not-supported;
  }

  deviation "/openconfig-system:system/openconfig-system:logging/openconfig-system:files" {
    deviate not-supported;
  }

  deviation "/openconfig-system:system/openconfig-system:logging/openconfig-system:remote-servers/openconfig-system:remote-server/openconfig-system:config/openconfig-system:tls-profile-id" {
    deviate not-supported;
  }

  deviation "/openconfig-system:system/openconfig-system:logging/openconfig-system:remote-servers/openconfig-system:remote-server/openconfig-system:config/openconfig-system:transport-security" {
    deviate not-supported;
  }

  deviation "/openconfig-system:system/openconfig-system:logging/openconfig-system:remote-servers/openconfig-system:remote-server/openconfig-system:state/openconfig-system:tls-profile-id" {
    deviate not-supported;
  }

  deviation "/openconfig-system:system/openconfig-system:logging/openconfig-system:remote-servers/openconfig-system:remote-server/openconfig-system:state/openconfig-system:transport-security" {
    deviate not-supported;
  }

  deviation "/openconfig-system:system/openconfig-system:logging/openconfig-system:vty" {
    deviate not-supported;
  }

  deviation "/openconfig-system:system/openconfig-system:memory/openconfig-system:state/openconfig-system:counters" {
    deviate not-supported;
  }

  deviation "/openconfig-system:system/openconfig-system:memory/openconfig-system:state/openconfig-system:free" {
    deviate not-supported;
  }

  deviation "/openconfig-system:system/openconfig-system:memory/openconfig-system:state/openconfig-system:used" {
    deviate not-supported;
  }

  deviation "/openconfig-system:system/openconfig-system:messages" {
    deviate not-supported;
  }

  deviation "/openconfig-system:system/openconfig-system:mount-points/openconfig-system:mount-point/openconfig-system:state/openconfig-system:type" {
    deviate not-supported;
  }

  deviation "/openconfig-system:system/openconfig-system:ntp/openconfig-system:config/openconfig-system:enable-ntp-auth" {
    deviate not-supported;
  }

  deviation "/openconfig-system:system/openconfig-system:ntp/openconfig-system:servers/openconfig-system:server/openconfig-system:config/openconfig-system:association-type" {
    deviate not-supported;
  }

  deviation "/openconfig-system:system/openconfig-system:ntp/openconfig-system:servers/openconfig-system:server/openconfig-system:config/openconfig-system:port" {
    deviate not-supported;
  }

  deviation "/openconfig-system:system/openconfig-system:ntp/openconfig-system:servers/openconfig-system:server/openconfig-system:config/openconfig-system:version" {
    deviate not-supported;
  }

  deviation "/openconfig-system:system/openconfig-system:ntp/openconfig-system:servers/openconfig-system:server/openconfig-system:state/openconfig-system:association-type" {
    deviate not-supported;
  }

  deviation "/openconfig-system:system/openconfig-system:ntp/openconfig-system:servers/openconfig-system:server/openconfig-system:state/openconfig-system:port" {
    deviate not-supported;
  }

  deviation "/openconfig-system:system/openconfig-system:ntp/openconfig-system:servers/openconfig-system:server/openconfig-system:state/openconfig-system:version" {
    deviate not-supported;
  }

  deviation "/openconfig-system:system/openconfig-system:ntp/openconfig-system:state/openconfig-system:auth-mismatch" {
    deviate not-supported;
  }

  deviation "/openconfig-system:system/openconfig-system:ntp/openconfig-system:state/openconfig-system:enable-ntp-auth" {
    deviate not-supported;
  }

  deviation "/openconfig-system:system/openconfig-system:processes/openconfig-system:process/openconfig-system:state/openconfig-system:cpu-usage-system" {
    deviate not-supported;
  }

  deviation "/openconfig-system:system/openconfig-system:processes/openconfig-system:process/openconfig-system:state/openconfig-system:cpu-usage-user" {
    deviate not-supported;
  }

  deviation "/openconfig-system:system/openconfig-system:ssh-server/openconfig-system:config/openconfig-system:protocol-version" {
    deviate not-supported;
  }

  deviation "/openconfig-system:system/openconfig-system:ssh-server/openconfig-system:config/openconfig-system:session-limit" {
    deviate not-supported;
  }

  deviation "/openconfig-system:system/openconfig-system:ssh-server/openconfig-system:state/openconfig-system:session-limit" {
    deviate not-supported;
  }

  deviation "/openconfig-system:system/openconfig-system:telnet-server" {
    deviate not-supported;
  }

  deviation "/openconfig-terminal-device:terminal-device/openconfig-terminal-device:config" {
    deviate not-supported;
  }

  deviation "/openconfig-terminal-device:terminal-device/openconfig-terminal-device:logical-channels/openconfig-terminal-device:channel/openconfig-terminal-device:config/openconfig-terminal-device:client-mapping-mode" {
    deviate not-supported;
  }

  deviation "/openconfig-terminal-device:terminal-device/openconfig-terminal-device:logical-channels/openconfig-terminal-device:channel/openconfig-terminal-device:config/openconfig-terminal-device:test-signal" {
    deviate not-supported;
  }

  deviation "/openconfig-terminal-device:terminal-device/openconfig-terminal-device:logical-channels/openconfig-terminal-device:channel/openconfig-terminal-device:ethernet" {
    deviate not-supported;
  }

  deviation "/openconfig-terminal-device:terminal-device/openconfig-terminal-device:logical-channels/openconfig-terminal-device:channel/openconfig-terminal-device:ingress/openconfig-terminal-device:config/openconfig-terminal-device:physical-channel" {
    deviate not-supported;
  }

  deviation "/openconfig-terminal-device:terminal-device/openconfig-terminal-device:logical-channels/openconfig-terminal-device:channel/openconfig-terminal-device:ingress/openconfig-terminal-device:state/openconfig-terminal-device:physical-channel" {
    deviate not-supported;
  }

  deviation "/openconfig-terminal-device:terminal-device/openconfig-terminal-device:logical-channels/openconfig-terminal-device:channel/openconfig-terminal-device:logical-channel-assignments/openconfig-terminal-device:assignment/openconfig-terminal-device:config/openconfig-terminal-device:mapping" {
    deviate not-supported;
  }

  deviation "/openconfig-terminal-device:terminal-device/openconfig-terminal-device:logical-channels/openconfig-terminal-device:channel/openconfig-terminal-device:logical-channel-assignments/openconfig-terminal-device:assignment/openconfig-terminal-device:config/openconfig-terminal-device:tributary-slot-index" {
    deviate not-supported;
  }

  deviation "/openconfig-terminal-device:terminal-device/openconfig-terminal-device:logical-channels/openconfig-terminal-device:channel/openconfig-terminal-device:logical-channel-assignments/openconfig-terminal-device:assignment/openconfig-terminal-device:state/openconfig-terminal-device:mapping" {
    deviate not-supported;
  }

  deviation "/openconfig-terminal-device:terminal-device/openconfig-terminal-device:logical-channels/openconfig-terminal-device:channel/openconfig-terminal-device:logical-channel-assignments/openconfig-terminal-device:assignment/openconfig-terminal-device:state/openconfig-terminal-device:tributary-slot-index" {
    deviate not-supported;
  }

  deviation "/openconfig-terminal-device:terminal-device/openconfig-terminal-device:logical-channels/openconfig-terminal-device:channel/openconfig-terminal-device:otn/openconfig-terminal-device:config" {
    deviate not-supported;
  }

  deviation "/openconfig-terminal-device:terminal-device/openconfig-terminal-device:logical-channels/openconfig-terminal-device:channel/openconfig-terminal-device:otn/openconfig-terminal-device:state/openconfig-terminal-device:background-block-errors" {
    deviate not-supported;
  }

  deviation "/openconfig-terminal-device:terminal-device/openconfig-terminal-device:logical-channels/openconfig-terminal-device:channel/openconfig-terminal-device:otn/openconfig-terminal-device:state/openconfig-terminal-device:code-violations" {
    deviate not-supported;
  }

  deviation "/openconfig-terminal-device:terminal-device/openconfig-terminal-device:logical-channels/openconfig-terminal-device:channel/openconfig-terminal-device:otn/openconfig-terminal-device:state/openconfig-terminal-device:errored-blocks" {
    deviate not-supported;
  }

  deviation "/openconfig-terminal-device:terminal-device/openconfig-terminal-device:logical-channels/openconfig-terminal-device:channel/openconfig-terminal-device:otn/openconfig-terminal-device:state/openconfig-terminal-device:errored-seconds" {
    deviate not-supported;
  }

  deviation "/openconfig-terminal-device:terminal-device/openconfig-terminal-device:logical-channels/openconfig-terminal-device:channel/openconfig-terminal-device:otn/openconfig-terminal-device:state/openconfig-terminal-device:esnr/openconfig-terminal-device:interval" {
    deviate not-supported;
  }

  deviation "/openconfig-terminal-device:terminal-device/openconfig-terminal-device:logical-channels/openconfig-terminal-device:channel/openconfig-terminal-device:otn/openconfig-terminal-device:state/openconfig-terminal-device:esnr/openconfig-terminal-device:max-time" {
    deviate not-supported;
  }

  deviation "/openconfig-terminal-device:terminal-device/openconfig-terminal-device:logical-channels/openconfig-terminal-device:channel/openconfig-terminal-device:otn/openconfig-terminal-device:state/openconfig-terminal-device:esnr/openconfig-terminal-device:min-time" {
    deviate not-supported;
  }

  deviation "/openconfig-terminal-device:terminal-device/openconfig-terminal-device:logical-channels/openconfig-terminal-device:channel/openconfig-terminal-device:otn/openconfig-terminal-device:state/openconfig-terminal-device:fec-corrected-bits" {
    deviate not-supported;
  }

  deviation "/openconfig-terminal-device:terminal-device/openconfig-terminal-device:logical-channels/openconfig-terminal-device:channel/openconfig-terminal-device:otn/openconfig-terminal-device:state/openconfig-terminal-device:fec-corrected-bytes" {
    deviate not-supported;
  }

  deviation "/openconfig-terminal-device:terminal-device/openconfig-terminal-device:logical-channels/openconfig-terminal-device:channel/openconfig-terminal-device:otn/openconfig-terminal-device:state/openconfig-terminal-device:fec-uncorrectable-words" {
    deviate not-supported;
  }

  deviation "/openconfig-terminal-device:terminal-device/openconfig-terminal-device:logical-channels/openconfig-terminal-device:channel/openconfig-terminal-device:otn/openconfig-terminal-device:state/openconfig-terminal-device:post-fec-ber" {
    deviate not-supported;
  }

  deviation "/openconfig-terminal-device:terminal-device/openconfig-terminal-device:logical-channels/openconfig-terminal-device:channel/openconfig-terminal-device:otn/openconfig-terminal-device:state/openconfig-terminal-device:pre-fec-ber/openconfig-terminal-device:interval" {
    deviate not-supported;
  }

  deviation "/openconfig-terminal-device:terminal-device/openconfig-terminal-device:logical-channels/openconfig-terminal-device:channel/openconfig-terminal-device:otn/openconfig-terminal-device:state/openconfig-terminal-device:pre-fec-ber/openconfig-terminal-device:max-time" {
    deviate not-supported;
  }

  deviation "/openconfig-terminal-device:terminal-device/openconfig-terminal-device:logical-channels/openconfig-terminal-device:channel/openconfig-terminal-device:otn/openconfig-terminal-device:state/openconfig-terminal-device:pre-fec-ber/openconfig-terminal-device:min-time" {
    deviate not-supported;
  }

  deviation "/openconfig-terminal-device:terminal-device/openconfig-terminal-device:logical-channels/openconfig-terminal-device:channel/openconfig-terminal-device:otn/openconfig-terminal-device:state/openconfig-terminal-device:q-value/openconfig-terminal-device:interval" {
    deviate not-supported;
  }

  deviation "/openconfig-terminal-device:terminal-device/openconfig-terminal-device:logical-channels/openconfig-terminal-device:channel/openconfig-terminal-device:otn/openconfig-terminal-device:state/openconfig-terminal-device:q-value/openconfig-terminal-device:max-time" {
    deviate not-supported;
  }

  deviation "/openconfig-terminal-device:terminal-device/openconfig-terminal-device:logical-channels/openconfig-terminal-device:channel/openconfig-terminal-device:otn/openconfig-terminal-device:state/openconfig-terminal-device:q-value/openconfig-terminal-device:min-time" {
    deviate not-supported;
  }

  deviation "/openconfig-terminal-device:terminal-device/openconfig-terminal-device:logical-channels/openconfig-terminal-device:channel/openconfig-terminal-device:otn/openconfig-terminal-device:state/openconfig-terminal-device:rdi-msg" {
    deviate not-supported;
  }

  deviation "/openconfig-terminal-device:terminal-device/openconfig-terminal-device:logical-channels/openconfig-terminal-device:channel/openconfig-terminal-device:otn/openconfig-terminal-device:state/openconfig-terminal-device:severely-errored-seconds" {
    deviate not-supported;
  }

  deviation "/openconfig-terminal-device:terminal-device/openconfig-terminal-device:logical-channels/openconfig-terminal-device:channel/openconfig-terminal-device:otn/openconfig-terminal-device:state/openconfig-terminal-device:tributary-slot-granularity" {
    deviate not-supported;
  }

  deviation "/openconfig-terminal-device:terminal-device/openconfig-terminal-device:logical-channels/openconfig-terminal-device:channel/openconfig-terminal-device:otn/openconfig-terminal-device:state/openconfig-terminal-device:tti-msg-auto" {
    deviate not-supported;
  }

  deviation "/openconfig-terminal-device:terminal-device/openconfig-terminal-device:logical-channels/openconfig-terminal-device:channel/openconfig-terminal-device:otn/openconfig-terminal-device:state/openconfig-terminal-device:tti-msg-expected" {
    deviate not-supported;
  }

  deviation "/openconfig-terminal-device:terminal-device/openconfig-terminal-device:logical-channels/openconfig-terminal-device:channel/openconfig-terminal-device:otn/openconfig-terminal-device:state/openconfig-terminal-device:tti-msg-recv" {
    deviate not-supported;
  }

  deviation "/openconfig-terminal-device:terminal-device/openconfig-terminal-device:logical-channels/openconfig-terminal-device:channel/openconfig-terminal-device:otn/openconfig-terminal-device:state/openconfig-terminal-device:tti-msg-transmit" {
    deviate not-supported;
  }

  deviation "/openconfig-terminal-device:terminal-device/openconfig-terminal-device:logical-channels/openconfig-terminal-device:channel/openconfig-terminal-device:otn/openconfig-terminal-device:state/openconfig-terminal-device:unavailable-seconds" {
    deviate not-supported;
  }

  deviation "/openconfig-terminal-device:terminal-device/openconfig-terminal-device:logical-channels/openconfig-terminal-device:channel/openconfig-terminal-device:state/openconfig-terminal-device:client-mapping-mode" {
    deviate not-supported;
  }

  deviation "/openconfig-terminal-device:terminal-device/openconfig-terminal-device:logical-channels/openconfig-terminal-device:channel/openconfig-terminal-device:state/openconfig-terminal-device:link-state" {
    deviate not-supported;
  }

  deviation "/openconfig-terminal-device:terminal-device/openconfig-terminal-device:logical-channels/openconfig-terminal-device:channel/openconfig-terminal-device:state/openconfig-terminal-device:test-signal" {
    deviate not-supported;
  }

  deviation "/openconfig-terminal-device:terminal-device/openconfig-terminal-device:operational-modes" {
    deviate not-supported;
  }

  deviation "/openconfig-terminal-device:terminal-device/openconfig-terminal-device:state" {
    deviate not-supported;
  }
}
