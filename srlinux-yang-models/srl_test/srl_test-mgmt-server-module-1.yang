module srl_test-mgmt-server-module-1 {
    yang-version 1.1;
    namespace "uri:srl_test/mgmt-server-module-1";
    prefix "srl_test-mgmt-server-module-1";
    list node1 {
        key "key-1 key-2";
        leaf key-1 { type uint64; }
        leaf key-2 { type uint64; }
        leaf leaf-1 { type string; }
        container cont {
            presence "presence container";
            leaf leaf-2 { type string; }
            leaf leaf-3 { type string; config false; }
            container cont2 {
                presence "presence container";
                leaf leaf-4 { type string; }
            }
            container cont3 {
                presence "presence container";
                leaf leaf-4 { type string; }
            }
        }
        list sub-node {
            key "skey-1";
            leaf skey-1 { type uint64; }
            leaf sleaf-1 { type string; }
            leaf sleaf-2 { type string; }
            leaf ileaf-3 { type uint32; }
        }
    }

    list node2 {
        key "key-1";
        leaf key-1 { type string; }
        leaf leaf-1 { type string; }
    }
}
