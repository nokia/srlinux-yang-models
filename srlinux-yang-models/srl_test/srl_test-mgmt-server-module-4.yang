module srl_test-mgmt-server-module-4 {
    yang-version 1.1;
    namespace "uri:srl_test/mgmt-server-module-4";
    prefix "srl_test-mgmt-server-module-4";
    list manufacturer {
        key "company";
        leaf company { type string; }

        leaf slogan { type string; }
        container company-info {
            presence "presence container";
            leaf country { type string; }
            container finance {
                presence "presence container";
            }
            container hr {
                presence "presence container";
            }
            container it {
                presence "presence container";
            }
        }

        container dealerships {
            presence "presence container";
        }

        list vehicles {
            key "model";
            leaf model { type string; }
            leaf top-speed { type uint64; }
        }
    }
}
