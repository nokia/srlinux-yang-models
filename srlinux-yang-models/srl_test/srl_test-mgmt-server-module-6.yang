module srl_test-mgmt-server-module-6 {
    yang-version 1.1;
    namespace "uri:srl_test/mgmt-server-module-6";
    prefix "srl_test-mgmt-server-module-6";

    import srl_test-mgmt-server-module-4 { prefix module-4; }
    import srl_test-mgmt-server-module-5 { prefix module-5; }

    grouping employee-sub-config
    {
        list children {
            key "name";
            leaf name { type string; }
        }
    }

    augment "/module-4:manufacturer/module-5:employees" {
        uses employee-sub-config;
    }
}
