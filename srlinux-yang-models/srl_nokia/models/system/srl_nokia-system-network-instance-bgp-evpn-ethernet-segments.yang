module srl_nokia-system-network-instance-bgp-evpn-ethernet-segments {
  yang-version 1.1;
  namespace "urn:nokia.com:srlinux:evpn:system-network-instance-bgp-evpn-ethernet-segments";
  prefix srl_nokia-system-bgp-evpn-ethernet-segments;

  import srl_nokia-system-network-instance-bgp-vpn {
    prefix srl_nokia-system-bgp-vpn;
  }
  import srl_nokia-common {
    prefix srl_nokia-comm;
  }
  import srl_nokia-extensions {
    prefix srl_nokia-ext;
  }
  import srl_nokia-interfaces {
    prefix srl_nokia-if;
  }
  import srl_nokia-rib-bgp {
    prefix srl_nokia-rib-bgp-routes;
  }
  import srl_nokia-system {
    prefix srl_nokia-system;
  }
  import srl_nokia-system-network-instance {
    prefix srl_nokia-system-network-instance;
  }
  import srl_nokia-features {
    prefix srl_nokia-feat;
  }
  import srl_nokia-routing-policy {
    prefix srl_nokia-routing-pol;
  }
  import srl_nokia-network-instance {
    prefix srl_nokia-netinst;
  }
  import srl_nokia-bgp-vpn {
    prefix srl_bgp-vpn;
  }

  organization
    "Nokia";
  contact
    "Nokia SR Linux Support
     Web: <http://www.nokia.com>";
  description
    "This yang file models configuration and state of the bgp-evpn ethernet segments.";

  revision 2026-07-31 {
    description
      "SRLinux 26.7.1";
  }
  revision 2026-03-31 {
    description
      "SRLinux 26.3.1";
  }
  revision 2025-10-31 {
    description
      "SRLinux 25.10.1";
  }
  revision 2025-07-31 {
    description
      "SRLinux 25.7.1";
  }
  revision 2025-03-31 {
    description
      "SRLinux 25.3.1";
  }
  revision 2024-07-31 {
    description
      "SRLinux 24.7.1";
  }
  revision 2023-10-31 {
    description
      "SRLinux 23.10.1";
  }
  revision 2023-03-31 {
    description
      "SRLinux 23.3.1";
  }
  revision 2022-11-30 {
    description
      "SRLinux 22.11.1";
  }
  revision 2022-03-31 {
    description
      "SRLinux 22.3.1";
  }
  revision 2021-06-30 {
    description
      "SRLinux 21.6.1";
  }
  revision 2021-03-31 {
    description
      "SRLinux 21.3.1";
  }

  typedef multi-homing-mode {
    type enumeration {
      enum all-active;
      enum single-active;
    }
    description
      "Multi-homing mode of an ethernet segment";
  }

  typedef df-algorithm-type {
    type enumeration {
      enum default;
      enum preference;
      enum manual;
    }
    description
      "Designated Forwarder algorithm type.
        Type 0 or default refers to the modulo based algorithm described in RFC8584.
        Type 2 or preference based refers to the algorithm described in draft-ietf-bess-evpn-pref-df.
        Manual refers to the configuration of the evi range for which the node is considered Designated Forwarder.";
  }

  typedef es-type {
    type enumeration {
      enum none;
      enum virtual {
        if-feature "srl_nokia-feat:evpn-mh-virtual-es";
      }
    }
    description
      "Ethernet Segment association type.

       Type none is the RFC7432 compliant Ethernet Segment, associated to an interface.
       Type virtual is described in draft-ietf-bess-evpn-virtual-eth-segment and associates the ES to
       an interface and VLANs or VLAN-ranges. It is also used for the association to other virtual interfaces
       such as Layer-3 CE next-hops (as described in draft-sajassi-bess-evpn-ip-aliasing) in the context of
       an IP-VRF network-instance.";
  }

  grouping anycast-eth-segments {
    description
      "Grouping containing the configuration of anycast ethernet segments";
    container anycast-multi-homing {
      if-feature "srl_nokia-feat:evpn-mh-anycast";
      presence "Enables the configuration of anycast ethernet segments";
      must "../multi-homing-mode = 'all-active'" {
        error-message "Anycast-multi-homing is only supported when multi-homing-mode is all-active";
      }
      must "../type = 'none'" {
        srl_nokia-ext:if-feature "not srl_nokia-feat:evpn-anycast-l3-subnet";
        error-message "Anycast-multi-homing is only supported when ethernet segment type is none";
      }
      description
        "Configuration of anycast ethernet segments";
      leaf ip-address {
        type union {
          type srl_nokia-comm:ipv4-address-excluding-all-zero;
        }
        description
          "The anycast IP address of the anycast ethernet segment";
      }
    }
  }

  grouping route-internal-tags {
    description
      "Grouping containing the configuration of internal tags";
    container internal-tags {
      if-feature "srl_nokia-feat:internal-tags";
      description
        "Enter the internal-tags context

         Configuration and state of internal tags";
      leaf-list set-tag-set {
        max-elements 1;
        type leafref {
          path "/srl_nokia-routing-pol:routing-policy/srl_nokia-routing-pol:tag-set/srl_nokia-routing-pol:name";
        }
        description
          "Reference to a tag-set defined under routing-policy";
      }
    }
  }

  grouping ifl-host-ip-aliasing {
    description
      "Grouping containing the configuration of evpn-ifl-host ip aliasing";
    container advertise-ifl-host-ad-routes {
      if-feature "srl_nokia-feat:evpn-ifl-host-ip-aliasing";
      presence "Configuration of evpn-ifl-host ip aliasing";
      description
        "Enables the advertisement of IP AD per EVI/ES routes for IP Aliasing

         When configured, AD per-EVI/ES routes are advertised for the IP-VRF and bgp-evpn instances with MAC-VRFs
         attached to the Ethernet Segment. The AD per-EVI routes for the IP-VRFs contain the route distinguisher,
         route targets and label/VNI of the IP-VRF bgp-evpn instance (with the instance indicated in the
         bgp-evpn-instance command). The AD per-ES routes for the IP-VRFs contain the route distinguisher and
         route targets of the IP-VRF bgp-evpn-instance. On the remote PEs, the reception of BGP-EVPN-IFL-HOST routes
         with an ESI matching the ESI of the IP-VRF AD per-EVI/ES routes, will enable the IP Aliasing procedures for
         BGP-EVPN-IFL-HOST routes.";
      leaf bgp-evpn-instance {
        if-feature "srl_nokia-feat:evpn or srl_nokia-feat:ipvpn";
        type leafref {
          path "/srl_nokia-netinst:network-instance/srl_nokia-netinst:protocols/srl_bgp-vpn:bgp-vpn/srl_bgp-vpn:bgp-instance/srl_bgp-vpn:id";
        }
        default "1";
        description
          "The bgp-evpn instance of the IP-VRF network-instance using the Ethernet Segment

           It indicates from which EVPN interface-less bgp-instance the label/VNI, route distinguisher and route
           targets are taken when advertising the AD per-EVI routes and the AD per-ES routes (except for the VNI/label
           in AD per-ES routes).";
      }
      uses route-internal-tags;
    }
  }

  grouping es-and-ad-es-routes {
    description
      "Grouping containing bgp-evpn ES and AD per-ES route configuration and state.";
    container routes {
      container ethernet-segment {
        leaf originating-ip {
          type srl_nokia-comm:next-hop-type;
          default "use-system-ipv4-address";
          description
            "The originating ip-address with which the Ethernet Segment route will be advertised in this evpn instance";
          must ". = 'use-system-ipv4-address'" {
            srl_nokia-ext:if-feature "not srl_nokia-feat:evpn-mh-non-system-ipv4-address";
            error-message "The originating ip-address must be the system ipv4 address";
          }
        }
        description
          "Enter the ethernet-segment context";
      }
      leaf next-hop {
        type srl_nokia-comm:next-hop-type;
        default "use-system-ipv4-address";
        description
          "The ip-address that will be used as the bgp-next hop for all ES and AD per-ES routes advertised for this Ethernet Segment.";
        must ". = 'use-system-ipv4-address'" {
          srl_nokia-ext:if-feature "not srl_nokia-feat:evpn-mh-non-system-ipv4-address";
          error-message "The next-hop must be the system ipv4 address";
        }
      }
      description
        "Enter the routes context";
    }
  }

  grouping eth-segments-global {
    description
      "Grouping containing ethernet segment configuration and state for global settings.";
    container timers {
      leaf boot-timer {
        type uint32 {
          range "0..6000";
        }
        units "seconds";
        default "10";
        srl_nokia-ext:show-importance "high";
        description
          "Remaining time before running BGP EVPN multi-homing DF election algorithm";
      }
      leaf activation-timer {
        type uint32 {
          range "0..100";
        }
        units "seconds";
        default "3";
        srl_nokia-ext:show-importance "high";
      }
      leaf boot-remaining-time {
        config false;
        type uint32;
        srl_nokia-ext:show-importance "high";
        units "seconds";
        description
          "Indicates the number of seconds remaining for the boot timer to expire.";
      }
      leaf boot-start-time {
        config false;
        type srl_nokia-comm:date-and-time-delta;
        description
          "Indicates the time at which the boot timer started.";
        srl_nokia-ext:show-importance "high";
      }
      description
        "Enter the timers context";
    }
  }

  grouping designated-forwarder-election-top {
    container df-election {
      container timers {
        leaf activation-timer {
          type uint32 {
            range "0..100";
          }
          units "seconds";
          srl_nokia-ext:show-importance "high";
          description
            "Remaining activation timer per Ethernet segment";
        }
        description
          "Enter the timers context";
      }
      container interface-standby-signaling-on-non-df {
        presence "Enables standby signaling on a non-Designated Forwarder node";
        must "../algorithm/type = 'preference'" {
          error-message "The algorithm type must be 'preference'";
        }
        must "../../multi-homing-mode = 'single-active'" {
          error-message "The multi-homing-mode must be 'single-active'";
        }
        srl_nokia-ext:show-importance "high";
      }
      container algorithm {
        leaf type {
          type df-algorithm-type;
          default "default";
          srl_nokia-ext:show-importance "high";
          description
            "Designated Forwarder algorithm type for this ethernet-segment.";
        }
        leaf oper-type {
          type df-algorithm-type;
          srl_nokia-ext:show-importance "high";
          config false;
          description
            "Operational Designated Forwarder algorithm type for this ethernet-segment.";
        }
        container preference-alg {
          presence "Configure preference DF Election algorithm aspects.";
          must "../type = 'preference'" {
            error-message "The algorithm type must be 'preference'";
          }
          leaf preference-value {
            type uint32 {
              range "0..65535";
            }
            default "32767";
            description
              "Preference that is used to elect the designated forwarder";
            srl_nokia-ext:show-importance "high";
            reference
              "draft-ietf-bess-evpn-pref-df";
          }
          leaf oper-preference-value {
            config false;
            type uint32;
            description
              "Operational Preference value";
            srl_nokia-ext:show-importance "high";
            reference
              "draft-ietf-bess-evpn-pref-df";
          }
          leaf oper-do-not-prempt {
            config false;
            type boolean;
            description
              "Operational do-not-preempt value";
            srl_nokia-ext:show-importance "high";
            reference
              "draft-ietf-bess-evpn-pref-df";
          }
          container capabilities {
            leaf ac-df {
              type enumeration {
                enum include;
                enum exclude;
              }
              default "include";
              must "not(. = 'include' and ../../../../../anycast-multi-homing)" {
                srl_nokia-ext:if-feature "srl_nokia-feat:evpn-mh-anycast";
                error-message "AC-DF include is not supported when anycast-multi-homing is configured";
              }
              description
                "Attachment Circuit influenced DF Election.";
              srl_nokia-ext:show-importance "high";
              reference
                "RFC8584";
            }
            leaf non-revertive {
              type boolean;
              default "false";
              description
                "Non Revertive mode. If set to true, the 'Don't Preempt Me' capability is advertised in the ES route.";
              srl_nokia-ext:show-importance "high";
              reference
                "draft-ietf-bess-evpn-pref-df";
            }
            description
              "Enter the capabilities context";
          }
        }
        container manual-alg {
          presence "Configure manual DF Election algorithm aspects.";
          must "../type = 'manual'" {
            error-message "The algorithm type must be 'manual'";
          }
          list primary-evi-range {
            key "start-evi";
            description
              "evi range for this ethernet-segment";
            leaf start-evi {
              description
                "start of the evi-range for this ethernet-segment";
              type srl_nokia-comm:evi;
              srl_nokia-ext:show-importance "high";
            }
            leaf end-evi {
              type srl_nokia-comm:evi;
              description
                "end of the evi-range for this ethernet-segment";
              srl_nokia-ext:show-importance "high";
              mandatory true;
              must '. >= ../start-evi' {
                error-message "end evi must be greater than the start.";
              }
            }
          }
        }
        description
          "Enter the algorithm context";
      }
      description
        "Enter the df-election context";
    }
  }

  grouping evi-df-candidates-info {
    container computed-designated-forwarder-candidates {
      list designated-forwarder-candidate {
        key "address";
        description
          "designated forwarder candidates for this evi";
        leaf address {
          type srl_nokia-comm:ip-address;
          srl_nokia-ext:show-importance "high";
        }
        leaf add-time {
          type srl_nokia-comm:date-and-time-delta;
          description
            "The date and time when the designated-forwarder-candidate was added to the designated forwarder candidate list for this evi";
          srl_nokia-ext:show-importance "high";
        }
        leaf designated-forwarder {
          type boolean;
          default "false";
          description
            "Indicates if this designated-forwarder-candidate is the designated-forwarder.";
          srl_nokia-ext:show-importance "high";
          reference
            "RFC8584";
        }
      }
      description
        "Enter the computed-designated-forwarder-candidates context";
    }
  }

  grouping associated-bgp-instance-df-info {
    leaf designated-forwarder-role-last-change {
      type srl_nokia-comm:date-and-time-delta;
      description
        "Indicates the time at which the designated-forwarder role was changed.";
      srl_nokia-ext:show-importance "high";
    }
    leaf designated-forwarder-activation-start-time {
      type srl_nokia-comm:date-and-time-delta;
      description
        "Indicates the time at which the designated-forwarder activation timer started.";
      srl_nokia-ext:show-importance "high";
    }
    leaf designated-forwarder-activation-time {
      type uint32;
      units "seconds";
      description
        "Indicates the number of seconds for the activation timer to run, for this node to become the designated forwarder for this bgp instance.";
      srl_nokia-ext:show-importance "high";
    }
  }

  grouping associated-bgp-instance-info {
    list bgp-instance {
      key "instance";
      description
        "bgp-instance associated to this ethernet-segment";
      leaf instance {
        type uint32;
        srl_nokia-ext:show-importance "high";
      }
      uses associated-bgp-instance-df-info;
      uses evi-df-candidates-info;
    }
  }

  grouping association-info {
    list network-instance {
      key "name";
      description
        "network instance associated to this ethernet-segment";
      leaf name {
        type string;
        srl_nokia-ext:show-importance "high";
      }
      uses associated-bgp-instance-info;
    }
  }

  grouping eth-segments-top {
    description
      "Top-level grouping containing the bgp-evpn ethernet segments configuration and state.";
    container ethernet-segments {
      srl_nokia-ext:first-released "21.3.1";
      presence "Container for evpn ethernet segments configuration and state.";
      uses eth-segments-global;
      list bgp-instance {
        key "id";
        max-elements 1;
        description
          "bgp global instances configured in net-instance";
        leaf id {
          type leafref {
            path "/srl_nokia-system:system/srl_nokia-system-network-instance:network-instance/srl_nokia-system-network-instance:protocols/srl_nokia-system-bgp-vpn:bgp-vpn/srl_nokia-system-bgp-vpn:bgp-instance/srl_nokia-system-bgp-vpn:id";
          }
        }
        list ethernet-segment {
          key "name";
          max-elements 1024;
          description
            "Ethernet Segment configuration and state.";
          leaf name {
            type srl_nokia-comm:name;
            description
              "A unique name identifying the ethernet segment.";
          }
          leaf type {
            type es-type;
            default "none";
            srl_nokia-ext:show-importance "high";
            description
              "Ethernet Segment type.";
          }
          leaf admin-state {
            type srl_nokia-comm:admin-state;
            default "disable";
            srl_nokia-ext:show-importance "high";
            description
              "Admin state of the ethernet segment";
          }
          leaf oper-state {
            config false;
            srl_nokia-ext:show-importance "high";
            type srl_nokia-comm:oper-state;
            description
              "This leaf contains the operational state of ethernet segment.";
          }
          leaf esi {
            type srl_nokia-comm:esi;
            must "not(.='00:00:00:00:00:00:00:00:00:00' or .='ff:ff:ff:ff:ff:ff:ff:ff:ff:ff' or re-match(.,'[0-9a-fA-F]{2}(:[0]{2}){6}.*'))";
            srl_nokia-ext:show-importance "high";
            description
              "The 10-byte Ethernet Segment Identifier of the ethernet segment.

               ESI-0 or MAX-ESI values are not allowed.
               ESI values with bytes 1-6 all zeros are not allowed since they would produce a null ESI-import route-target.";
          }
          leaf use-esi-label {
            if-feature "srl_nokia-feat:evpn-mh-no-esi-label";
            type boolean;
            default "true";
            description
              "Indicates if an ESI label is used for the ethernet segment

               When set to true, the ESI label is used for split-horizon filtering within the Ethernet Segment. 'True' is mandatory for
               all-active multi-homing mode Ethernet Segments connected to MAC-VRF network-instances using MPLS encapsulation. For all-active
               Ethernet Segments connected to VPWS network-instances with any encapsulation or MAC-VRFs using VXLAN encapsulation, as well as
               for single-active Ethernet Segments, the use of the ESI label is optional.";
          }
          leaf oper-esi {
            type srl_nokia-comm:esi;
            config false;
            srl_nokia-ext:show-importance "high";
            description
              "The operational Ethernet Segment Identifier used in the ethernet segment.";
          }
          leaf esi-label {
            config false;
            type srl_nokia-comm:mpls-label-non-reserved;
            description
              "The esi label allocated for this ethernet-segment.

               The esi-label is advertised by the EVPN Auto-Discovery-Ethernet-Segment
               Advertisement routes and it is expected on received EVPN packets
               that were generated as multicast packets from this ethernet-segments peers.";
          }
          choice interface-association {
            description
              "Interface or virtual interface associated to the Ethernet Segment.";
            case layer-2-interface {
              list interface {
                key "ethernet-interface";
                max-elements 1;
                leaf ethernet-interface {
                  type leafref {
                    path "/srl_nokia-if:interface/srl_nokia-if:name";
                  }
                  must "(starts-with(.,'ethernet') or  starts-with(.,'lag') or starts-with(., 'lif') or starts-with(., 'enp') or starts-with(., 'vhn'))" {
                    error-message "Interface cannot be associated with Ethernet Segments. Not supported.";
                  }
                  must "../../type = 'none'" {
                    error-message "not supported with virtual type";
                  }
                  description
                    "Interface associated with the ethernet segment.";
                }
              }
            }
            case layer-3-next-hop {
              if-feature "srl_nokia-feat:evpn-mh-ip-aliasing";
              list next-hop {
                key "l3-next-hop";
                max-elements 1;
                leaf l3-next-hop {
                  type srl_nokia-comm:ip-address;
                  must "../../type = 'virtual'" {
                    error-message "supported only with virtual type";
                  }
                  must 'not(../../advertise-ifl-host-ad-routes)' {
                    error-message "Cannot configure next-hop when advertise-ifl-host-ad-routes is configured";
                  }
                  description
                    "Layer-3 next-hop associated with the ethernet segment.";
                }
                list evi {
                  key "start";
                  max-elements 1;
                  description
                    "evi range for this ethernet-segment association";
                  leaf start {
                    description
                      "start of the evi-range for this ethernet-segment";
                    type srl_nokia-comm:evi;
                    srl_nokia-ext:show-importance "high";
                  }
                }
              }
            }
          }
          leaf multi-homing-mode {
            type multi-homing-mode;
            default "all-active";
            srl_nokia-ext:show-importance "high";
            description
              "Multi-homing mode of the ethernet segment.

               The state of this leaf can be different than the configured value in cases where the configured value is 'all-active' and the
               multi-homing mode advertised by the ES peers in the AD per-ES routes is 'single-active'. In this case, the state of this
               leaf will show 'single-active'.

               When an Ethernet Segment (ES) is configured as either all-active-no-esi-label or single-active-no-esi-label, no ESI (Ethernet
               Segment Identifier) label is allocated. This configuration is suitable for Ethernet segments connected exclusively to VXLAN or
               VPWS network instances.";
            reference
              "RFC7432";
          }
          leaf oper-multi-homing-mode {
            config false;
            type multi-homing-mode;
            srl_nokia-ext:show-importance "high";
            description
              "Operational Multi-homing mode of the ethernet segment.

               The state of this leaf can be different than the configured value in cases where the configured value is 'all-active' and the
               multi-homing mode advertised by the ES peers in the AD per-ES routes is 'single-active'. In this case, the state of this leaf
               will show 'single-active'.";
            reference
              "RFC7432";
          }
          leaf layer-3-neighbor-synchronization {
            if-feature "srl_nokia-feat:evpn-neighbor-synchronization";
            type boolean;
            default "false";
            must "not(. = true() and ../type != 'none')" {
              error-message "layer-3-neighbor-synchronization true is only supported when the ethernet segment type is none";
            }
            description
              "Enables the layer-3 ARP and ND synchronization across PEs

               When set to true, the Ethernet Segment is used to synchronize ARP and/or Neighbor Discovery entries on non-IRB subinterfaces
               across all the PEs attached to the same CE that uses a single LAG.";
          }
          uses ifl-host-ip-aliasing;
          uses designated-forwarder-election-top;
          uses anycast-eth-segments;
          uses es-and-ad-es-routes;
          container autodiscovery-per-ethernet-segment-routes {
            config false;
            uses srl_nokia-rib-bgp-routes:evpn-ethernet-ad-common;
            description
              "Enter the autodiscovery-per-ethernet-segment-routes context";
          }
          container ethernet-segment-routes {
            config false;
            uses srl_nokia-rib-bgp-routes:evpn-es-common;
            description
              "Enter the ethernet-segment-routes context";
          }
          leaf oper-down-reason {
            config false;
            type enumeration {
              enum admin-disabled;
              enum no-nexthop-address;
              enum no-originating-address;
              enum no-associated-interface;
              enum associated-interface-oper-down;
              enum no-esi;
              enum no-esi-label;
              enum tag-set-not-resolved;
            }
            description
              "The reason for the ethernet-segment being down in the bgp-instance";
          }
          container association {
            config false;
            uses association-info;
            description
              "Enter the association context";
          }
        }
      }
    }
  }

  augment "/srl_nokia-system:system/srl_nokia-system-network-instance:network-instance/srl_nokia-system-network-instance:protocols/srl_nokia-system-network-instance:evpn" {
    uses eth-segments-top;
  }
}
