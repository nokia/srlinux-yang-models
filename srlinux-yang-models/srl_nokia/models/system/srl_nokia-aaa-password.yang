module srl_nokia-aaa-password {
  yang-version 1.1;
  namespace "urn:nokia.com:srlinux:aaa:aaa-password";
  prefix srl-aaa-password;

  import srl_nokia-features {
    prefix srl_nokia-feat;
  }

  organization
    "Nokia";
  contact
    "Nokia SR Linux Support
     Web: <http://www.nokia.com>";
  description
    "This module defines configuration and operational state data
     related to the password complexity and lockout for local users,
     including admin and linuxadmin users.";

  revision 2026-07-31 {
    description
      "SRLinux 26.7.1";
  }
  revision 2026-03-31 {
    description
      "SRLinux 26.3.1";
  }
  revision 2025-07-31 {
    description
      "SRLinux 25.7.1";
  }
  revision 2025-03-31 {
    description
      "SRLinux 25.3.1";
  }
  revision 2024-03-31 {
    description
      "SRLinux 24.3.1";
  }
  revision 2023-10-31 {
    description
      "SRLinux 23.10.1";
  }
  revision 2023-03-31 {
    description
      "SRLinux 23.3.1";
  }
  revision 2022-11-30 {
    description
      "SRLinux 22.11.1";
  }
  revision 2022-06-30 {
    description
      "SRLinux 22.6.1";
  }

  grouping aaa-password-complexity-config {
    description
      "Configuration data for password complexity rules";
    container complexity-rules {
      description
        "Enter the complexity-rules context

         Top-level container for password complexity rules";
      leaf minimum-length {
        type uint16 {
          range "1..12";
        }
        default "1";
        must '. >= ../minimum-lowercase + ../minimum-uppercase + ../minimum-numeric + ../minimum-special-character' {
          error-message "Minimum length must be at least the sum of minimum lengths of all character classes";
        }
        description
          "The minimum length of the password in bytes for local users, including admin and linuxadmin";
      }
      leaf maximum-length {
        type uint16 {
          range "1..1023";
        }
        default "1023";
        must '. >= ../minimum-length' {
          error-message "Maximum length must be at least equal to minimum length";
        }
        description
          "The maximum length of the password in bytes for local users, including admin and linuxadmin";
      }
      leaf minimum-lowercase {
        type uint16 {
          range "0..10";
        }
        default "0";
        description
          "The minimum lowercase characters from (a-z) that the user password must include

           A value of 0 results in no minimum-lowercase being enforced.";
      }
      leaf minimum-uppercase {
        type uint16 {
          range "0..10";
        }
        default "0";
        description
          "The minimum uppercase characters from (A-Z) that the user password must include

           A value of 0 results in no minimum-uppercase being enforced.";
      }
      leaf minimum-numeric {
        type uint16 {
          range "0..10";
        }
        default "0";
        description
          "The minimum numeric digits that the user password must include

           A value of 0 results in no minimum-numeric being enforced.";
      }
      leaf minimum-special-character {
        type uint16 {
          range "0..10";
        }
        default "0";
        description
          "The minimum special characters that the user password must include

           A value of 0 results in no minimum-special-character being enforced.";
      }
      leaf allow-username {
        type boolean;
        default "true";
        description
          "Enable or disable using username as part of the user password";
      }
      leaf disallow-sequence-keys {
        if-feature "srl_nokia-feat:password-complexity-sequence";
        type uint32 {
          range "0 | 2..8";
        }
        default "0";
        description
          "The minimum length of disallowed sequential characters
           to appear (letters or numbers) from left to right,
           right to left, down to up-right/left, or up to down-right/left.";
      }
      leaf repeated-characters {
        if-feature "srl_nokia-feat:password-complexity-repeated-characters";
        type uint16 {
          range "0 | 2..8";
        }
        default "0";
        description
          "Number of times same character can repeat consecutively";
      }
    }
  }

  grouping aaa-password-lockout-policy-config {
    description
      "Configuration data for lockout policy";
    container lockout-policy {
      description
        "Enter the lockout-policy context

         Top-level container for lockout policy";
      leaf attempts {
        type uint16 {
          range "0..64";
        }
        default "0";
        description
          "The number of failed login attempts that will lock the account

           A value of 0 means unlimited number of failed login attempts is allowed";
      }
      leaf time {
        type uint16 {
          range "0..1440";
        }
        units "minutes";
        default "1";
        description
          "The time period in minutes within which the failed login attempts occur";
      }
      leaf lockout {
        type uint16 {
          range "0..1440";
        }
        units "minutes";
        default "15";
        description
          "The time duration in minutes the user account will be locked out

           A value of 0 means that the user account will be locked out/disabled indefinitely";
      }
    }
  }

  grouping aaa-password-hash-method-config {
    description
      "Grouping of password hash method relating to user";
    leaf hash-method {
      type enumeration {
        enum ar2 {
          description
            "The Argon2 password hashing algorithm";
        }
        enum sha2 {
          description
            "The SHA512 password hashing algorithm";
        }
        enum yescrypt {
          description
            "The Yescrypt password hashing algorithm";
        }
      }
      description
        "The hash algorithm for the passwords entered as plain text

         If no value is configured, then Yescrypt will be used as the hash algorithm unless overriden for specific leafs
         using the srl_nokia-extensions:hash-algorithm yang extension. The Argon2 (ar2) hash algorithm is not supported
         for the linuxadmin user and if selected then the linuxadmin password will be hashed using Yescrypt.";
    }
  }

  grouping aaa-password-top {
    description
      "Top-level grouping for policies around user passwords";
    container password {
      description
        "Enter the password context

         Top-level container for policies around user passwords";
      uses aaa-password-complexity-config;
      uses aaa-password-lockout-policy-config;
      uses aaa-password-hash-method-config;
      leaf aging {
        type uint16 {
          range "0..500";
        }
        units "days";
        default "0";
        description
          "Expire user passwords after this period

           A value of 0 means that the user passwords do not expire";
      }
      leaf change-on-first-login {
        type boolean;
        default "false";
        description
          "Enable or disable a user being forced to change their password on first time login";
      }
      leaf history {
        type uint16 {
          range "0..20";
        }
        default "0";
        description
          "Defines how many previous passwords a new password is matched against, such that a new password can't be one of the previous n passwords";
      }
      leaf require-ntp-sync {
        if-feature "not srl_nokia-feat:platform-imgmt";
        type boolean;
        default "true";
        description
          "Enable or disable dependence of password aging and user lockout on NTP sync status";
      }
    }
  }
}
