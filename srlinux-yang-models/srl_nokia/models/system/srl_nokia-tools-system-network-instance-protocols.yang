module srl_nokia-tools-system-network-instance-protocols {
  yang-version 1.1;
  namespace "urn:nokia.com:srlinux:general:tools-system-network-instance-protocols";
  prefix srl_nokia-tools-system-network-instance-protocols;

  import srl_nokia-tools-system {
    prefix srl-tools-system;
  }

  organization
    "Nokia";
  contact
    "Nokia SR Linux Support
     Web: <http://www.nokia.com>";
  description
    "Tools related to the System Network Instance protocols";

  revision 2026-07-31 {
    description
      "SRLinux 26.7.1";
  }
  revision 2025-07-31 {
    description
      "SRLinux 25.7.1";
  }

  grouping tools-sys-net-inst-protocols-top {
    container network-instance {
      presence "Configure tools system network-instance";
      description
        "Enclosing container for system network-instance";
      container protocols {
        description
          "Enter the protocols context

           Enclosing container for system network-instance protocols";
      }
    }
  }

  augment "/srl-tools-system:system" {
    uses tools-sys-net-inst-protocols-top;
  }
}
