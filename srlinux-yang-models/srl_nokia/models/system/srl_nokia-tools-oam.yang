module srl_nokia-tools-oam {
    yang-version 1.1;
    namespace "urn:srl_nokia/tools-oam";
    prefix srl_nokia-tools-oam;

  organization
    "Nokia";
  contact
    "Nokia SR Linux Support
     Web: <http://www.nokia.com>";

    description
        "Model for operational commands on OAM.";

  revision 2021-11-30 {
    description
      "SRLinux 21.11.1";
  }

    container oam {
        presence "Configure tools OAM";
        description
            "Enclosing container for OAM management.";
    }
}
