module srl_nokia-system-bridge-table {
  yang-version 1.1;
  namespace "urn:nokia.com:srlinux:l2-mac:system-bridge-table";
  prefix srl_nokia-system-bridge-table;

  import srl_nokia-system {
    prefix srl-system;
  }
  import srl_nokia-common {
    prefix srl_nokia-comm;
  }
  import srl_nokia-extensions {
    prefix srl_nokia-ext;
  }

  organization
    "Nokia";
  contact
    "Nokia SR Linux Support
     Web: <http://www.nokia.com>";
  description
    "This module defines system bridge-table configuration and operational
     state data.";

  revision 2026-07-31 {
    description
      "SRLinux 26.7.1";
  }
  revision 2020-06-30 {
    description
      "SRLinux 20.6.1";
  }

  grouping bridge-table-statistics-top {
    container statistics {
      config false;
      leaf active-entries {
        type srl_nokia-comm:zero-based-counter64;
        description
          "The total number of macs that are active on the system.";
        srl_nokia-ext:show-importance "high";
      }
      leaf total-entries {
        type srl_nokia-comm:zero-based-counter64;
        description
          "The total number of macs, active and inactive, on the system.";
        srl_nokia-ext:show-importance "high";
      }
      leaf failed-entries {
        type srl_nokia-comm:zero-based-counter64;
        description
          "The total number of macs, which have not been programmed on atleast one slot";
        srl_nokia-ext:show-importance "high";
      }
      list mac-type {
        key "type";
        description
          "the type of the mac in the system.";
        leaf type {
          type srl_nokia-comm:mac-type;
          srl_nokia-ext:show-importance "high";
        }
        leaf active-entries {
          type srl_nokia-comm:zero-based-counter64;
          description
            "The total number of macs of this type on the system.";
          srl_nokia-ext:show-importance "high";
        }
        leaf total-entries {
          type srl_nokia-comm:zero-based-counter64;
          description
            "The total number of macs of this type , active and inactive, on the system.";
          srl_nokia-ext:show-importance "high";
        }
        leaf failed-entries {
          type srl_nokia-comm:zero-based-counter64;
          description
            "The total number of macs of this type, which have not been programmed on atleast one slot";
          srl_nokia-ext:show-importance "high";
        }
      }
      description
        "Enter the statistics context";
    }
  }

  grouping bridge-table-mac-learning-top {
    container mac-learning {
      leaf mac-relearn-only {
        config false;
        type boolean;
        description
          "The value of this leaf indicates that the system will not
           learn any new mac addresses, but will relearn any that are already
           programmed";
      }
      description
        "Enter the mac-learning context";
    }
  }

  grouping bridge-table-mac-limit-top {
    container mac-limit {
      description
        "Enter the mac-limit context

         Bridge Table size and thresholds.";
      leaf maximum-entries {
        config false;
        type int32;
        description
          "Maximum number of mac addresses allowed in the system bridge-table.";
      }
      leaf warning-threshold-pct {
        config false;
        type int32;
        description
          "Percentage of the configured max-number-macs over which a warning is triggered.
           The warning message is cleared when the percentage drops below the configured
           percentage minus 5%";
      }
    }
  }

  grouping bridge-table-top {
    container bridge-table {
      description
        "Enter the bridge-table context

         system bridge-table information";
      uses bridge-table-mac-learning-top;
      uses bridge-table-mac-limit-top;
      uses bridge-table-statistics-top;
    }
  }

  augment "/srl-system:system" {
    uses bridge-table-top;
  }
}
