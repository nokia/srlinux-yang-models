module srl_nokia-tools-l2cp {
  yang-version 1.1;
  namespace "urn:nokia.com:srlinux:chassis:tools-l2cp";
  prefix srl_nokia-tools-l2cp;

  import srl_nokia-tools-system {
    prefix srl-tools-system;
  }
  import srl_nokia-features {
    prefix srl_nokia-feat;
  }

  organization
    "Nokia";
  contact
    "Nokia SR Linux Support
     Web: <http://www.nokia.com>";
  description
    "Model for system level L2CP operational commands";

  revision 2026-07-31 {
    description
      "SRLinux 26.7.1";
  }
  revision 2025-03-31 {
    description
      "SRLinux 25.3.1";
  }
  revision 2024-10-31 {
    description
      "SRLinux 24.10.1";
  }
  revision 2022-03-31 {
    description
      "SRLinux 22.3.1";
  }

  grouping tools-l2cp-top {
    container l2cp-transparency {
      presence "Configure tools l2cp-transparency";
      if-feature "srl_nokia-feat:l2cp-transparency";
      container l2cp-total-statistics {
        leaf clear {
          type empty;
          description
            "Clears the global statistics for the L2CP protocols";
        }
        description
          "Enter the l2cp-total-statistics context";
      }
      container lldp {
        leaf clear {
          type empty;
          description
            "Clears the statistics for Link Layer Discovery Protocol";
        }
        description
          "Enter the lldp context";
      }
      container lacp {
        leaf clear {
          type empty;
          description
            "Clears the statistics for Link Aggregation Control Protocol";
        }
        description
          "Enter the lacp context";
      }
      container xstp {
        if-feature "srl_nokia-feat:l2cp-transparency-xstp";
        leaf clear {
          type empty;
          description
            "Clears the statistics for all the Spanning Tree Protocols";
        }
        description
          "Enter the xstp context";
      }
      container ptp {
        leaf clear {
          type empty;
          description
            "Clears the statistics for the Precision Time Protocol";
        }
        description
          "Enter the ptp context";
      }
      container esmc {
        if-feature "srl_nokia-feat:l2cp-transparency-esmc";
        leaf clear {
          type empty;
          description
            "Clears the statistics for the Ethernet Synchronization Messaging Channel protocol";
        }
        description
          "Enter the esmc context";
      }
      container elmi {
        if-feature "srl_nokia-feat:l2cp-transparency-elmi";
        leaf clear {
          type empty;
          description
            "Clears the statistics for the Ethernet Local Management Interface protocol";
        }
        description
          "Enter the elmi context";
      }
      container efm-oam {
        if-feature "srl_nokia-feat:l2cp-transparency-efm-oam";
        leaf clear {
          type empty;
          description
            "Clears the statistics for the Ethernet in the First Mile OAM protocol";
        }
        description
          "Enter the efm-oam context";
      }
    }
  }

  augment "/srl-tools-system:system" {
    if-feature "srl_nokia-feat:l2cp-transparency";
    uses tools-l2cp-top;
  }
}
