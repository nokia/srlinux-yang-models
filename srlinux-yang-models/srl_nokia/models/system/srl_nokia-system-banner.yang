module srl_nokia-system-banner {
  yang-version 1.1;
  namespace "urn:nokia.com:srlinux:linux:system-banner";
  prefix srl_nokia-system-banner;

  import srl_nokia-system {
    prefix srl-system;
  }

  organization
    "Nokia";
  contact
    "Nokia SR Linux Support
     Web: <http://www.nokia.com>";
  description
    "This module defines configuration related system banners";

  revision 2026-07-31 {
    description
      "SRLinux 26.7.1";
  }
  revision 2019-11-30 {
    description
      "SRLinux 19.11.1";
  }

  grouping banner-config-top {
    container banner {
      description
        "Enter the banner context

         Contains configuration and state related to system banners";
      leaf login-banner {
        type string;
        description
          "Banner to display before a user has authenticated";
      }
      leaf motd-banner {
        type string;
        description
          "Banner to display after a user has authenticated";
      }
    }
  }

  grouping banner-top {
    uses banner-config-top;
  }

  augment "/srl-system:system" {
    uses banner-top;
  }
}
