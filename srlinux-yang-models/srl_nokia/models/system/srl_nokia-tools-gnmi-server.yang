module srl_nokia-tools-gnmi-server {
  yang-version 1.1;
  namespace "urn:srl_nokia/tools-gnmi-server";
  prefix srl-tools-gnmi-server;

  import srl_nokia-tools-system {
    prefix srl-tools-system;
  }
  import srl_nokia-features {
    prefix srl-feat;
  }
  import srl_nokia-extensions {
    prefix srl-ext;
  }

  organization
    "Nokia";
  contact
    "Nokia SR Linux Support
     Web: <http://www.nokia.com>";
  description
    "This module defines tools related to the gRIBI server";

  revision 2023-10-31 {
    description
      "SRLinux 23.10.1";
  }

  grouping gnmi-tools-common {
    leaf disconnect {
      description
        "Disconnect this client from the server";
      type empty;
    }
  }

  grouping gnmi-server-top {
    container gnmi-server {
      presence "Configure tools gnmi-server";
      description
        "Tools relating to the gNMI service";
      list client {
        description
          "List of active gNMI client sessions";
        key "id";
        leaf id {
          type uint32 {
            range "0..4294967295";
          }
          description
            "System generated ID for for the client";
        }
        uses gnmi-tools-common;
      }
    }
  }

  augment "/srl-tools-system:system" {
    srl-ext:first-released "23.10.1";
    uses gnmi-server-top;
  }
}
