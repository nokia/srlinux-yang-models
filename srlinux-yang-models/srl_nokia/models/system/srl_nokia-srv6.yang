module srl_nokia-srv6 {
  yang-version 1.1;
  namespace "urn:nokia.com:srlinux:srv6:srv6";
  prefix srl_nokia-srv6;

  import srl_nokia-features {
    prefix srl_nokia-feat;
  }
  import srl_nokia-extensions {
    prefix srl_nokia-ext;
  }
  import srl_nokia-common {
    prefix srl_nokia-comm;
  }
  import srl_nokia-system {
    prefix srl_nokia-system;
  }
  import srl_nokia-srv6-types {
    prefix srl_nokia-srv6-types;
  }

  organization
    "Nokia";
  contact
    "Nokia SR Linux Support
     Web: <http://www.nokia.com>";
  description
    "This YANG file covers the non-protocol specific segment routing v6 enhancements to SRL";

  revision 2026-07-31 {
    description
      "SRLinux 26.7.1";
  }
  revision 2026-03-31 {
    description
      "SRLinux 26.3.1";
  }
  revision 2025-10-31 {
    description
      "SRLinux 25.10.1";
  }
  revision 2025-07-31 {
    description
      "SRLinux 25.7.1";
  }

  grouping srv6-system {
    container srv6 {
      presence "Enable the srv6 context";
      description
        "Enter the srv6 context to configure locators and other SRv6 functionalities";
      list source-address {
        if-feature "srl_nokia-feat:srv6";
        key "ip-address";
        max-elements 7;
        description
          "List of sourcess addresses";
        leaf ip-address {
          type srl_nokia-comm:ipv6-address-unicast;
          description
            "Source address used in the SRv6 packet";
        }
      }
      leaf default-source-address {
        if-feature "srl_nokia-feat:srv6";
        type leafref {
          path "../source-address/ip-address";
        }
        mandatory true;
        description
          "Default source address";
      }
      container micro-segment {
        description
          "Enter the micro-segment context";
        leaf block-length {
          type uint8 {
            range "32";
          }
          default "32";
          description
            "Micro-SID block length";
        }
        leaf gib-size {
          type uint8 {
            range "4..60";
          }
          default "16";
          description
            "Maximum number of micro-segment locators network wide (x 1024)";
        }
        leaf sid-length {
          type uint8 {
            range "16";
          }
          default "16";
          description
            "Micro-SID length";
        }
        list block {
          key "block-name";
          max-elements 8;
          description
            "Enter the block list instance";
          leaf block-name {
            type srl_nokia-comm:name {
              pattern '[^@]*' {
                error-message "Micro-segment block name cannot contain @";
              }
              length "1..64" {
                error-message "Micro-segment block name cannot be longer than 64 characters";
              }
            }
            description
              "Micro-SID block name";
          }
          container prefix {
            description
              "Enter the prefix context";
            leaf ip-prefix {
              type srl_nokia-comm:ipv6-prefix-unicast;
              mandatory true;
              description
                "SRv6 micro-segment block prefix";
            }
          }
          container static-function {
            if-feature "srl_nokia-feat:srv6";
            description
              "Enter the static-function context";
            leaf max-entries {
              type uint32 {
                range "1..65535";
              }
              default "1";
              description
                "Maximum number of static micro-segment functions";
            }
          }
          leaf status {
            config false;
            description
              "The status of the SRv6 full segment locator";
            type srl_nokia-srv6-types:status;
          }
        }
      }
      list locator {
        key "locator-name";
        max-elements 16;
        description
          "Enter the locator list instance";
        leaf locator-name {
          type srl_nokia-comm:name {
            pattern '[^@]*' {
              error-message "Locator name cannot contain @";
            }
            length "1..64" {
              error-message "Locator name cannot be longer than 64 characters";
            }
          }
          description
            "SRv6 locator name";
        }
        must 'not (full-segment = true() and micro-segment = true())' {
          error-message "Full-segment and micro-segment cannot be configured together";
        }
        must 'not (full-segment = false() and micro-segment = false())' {
          error-message "Must configure either full-segment or micro-segment";
        }
        unique "micro-segment/un/value micro-segment/block";
        container full-segment {
          if-feature "srl_nokia-feat:srv6";
          presence "Enable full-segment for the locator";
          description
            "Enter the context to configure the full-segment locator";
          leaf block-length {
            type uint8 {
              range "0|8|16|24|32|40|48|56|64|72|80|88|96";
            }
            default "0";
            description
              "SRv6 locator block address length";
          }
          leaf function-length {
            type uint8 {
              range "16";
            }
            mandatory true;
            description
              "Function length";
          }
          leaf argument-length {
            if-feature "srl_nokia-feat:srv6-dt2";
            type uint8 {
              range "0|16";
            }
            default "0";
            description
              "Argument length";
          }
          leaf algorithm {
            type uint32 {
              range "0|128..255";
            }
            default "0";
            description
              "IGP flexible algorithm ID";
          }
          container prefix {
            description
              "Enter the prefix context";
            leaf ip-prefix {
              type srl_nokia-comm:ipv6-prefix-unicast;
              mandatory true;
              description
                "SRv6 locator prefix";
            }
          }
          container static-function {
            description
              "Enter the static-function context";
            leaf max-entries {
              type uint32 {
                range "1..1048575";
              }
              default "1";
              description
                "Maximum number of static SID functions";
            }
          }
          leaf status {
            config false;
            description
              "The status of the SRv6 full segment locator";
            type srl_nokia-srv6-types:status;
          }
        }
        container micro-segment {
          presence "Enable micro-segment for the locator";
          description
            "Enter the context to configure the micro-segment locator";
          leaf block {
            type leafref {
              path "../../../micro-segment/block/block-name";
            }
            mandatory true;
            description
              "Pre-defined micro-SID block";
          }
          leaf argument-length {
            if-feature "srl_nokia-feat:srv6-dt2";
            type uint8 {
              range "0|16";
            }
            must '128 > (. + ../../../micro-segment/block-length + 2 * ../../../micro-segment/sid-length)' {
              error-message "Argument-length + 2*Sid-length + block-length must be less than or equal to 128";
            }
            default "0";
            description
              "Argument length";
          }
          leaf algorithm {
            if-feature "srl_nokia-feat:srv6";
            type uint32 {
              range "0|128..255";
            }
            default "0";
            description
              "IGP flexible algorithm ID";
          }
          container un {
            description
              "Enter the un context";
            leaf srh-mode {
              type srl_nokia-srv6-types:srh-mode;
              default "psp";
              description
                "Segment Routing Header (SRH) mode";
              must '. = "psp-usp-usd"' {
                srl_nokia-ext:if-feature "srl_nokia-features:srv6-usid-basic";
                error-message "Only support psp-usp-usd on this platform.";
              }
            }
            leaf value {
              type uint32 {
                range "1..65535";
              }
              must '. < (1024 * ../../../../micro-segment/gib-size)' {
                error-message "Value must be within global sid space";
              }
              mandatory true;
              description
                "SRv6 uN function value";
            }
            leaf status {
              config false;
              description
                "The status of the SRv6 micro segment locator un";
              type srl_nokia-srv6-types:status;
            }
            leaf sid {
              config false;
              description
                "The sid address associated with function";
              type srl_nokia-comm:ipv6-prefix;
            }
          }
          leaf status {
            config false;
            description
              "The status of the SRv6 full segment locator";
            type srl_nokia-srv6-types:status;
          }
        }
      }
    }
  }

  augment "/srl_nokia-system:system" {
    uses srv6-system;
    if-feature "srl_nokia-feat:srv6 or srl_nokia-feat:srv6-usid-basic";
  }
}
