module srl_nokia-tftp {
  yang-version 1.1;
  namespace "urn:nokia.com:srlinux:linux:tftp";
  prefix srl_nokia-tftp;

  import srl_nokia-system {
    prefix srl-system;
  }
  import srl_nokia-network-instance {
    prefix srl_nokia-netinst;
  }
  import srl_nokia-common {
    prefix srl_nokia-comm;
  }
  import srl_nokia-features {
    prefix srl_nokia-feat;
  }

  organization
    "Nokia";
  contact
    "Nokia SR Linux Support
     Web: <http://www.nokia.com>";
  description
    "This module defines TFTP configuration";

  revision 2025-10-31 {
    description
      "SRLinux 25.10.1";
  }

  grouping tftp-top {
    container tftp-server {
      presence "Configure TFTP server";
      list network-instance {
        description
          "List of network instances to run a TFTP server in";
        key "name";
        leaf name {
          type leafref {
            path "/srl_nokia-netinst:network-instance/srl_nokia-netinst:name";
          }
          description
            "Reference to a configured network-instance";
        }
        leaf admin-state {
          type srl_nokia-comm:admin-state;
          default "disable";
          description
            "Administratively enables or disables the TFTP server";
        }
        leaf oper-state {
          type srl_nokia-comm:oper-state;
          config false;
          description
            "Details if the server is operationally available";
        }
        leaf-list source-address {
          if-feature "not srl_nokia-feat:platform-imgmt";
          type srl_nokia-comm:ip-address;
          description
            "List of IP addresses for the TFTP server to listen on within the network-instance";
        }
        leaf root-directory {
          type string;
          default "/srv/tftpboot";
          description
            "Set the root directory of the TFTP server. If the directory needs to be synchronized to the secondary control card,
             it is recommended to use a directory under /opt or /srv.";
        }
      }
    }
  }

  augment "/srl-system:system" {
    uses tftp-top;
    if-feature "srl_nokia-feat:tftp";
  }
}
