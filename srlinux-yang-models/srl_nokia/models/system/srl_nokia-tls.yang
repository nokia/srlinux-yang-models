module srl_nokia-tls {
  yang-version 1.1;
  namespace "urn:nokia.com:srlinux:linux:tls";
  prefix srl_nokia-tls;

  import srl_nokia-system {
    prefix srl-system;
  }
  import srl_nokia-common {
    prefix srl-comm;
  }
  import srl_nokia-features {
    prefix srl_nokia-feat;
  }
  import srl_nokia-extensions {
    prefix srl-ext;
  }

  organization
    "Nokia";
  contact
    "Nokia SR Linux Support
     Web: <http://www.nokia.com>";
  description
    "This module defines TLS configuration";

  revision 2026-07-31 {
    description
      "SRLinux 26.7.1";
  }
  revision 2026-03-31 {
    description
      "SRLinux 26.3.1";
  }
  revision 2025-10-31 {
    description
      "SRLinux 25.10.1";
  }
  revision 2025-03-31 {
    description
      "SRLinux 25.3.1";
  }
  revision 2024-10-31 {
    description
      "SRLinux 24.10.1";
  }
  revision 2024-07-31 {
    description
      "SRLinux 24.7.1";
  }
  revision 2023-10-31 {
    description
      "SRLinux 23.10.1";
  }
  revision 2022-11-30 {
    description
      "SRLinux 22.11.1";
  }
  revision 2019-11-30 {
    description
      "SRLinux 19.11.1";
  }

  identity cipher-type {
    description
      "Base identity for cipher types";
  }

  identity ecdhe-rsa-aes256-gcm-sha384 {
    base cipher-type;
  }

  identity ecdhe-ecdsa-aes256-gcm-sha384 {
    base cipher-type;
  }

  identity ecdhe-rsa-aes256-sha384 {
    base cipher-type;
  }

  identity ecdhe-ecdsa-aes256-sha384 {
    base cipher-type;
  }

  identity ecdhe-rsa-aes256-sha {
    base cipher-type;
  }

  identity ecdhe-ecdsa-aes256-sha {
    base cipher-type;
  }

  identity dhe-dss-aes256-gcm-sha384 {
    base cipher-type;
  }

  identity dhe-rsa-aes256-gcm-sha384 {
    base cipher-type;
  }

  identity dhe-rsa-aes256-sha256 {
    base cipher-type;
  }

  identity dhe-dss-aes256-sha256 {
    base cipher-type;
  }

  identity dhe-rsa-aes256-sha {
    base cipher-type;
  }

  identity dhe-dss-aes256-sha {
    base cipher-type;
  }

  identity dhe-rsa-camellia256-sha {
    if-feature "not (srl_nokia-feat:system-fips-mode)";
    base cipher-type;
  }

  identity dhe-dss-camellia256-sha {
    if-feature "not (srl_nokia-feat:system-fips-mode)";
    base cipher-type;
  }

  identity aes256-gcm-sha384 {
    base cipher-type;
  }

  identity aes256-sha256 {
    base cipher-type;
  }

  identity aes256-sha {
    base cipher-type;
  }

  identity camellia256-sha {
    if-feature "not (srl_nokia-feat:system-fips-mode)";
    base cipher-type;
  }

  identity psk-aes256-cbc-sha {
    base cipher-type;
  }

  identity ecdhe-rsa-aes128-gcm-sha256 {
    base cipher-type;
  }

  identity ecdhe-ecdsa-aes128-gcm-sha256 {
    base cipher-type;
  }

  identity ecdhe-rsa-aes128-sha256 {
    base cipher-type;
  }

  identity ecdhe-ecdsa-aes128-sha256 {
    base cipher-type;
  }

  identity ecdhe-rsa-aes128-sha {
    base cipher-type;
  }

  identity ecdhe-ecdsa-aes128-sha {
    base cipher-type;
  }

  identity dhe-dss-aes128-gcm-sha256 {
    base cipher-type;
  }

  identity dhe-rsa-aes128-gcm-sha256 {
    base cipher-type;
  }

  identity dhe-rsa-aes128-sha256 {
    base cipher-type;
  }

  identity dhe-dss-aes128-sha256 {
    base cipher-type;
  }

  identity dhe-rsa-aes128-sha {
    base cipher-type;
  }

  identity dhe-dss-aes128-sha {
    base cipher-type;
  }

  identity dhe-rsa-seed-sha {
    base cipher-type;
  }

  identity dhe-dss-seed-sha {
    base cipher-type;
  }

  identity dhe-rsa-camellia128-sha {
    if-feature "not (srl_nokia-feat:system-fips-mode)";
    base cipher-type;
  }

  identity dhe-dss-camellia128-sha {
    if-feature "not (srl_nokia-feat:system-fips-mode)";
    base cipher-type;
  }

  identity aes128-gcm-sha256 {
    base cipher-type;
  }

  identity aes128-sha256 {
    base cipher-type;
  }

  identity aes128-sha {
    base cipher-type;
  }

  identity seed-sha {
    base cipher-type;
  }

  identity camellia128-sha {
    if-feature "not (srl_nokia-feat:system-fips-mode)";
    base cipher-type;
  }

  identity psk-aes128-cbc-sha {
    base cipher-type;
  }

  identity ecdhe-rsa-des-cbc3-sha {
    base cipher-type;
  }

  identity ecdhe-ecdsa-des-cbc3-sha {
    base cipher-type;
  }

  identity edh-rsa-des-cbc3-sha {
    base cipher-type;
  }

  identity edh-dss-des-cbc3-sha {
    base cipher-type;
  }

  identity des-cbc3-sha {
    base cipher-type;
  }

  identity idea-cbc-sha {
    base cipher-type;
  }

  identity psk-3des-ede-cbc-sha {
    base cipher-type;
  }

  identity ecdhe-rsa-rc4-sha {
    base cipher-type;
  }

  identity ecdhe-ecdsa-rc4-sha {
    base cipher-type;
  }

  identity rc4-sha {
    base cipher-type;
  }

  identity psk-rc4-sha {
    base cipher-type;
  }

  grouping profile-interface {
    list profile {
      description
        "List of configured TLS profiles";
      key "name";
      leaf name {
        srl-ext:show-importance "high";
        type srl-comm:name {
          length "1..247";
        }
        description
          "Name of the TLS profile";
      }
      leaf key {
        srl-ext:show-importance "low";
        type string {
          length "0..10240";
          srl-ext:generated-class-name "SecretKey";
        }
        description
          "Base64 encoded key to use with the certificate

           This includes the '-----BEGIN PRIVATE KEY-----', and '-----END PRIVATE KEY-----' header and footer.
           The value is hashed, and only the hashed value is kept.";
      }
      leaf certificate {
        srl-ext:show-importance "low";
        type string {
          length "0..102400";
        }
        description
          "Base64 encoded certificate to use with the private key

           This includes the '-----BEGIN CERTIFICATE-----' and '-----END CERTIFICATE-----' header and footer.
           Can contain a certificate chain containing multiple certificates separated by '-----BEGIN CERTIFICATE-----'
           and '-----END CERTIFICATE-----' headers and footers. Must start with the client certificate.";
      }
      leaf use-tpm-devid {
        if-feature "srl_nokia-feat:tpm-idevid";
        type enumeration {
          enum idevid {
            value 1;
            description
              "The TPM iDevID key and certificate is used";
          }
          enum oidevid {
            if-feature "srl_nokia-feat:tpm-oidevid";
            value 2;
            description
              "The TPM iDevID key and oIDevID certificate is used";
          }
        }
        must 'not (../key or ../certificate)' {
          error-message "The TLS profile can only be configured with idevid or oidevid if the local key and certificate are not configured";
        }
        description
          "Defines if the TLS profile key and certificate uses the TPM idevid or oidevid";
      }
      leaf authenticate-client {
        default "false";
        srl-ext:show-importance "high";
        type boolean;
        description
          "Defines if the server should authenticate the identity of connecting clients using the trust anchor

           This is only applicable when the TLS profile is a server.  Client services will ignore this setting.";
      }
      leaf trust-anchor {
        type string {
          length "0..5242880";
        }
        srl-ext:show-importance "low";
        description
          "Base64 encoded certificate to use as a trust anchor

           This includes the '-----BEGIN CERTIFICATE-----' and '-----END CERTIFICATE-----' header and footer.
           Can contain multiple trust anchors separated by '-----BEGIN CERTIFICATE-----' and '-----END CERTIFICATE-----'
           headers and footers.";
      }
      leaf certificate-revocation-list {
        type string {
          length "0..5242880";
        }
        srl-ext:show-importance "low";
        description
          "Base64 encoded certificate revocation list

           This includes the '-----BEGIN X509 CRL' and '-----END X509 CRL' header and footer.
           Can contain multiple crls separated by '-----BEGIN X509 CRL' and '-----END X509 CRL' headers and footers.
           If empty, then no CRL verification is performed.";
      }
      leaf relaxed-crl-verification {
        type boolean;
        srl-ext:show-importance "low";
        default "false";
        description
          "Defines if the CRL verification is done in a relaxed (non-strict) way.

           If set to true, the CRL verification allows nonexistent and/or expired CRLs in the client certificate chain.
           If set to false, the CRL verification will fail if any CRL in the client certificate chain is not found or
           expired.";
      }
      leaf-list cipher-list {
        ordered-by user;
        srl-ext:show-importance "low";
        type identityref {
          base cipher-type;
        }
        default "ecdhe-ecdsa-aes256-gcm-sha384";
        default "ecdhe-ecdsa-aes128-gcm-sha256";
        default "ecdhe-rsa-aes256-gcm-sha384";
        default "ecdhe-rsa-aes128-gcm-sha256";
        description
          "List of ciphers to use when negotiating TLS 1.2 with clients

           TLS 1.3 cipher suites are always enabled:
               tls_aes_256_gcm_sha384, tls_aes_128_gcm_sha256, tls_chacha20_poly1305_sha256";
      }
      leaf dynamic {
        config false;
        srl-ext:show-importance "high";
        type boolean;
        description
          "Defines if the profile was dynamically created by service (for example gNSI Authz/Certz)";
      }
      leaf valid-after {
        if-feature "srl_nokia-feat:tls-cert-expiry";
        config false;
        type srl-comm:date-and-time;
        description
          "Date and time the certificate becomes valid";
      }
      leaf expiration {
        if-feature "srl_nokia-feat:tls-cert-expiry";
        config false;
        type srl-comm:date-and-time;
        description
          "Date and time the certificate expires";
      }
      leaf expired {
        if-feature "srl_nokia-feat:tls-cert-expiry";
        config false;
        type boolean;
        description
          "Indicates whether the certificate is expired.

           The certificate is expired if current time is before valid-after time or current
           time is after expiration time";
      }
    }
  }

  grouping tls-top {
    container tls {
      description
        "Enter the tls context

         Top-level container for TLS configuration and state";
      uses profile-interface;
    }
  }

  augment "/srl-system:system" {
    uses tls-top;
  }
}
