module srl_nokia-gnmi-server {
  yang-version 1.1;
  namespace "urn:srl_nokia/gnmi-server";
  prefix srl-gnmi-server;

  import srl_nokia-common {
    prefix srl-comm;
  }
  import srl_nokia-system {
    prefix srl-system;
  }
  import srl_nokia-network-instance {
    prefix srl-netinst;
  }
  import srl_nokia-tls {
    prefix srl-tls;
  }
  import srl_nokia-extensions {
    prefix srl-ext;
  }
  import srl_nokia-features {
    prefix srl-feat;
  }

  organization
    "Nokia";
  contact
    "Nokia SR Linux Support
     Web: <http://www.nokia.com>";
  description
    "This module defines configuration and operational state data related to the gnmi server.";

  revision 2023-10-31 {
    description
      "SRLinux 23.10.1";
  }
  revision 2023-07-31 {
    description
      "SRLinux 23.7.1";
  }
  revision 2023-03-31 {
    description
      "SRLinux 23.3.1";
  }
  revision 2022-06-30 {
    description
      "SRLinux 22.6.1";
  }
  revision 2022-03-31 {
    description
      "SRLinux 22.3.1";
  }
  revision 2021-03-31 {
    description
      "SRLinux 21.3.1";
  }
  revision 2020-06-30 {
    description
      "SRLinux 20.6.1";
  }
  revision 2019-11-30 {
    description
      "SRLinux 19.11.1";
  }

  identity grpc-service {
    description
      "Base identity for a gRPC-based service.";
  }

  identity gnmi {
    base grpc-service;
    description
      "gNMI: gRPC Network Management Interface";
  }

  identity gnoi {
    base grpc-service;
    description
      "gNOI: gRPC Network Operations Interface";
  }

  identity gnsi {
    if-feature "srl-feat:gnsi-authz";
    base grpc-service;
    description
      "gNSI: gRPC Network Security Interface";
  }

  grouping counters {
    description
      "A collection of counters that were collected while evaluating
       access to the gRPC server.";
    container counters {
      config false;
      description
        "A collection of counters that were collected by the gRPC during
         the authentication process.";
      leaf access-rejects {
        type uint64;
        description
          "The total number of times the gRPC denied access to the server.";
      }
      leaf last-access-reject {
        type srl-comm:date-and-time-delta;
        description
          "A timestamp of the last time the gRPC denied access to
           the server.";
      }
      leaf access-accepts {
        type uint64;
        description
          "The total number of times the gPRC allowed access to
           the server.";
      }
      leaf last-access-accept {
        type srl-comm:date-and-time-delta;
        description
          "A timestamp of the last time the gRPC allowed access to
           the server.";
      }
    }
  }

  grouping gnmi-common {
    leaf admin-state {
      type srl-comm:admin-state;
      srl-ext:show-importance "high";
      default "disable";
      description
        "Administratively enable or disable the gNMI server";
    }
    leaf oper-state {
      config false;
      type srl-comm:oper-state;
      srl-ext:show-importance "high";
      description
        "Details if the gNMI server is operationally available";
    }
    leaf use-authentication {
      type boolean;
      srl-ext:show-importance "high";
      default "true";
      description
        "Enable or disable the use of username/password authentication for every gNMI request";
    }
    leaf yang-models {
      if-feature "srl-feat:openconfig";
      type enumeration {
        enum native;
        enum openconfig;
      }
      srl-ext:show-importance "high";
      default "native";
      description
        "Specify yang-models to be used when origin field is not present in the gnmi requests";
    }
    leaf-list services {
      if-feature "srl-feat:gnmi-services";
      type identityref {
        base grpc-service;
      }
      description
        "The gRPC service definitions that should be enabled for the
         specified server. A target may support only specific
         sets of services being enabled on the same server (e.g.,
         it may be possible to run gNMI and gNOI services on the same
         port, but not to run gRIBI and gNMI on the same port).

         The set of gRPC services that are available to be configured is
         defined through the grpc-service identity, which can be extended
         for each protocol that is based on gRPC that is available on the
         device.";
    }
    leaf tls-profile {
      type leafref {
        path "/srl-system:system/srl-tls:tls/srl-tls:server-profile/srl-tls:name";
        require-instance false;
      }
      srl-ext:show-importance "high";
      description
        "Reference to the TLS profile to use on the gNMI server

         If none is specified, then TLS is not used.";
    }
    leaf default-tls-profile {
      if-feature "srl-feat:gnsi-authz";
      type boolean;
      srl-ext:show-importance "high";
      default "false";
      description
        "Whether to use default TLS profile (generated by the system) if none is configured via tls-profile field";
    }
  }

  grouping gnmi-socket {
    container unix-socket {
      description
        "Top-level container for configuration and state related to unix sockets";
      uses gnmi-common;
      leaf socket-path {
        srl-ext:show-importance "high";
        config false;
        type string;
        description
          "Path to the unix socket used by gNMI";
      }
    }
  }

  grouping gnmi-netinst {
    list network-instance {
      description
        "List of network instances to run a gNMI server in";
      key "name";
      uses gnmi-common;
      leaf name {
        type leafref {
          path "/srl-netinst:network-instance/srl-netinst:name";
        }
        must 'not(/srl-netinst:network-instance[srl-netinst:name=current()]/srl-netinst:type = "srl-netinst:mac-vrf")' {
          error-message "gNMI server cannot be started in a network-instance of type 'mac-vrf'";
        }
        description
          "Reference to a configured network instance";
      }
      leaf-list source-address {
        type srl-comm:ip-address;
        default "::";
        description
          "List of IP addresses the gNMI server will listen on within the network instance";
      }
      leaf port {
        type srl-comm:port-number;
        srl-ext:show-importance "high";
        default "57400";
        description
          "Port the gNMI server will listen on for incoming connections";
      }
      uses counters {
        if-feature "srl-feat:gnsi-certz";
      }
    }
  }

  grouping gnmi-traceoptions {
    description
      "Top-level grouping for gNMI trace options";
    leaf-list trace-options {
      description
        "gNMI trace options";
      type enumeration {
        enum request;
        enum response;
        enum common;
        enum grpc;
      }
    }
  }

  grouping gnmi-server-top {
    container gnmi-server {
      description
        "Configures the gNMI server access API";
      presence "Configures the gNMI server access API";
      leaf admin-state {
        type srl-comm:admin-state;
        default "disable";
        srl-ext:show-importance "high";
        description
          "Globally enable or disable the gNMI server
           Disabling this will disable all gNMI servers.";
      }
      uses gnmi-traceoptions;
      uses gnmi-netinst;
      uses gnmi-socket;
      leaf timeout {
        type uint16 {
          range "0..65535";
        }
        default "7200";
        srl-ext:show-importance "low";
        units "seconds";
        description
          "Set the idle timeout in seconds on gNMI connections";
      }
      leaf rate-limit {
        type uint16 {
          range "0..65535";
        }
        srl-ext:show-importance "low";
        default "60";
        description
          "Set a limit on the number of RPC calls per minute";
      }
      leaf session-limit {
        type uint16 {
          range "0..65535";
        }
        srl-ext:show-importance "low";
        default "20";
        description
          "Set a limit on the number of simultaneous active gNMI sessions

          A session is defined as an individual RPC invocation, which could result in a single client generating multiple sessions.
          In the context of a Subscribe RPC this is the number of simultaneously active SubscribeRequests across all Subscribe RPCs.";
      }
      leaf commit-confirmed-timeout {
        srl-ext:first-released "20.6.1";
        type uint32 {
          range "0..86400";
        }
        default "0";
        srl-ext:show-importance "low";
        units "seconds";
        description
          "Number of seconds to wait for confirmation. A value of 0 means commit confirmed is not used";
      }
      leaf commit-save {
        srl-ext:first-released "21.3.1";
        type boolean;
        default "false";
        srl-ext:show-importance "low";
        description
          "Specifies whether to save startup configuration after every successful commit";
      }
      leaf include-defaults-in-config-only-responses {
        srl-ext:first-released "20.6.4";
        type boolean;
        default "false";
        srl-ext:show-importance "low";
        description
          "Specifies whether to include field default values in get/subscribe responses when
           using configuration only datastore (for example running/intended datastore)";
      }
      list subscription {
        config false;
        description
          "List of subscriptions";
        key "id";
        leaf id {
          type uint32 {
            range "0..4294967295";
          }
          description
            "System generated ID for for the subscription";
        }
        leaf user {
          type string;
          srl-ext:show-importance "high";
          description
            "Authenticated username for the subscription";
        }
        leaf user-agent {
          type string;
          srl-ext:show-importance "low";
          description
            "User agent used for the subscription";
        }
        leaf remote-host {
          type srl-comm:ip-address;
          srl-ext:show-importance "high";
          description
            "Remote host of the subscription";
        }
        leaf remote-port {
          type srl-comm:port-number;
          srl-ext:show-importance "high";
          description
            "Remote port of the subscription";
        }
        leaf-list paths {
          type string;
          srl-ext:show-importance "low";
          description
            "List of paths being subscribed to";
        }
        leaf sample-interval {
          type uint64;
          srl-ext:show-importance "low";
          units "seconds";
          description
            "Time in seconds to provide updates to the remote host, set to 0 for all subscription modes except SAMPLE";
        }
        leaf mode {
          type enumeration {
            enum ON_CHANGE {
              value 1;
            }
            enum SAMPLE {
              value 2;
            }
            enum TARGET_DEFINED {
              value 3;
            }
            enum POLL {
              value 4;
            }
            enum ONCE {
              value 5;
            }
          }
          srl-ext:show-importance "low";
          description
            "Subscription mode (ON_CHANGE, SAMPLE, TARGET_DEFINED, POLL, ONCE)";
        }
        leaf start-time {
          type srl-comm:date-and-time-delta;
          srl-ext:show-importance "high";
          description
            "Time of the subscription creation";
        }
      }
    }
  }

  augment "/srl-system:system" {
    srl-ext:first-released "19.11.1";
    uses gnmi-server-top;
  }
}
