module srl_nokia-system-snmp {
  yang-version 1.1;
  namespace "urn:nokia.com:srlinux:linux:snmp";
  prefix srl_nokia-snmp;

  import srl_nokia-system {
    prefix srl-system;
  }
  import srl_nokia-network-instance {
    prefix srl-netinst;
  }
  import srl_nokia-common {
    prefix srl-comm;
  }
  import srl_nokia-features {
    prefix srl_nokia-feat;
  }
  import srl_nokia-extensions {
    prefix srl-ext;
  }

  organization
    "Nokia";
  contact
    "Nokia SR Linux Support
     Web: <http://www.nokia.com>";
  description
    "This module defines SNMP configuration and state";

  revision 2026-07-31 {
    description
      "SRLinux 26.7.1";
  }
  revision 2026-03-31 {
    description
      "SRLinux 26.3.1";
  }
  revision 2025-07-31 {
    description
      "SRLinux 25.7.1";
  }
  revision 2024-07-31 {
    description
      "SRLinux 24.7.1";
  }
  revision 2024-03-31 {
    description
      "SRLinux 24.3.1";
  }

  typedef engine-id {
    type srl-comm:hex-string {
      pattern '([0-9a-fA-F]){2}(:([0-9a-fA-F]){2}){4,31}';
    }
    description
      "The engine ID specified as a list of colon-specified
       hexadecimal octets, e.g., '80:00:02:b8:04:61:62:63'.";
    reference
      "RFC 3411: An Architecture for Describing Simple Network
         Management Protocol (SNMP) Management Frameworks";
  }

  typedef auth-protocol {
    type enumeration {
      enum hmac-md5-96 {
        description
          "MD5";
        reference
          "RFC3414";
      }
      enum hmac-sha1-96 {
        description
          "SHA";
        reference
          "RFC3414";
      }
      enum hmac-sha2-224 {
        description
          "SHA-224";
        reference
          "RFC7630";
      }
      enum hmac-sha2-256 {
        description
          "SHA-256";
        reference
          "RFC7630";
      }
      enum hmac-sha2-384 {
        description
          "SHA-384";
        reference
          "RFC7630";
      }
      enum hmac-sha2-512 {
        description
          "SHA-512";
        reference
          "RFC7630";
      }
    }
    description
      "Authentication protocol used for authenticated SNMPv3 messages";
  }

  typedef priv-protocol {
    type enumeration {
      enum cbc-des {
        description
          "DES";
        reference
          "RFC3414";
      }
      enum cfb128-aes-128 {
        description
          "AES";
        reference
          "RFC3826";
      }
      enum cfb128-aes-192 {
        description
          "AES-192";
        reference
          "draft-blumenthal-aes-usm-04";
      }
      enum cfb128-aes-256 {
        description
          "AES-256";
        reference
          "draft-blumenthal-aes-usm-04";
      }
    }
    description
      "Privacy protocol used for encrypted SNMPv3 messages";
  }

  typedef security-level {
    type enumeration {
      enum no-auth-no-priv;
      enum auth-no-priv;
      enum auth-priv;
    }
    description
      "Security level used for SNMPv3 messages";
  }

  grouping community-entry {
    leaf name {
      type srl-comm:name-without-space;
      description
        "Unique name for the SNMPv2 community";
    }
    leaf description {
      type srl-comm:description;
      description
        "Description for the SNMPv2 community";
    }
    leaf community {
      description
        "SNMPv2 community";
      type srl-comm:name-without-space {
        srl-ext:generated-class-name "SecretKey";
      }
      mandatory true;
    }
    leaf-list prefix-list {
      description
        "Prefixes where this community can be used, both IPv4 and IPv6 addresses

         A /32 or /128 mask can be used to limit it to a single ip-address.";
      type srl-comm:ip-prefix;
      ordered-by system;
      max-elements 16;
    }
  }

  grouping community-interface {
    list community-entry {
      key "name";
      description
        "List of configured SNMPv2 communities";
      uses community-entry;
      must "../security-level = 'no-auth-no-priv'" {
        error-message "SNMP communities can only be used in an access-group when security-level is set to 'no-auth-no-priv'";
      }
    }
  }

  grouping user-authentication {
    container authentication {
      description
        "Enter the authentication context

         Authentication parameters for this user";
      leaf protocol {
        type auth-protocol;
        default "hmac-md5-96";
        description
          "Authentication protocol used by this user";
      }
      leaf password {
        type string {
          srl-ext:generated-class-name "SecretKey";
          length "8..255";
        }
        mandatory true;
        description
          "User authentication password supplied either as cleartext or as a hashed value

           If provided as cleartext, the system will hash the value on input, storing only the hashed value.
           If provided as a hashed value, the value should include any '$' characters, for example '$ar2$aOvsuj0ALlU=$r750fMa3ZEA/Di8dIfU2fQ=='.";
      }
    }
  }

  grouping user-privacy {
    container privacy {
      description
        "Enter the privacy context

         Privacy parameters for this user";
      leaf protocol {
        type priv-protocol;
        default "cbc-des";
        description
          "Privacy protocol used by this user";
        must "not((../../authentication/protocol = 'hmac-md5-96') and (../../privacy/protocol = 'cfb128-aes-192'))" {
          error-message "Combination of hmac-md5-96 and cfb128-aes-192 isn't valid : authentication hash hasn't enough bytes (16) to be used as encryption key (24)";
        }
        must "not((../../authentication/protocol = 'hmac-md5-96') and (../../privacy/protocol = 'cfb128-aes-256'))" {
          error-message "Combination of hmac-md5-96 and cfb128-aes-256 isn't valid : authentication hash hasn't enough bytes (16) to be used as encryption key (32)";
        }
        must "not((../../authentication/protocol = 'hmac-sha1-96') and (../../privacy/protocol = 'cfb128-aes-192'))" {
          error-message "Combination of hmac-sha1-96 and cfb128-aes-192 isn't valid : authentication hash hasn't enough bytes (20) to be used as encryption key (24)";
        }
        must "not((../../authentication/protocol = 'hmac-sha1-96') and (../../privacy/protocol = 'cfb128-aes-256'))" {
          error-message "Combination of hmac-sha1-96 and cfb128-aes-256 isn't valid : authentication hash hasn't enough bytes (20) to be used as encryption key (32)";
        }
        must "not((../../authentication/protocol = 'hmac-sha2-224') and (../../privacy/protocol = 'cfb128-aes-256'))" {
          error-message "Combination of hmac-sha2-224 and cfb128-aes-256 isn't valid : authentication hash hasn't enough bytes (28) to be used as encryption key (32)";
        }
      }
      leaf password {
        type string {
          srl-ext:generated-class-name "SecretKey";
          length "8..255";
        }
        description
          "User privacy password, supplied either as cleartext or as a hashed value

            If not provided, authentication/password will be used.
            If provided as cleartext, the system will hash the value on input, storing only the hashed value.
            If provided as a hashed value, the value should include any '$' characters, for example '$ar2$aOvsuj0ALlU=$r750fMa3ZEA/Di8dIfU2fQ=='.";
      }
    }
  }

  grouping user-entry {
    leaf name {
      description
        "Unique name of the SNMPv3 security";
      type srl-comm:name-without-space;
    }
    leaf description {
      type srl-comm:description;
      description
        "Description for this user";
    }
    leaf user {
      description
        "User name used in SNMPv3 authentication and privacy";
      type srl-comm:name-without-space;
      mandatory true;
    }
    uses user-authentication;
    uses user-privacy;
  }

  grouping user-interface {
    list security-entry {
      key "name";
      description
        "List of configured SNMPv3 users";
      uses user-entry;
    }
  }

  grouping access-group-entry {
    leaf name {
      type srl-comm:name-without-space;
      description
        "Name of the SNMP access-group";
    }
    leaf description {
      type srl-comm:description;
      description
        "Description for this access-group";
    }
    leaf admin-state {
      type srl-comm:admin-state;
      default "enable";
      description
        "Enables the SNMP access-group";
    }
    uses community-interface;
    uses user-interface;
    leaf security-level {
      type security-level;
      mandatory true;
      description
        "Minimum security level required for this access-group";
    }
  }

  grouping access-group-interface {
    list access-group {
      if-feature "srl_nokia-feat:snmp-v3";
      description
        "List of configured SNMP access-groups";
      key "name";
      uses access-group-entry;
    }
  }

  grouping community-interface-destination {
    list community-entry {
      description
        "SNMPv2 community configured on this destination";
      key "name";
      max-elements 1;
      leaf name {
        type srl-comm:name-without-space;
        description
          "Unique name for the SNMP community on this destination";
      }
      leaf description {
        type srl-comm:description;
        description
          "Description for the SNMPv2 community";
      }
      leaf community {
        description
          "SNMPv2 community";
        type srl-comm:name-without-space {
          srl-ext:generated-class-name "SecretKey";
        }
        mandatory true;
      }
      must "../security-level = 'no-auth-no-priv'" {
        error-message "A SNMP community can only be used in a trap-group when security-level is set to 'no-auth-no-priv'";
      }
    }
  }

  grouping user-interface-destination {
    list security-entry {
      description
        "SNMPv3 security configured on this destination";
      key "name";
      max-elements 1;
      leaf name {
        description
          "Unique name of the SNMPv3 security";
        type srl-comm:name-without-space;
      }
      leaf description {
        type srl-comm:description;
        description
          "Description for this user";
      }
      leaf user {
        description
          "User name used in SNMPv3 authentication and privacy";
        type srl-comm:name-without-space;
        mandatory true;
      }
      uses user-authentication;
      uses user-privacy;
      leaf engine-id {
        type engine-id;
        description
          "Unique identifier for the SNMP engine of a trap sender

           If this leaf is not set, the local SNMP engine will be used. This also needs to
           be configured on the destination side.";
      }
    }
  }

  grouping destination-entry {
    leaf name {
      type srl-comm:name-without-space;
      description
        "Name of the SNMPv3 destination";
    }
    leaf description {
      type srl-comm:description;
      description
        "Description for this destination";
    }
    leaf admin-state {
      type srl-comm:admin-state;
      default "enable";
      description
        "Enables SNMP traps to this destination";
    }
    leaf address {
      type srl-comm:ip-address;
      mandatory true;
      description
        "Destination IP addresses for the SNMP trap";
    }
    leaf port {
      type srl-comm:port-number;
      default "162";
      description
        "Destination port for the SNMP trap";
    }
    leaf security-level {
      type security-level;
      mandatory true;
      description
        "Security level required for this destination";
    }
    choice authenticate-trap {
      mandatory true;
      description
        "Configuration to authenticate the SNMP trap to this destination";
      case community-entry {
        uses community-interface-destination;
      }
      case security-entry {
        uses user-interface-destination;
      }
    }
  }

  grouping destination-interface {
    list destination {
      key "name";
      description
        "List of configured SNMPv3 trap-destinations";
      uses destination-entry;
      max-elements 16;
    }
  }

  grouping trap-group-entry {
    leaf name {
      type srl-comm:name-without-space;
      description
        "Name of the SNMP trap-group";
    }
    leaf description {
      type srl-comm:description;
      description
        "Description for this trap-group";
    }
    leaf admin-state {
      type srl-comm:admin-state;
      default "enable";
      description
        "Enables the SNMP traps in the network-instance";
    }
    leaf network-instance {
      type leafref {
        path "/srl-system:system/srl_nokia-snmp:snmp/srl_nokia-snmp:network-instance/srl_nokia-snmp:name";
      }
      mandatory true;
      description
        "Reference to a network-instance configured for SNMP";
    }
    leaf source-address {
      type srl-comm:ip-address;
      default "::";
      description
        "IP address for the SNMP server to use as source-address within the network-instance";
    }
  }

  grouping trap-group-interface {
    list trap-group {
      if-feature "srl_nokia-feat:snmp-traps";
      description
        "List of configured SNMP trap-groups";
      key "name";
      uses trap-group-entry;
      uses destination-interface;
    }
  }

  grouping network-instance-entry-config {
    leaf admin-state {
      type srl-comm:admin-state;
      default "disable";
      description
        "Enables the SNMP server in this network-instance";
    }
    leaf-list listen-address {
      type srl-comm:ip-address;
      default "::";
      description
        "List of IP addresses for the SNMP server to listen on within the network-instance";
      max-elements 16;
    }
    leaf transport {
      if-feature "srl_nokia-feat:snmp-over-tcp";
      type enumeration {
        enum udp;
        enum tcp;
        enum both;
      }
      default "udp";
      description
        "Transport to be used for SNMP requests";
    }
    leaf engine-id {
      if-feature "srl_nokia-feat:snmp-v3";
      type engine-id;
      description
        "Local SNMP engine's administratively assigned unique identifier.

          If this leaf is not set, the device automatically calculates an engine ID,
          as described in RFC 3411.";
    }
  }

  grouping network-instance-entry-state {
    leaf oper-state {
      type srl-comm:oper-state;
      config false;
      description
        "Details the operational state of the SNMP server";
    }
    leaf error-msg {
      if-feature "srl_nokia-feat:snmp-traps";
      type string;
      config false;
      description
        "Indicates a possible error message if the snmp-server was stopped at runtime";
    }
    uses snmp-statistics;
  }

  grouping network-instance-entry {
    leaf name {
      type leafref {
        path "/srl-netinst:network-instance/srl-netinst:name";
      }
      must 'not(/srl-netinst:network-instance[srl-netinst:name=current()]/srl-netinst:type = "srl-netinst:mac-vrf")' {
        error-message "SNMP server cannot be started in a network-instance of type 'mac-vrf'";
      }
      description
        "Reference to a configured network-instance";
    }
    uses network-instance-entry-config;
    uses network-instance-entry-state;
  }

  grouping network-instance-interface {
    list network-instance {
      description
        "List of network-instances to run an SNMP server in";
      key "name";
      max-elements 5;
      uses network-instance-entry;
    }
  }

  grouping snmp-top {
    container snmp {
      if-feature "srl_nokia-feat:snmp";
      description
        "Top-level container for SNMP configuration and state";
      presence "Configure SNMP";
      uses access-group-interface;
      uses trap-group-interface;
      uses network-instance-interface;
    }
  }

  augment "/srl-system:system" {
    if-feature "not srl_nokia-feat:platform-imgmt";
    uses snmp-top;
  }

  grouping snmp-statistics {
    container statistics {
      if-feature "srl_nokia-feat:snmp-counters";
      config false;
      description
        "Enter the statistics context

         Container for snmp statistics, as defined by RFC 1213, RFC 3418, RFC 3414 and RFC 3412";
      leaf snmp-unknown-security-models {
        type srl-comm:zero-based-counter32;
        description
          "The total number of packets received by the SNMP
           engine which were dropped because they referenced a
           securityModel that was not known to or supported by
           the SNMP engine.";
      }
      leaf snmp-invalid-msgs {
        type srl-comm:zero-based-counter32;
        description
          "The total number of packets received by the SNMP
           engine which were dropped because there were invalid
           or inconsistent components in the SNMP message.";
      }
      leaf snmp-unknown-pdu-handlers {
        type srl-comm:zero-based-counter32;
        description
          "The total number of packets received by the SNMP
           engine which were dropped because the PDU contained
           in the packet could not be passed to an application
           responsible for handling the pduType, e.g. no SNMP
           application had registered for the proper
           combination of the contextEngineID and the pduType.";
      }
      leaf snmp-in-pkts {
        type srl-comm:zero-based-counter32;
        description
          "The total number of messages delivered to the SNMP
           entity from the transport service.";
      }
      leaf snmp-out-pkts {
        type srl-comm:zero-based-counter32;
        description
          "The total number of SNMP Messages which were
           passed from the SNMP protocol entity to the
           transport service.";
      }
      leaf snmp-in-bad-versions {
        type srl-comm:zero-based-counter32;
        description
          "The total number of SNMP messages which were delivered
           to the SNMP entity and were for an unsupported SNMP
           version.";
      }
      leaf snmp-in-bad-community-names {
        type srl-comm:zero-based-counter32;
        description
          "The total number of community-based SNMP messages (for
           example,  SNMPv1) delivered to the SNMP entity which
           used an SNMP community name not known to said entity.";
      }
      leaf snmp-in-bad-community-uses {
        type srl-comm:zero-based-counter32;
        description
          "The total number of community-based SNMP messages (for
           example, SNMPv1) delivered to the SNMP entity which
           represented an SNMP operation that was not allowed for
           the SNMP community named in the message.";
      }
      leaf snmp-in-asn-parse-errs {
        type srl-comm:zero-based-counter32;
        description
          "The total number of ASN.1 or BER errors encountered by
           the SNMP entity when decoding received SNMP messages.";
      }
      leaf snmp-in-gen-errs {
        type srl-comm:zero-based-counter32;
        description
          "The total number of SNMP PDUs which were
           delivered to the SNMP protocol entity and for
           which the value of the error-status field is
           'genErr'.";
      }
      leaf snmp-in-total-req-vars {
        type srl-comm:zero-based-counter32;
        description
          "The total number of MIB objects which have been
           retrieved successfully by the SNMP protocol entity
           as the result of receiving valid SNMP Get-Request
           and Get-Next PDUs.";
      }
      leaf snmp-in-get-requests {
        type srl-comm:zero-based-counter32;
        description
          "The total number of SNMP Get-Request PDUs which
           have been accepted and processed by the SNMP
           protocol entity.";
      }
      leaf snmp-in-get-nexts {
        type srl-comm:zero-based-counter32;
        description
          "The total number of SNMP Get-Next PDUs which have
           been accepted and processed by the SNMP protocol
           entity.";
      }
      leaf snmp-out-gen-errs {
        type srl-comm:zero-based-counter32;
        description
          "The total number of SNMP PDUs which were
           generated by the SNMP protocol entity and for
           which the value of the error-status field is
           'genErr'.";
      }
      leaf snmp-out-get-responses {
        type srl-comm:zero-based-counter32;
        description
          "The total number of SNMP Get-Response PDUs which
           have been generated by the SNMP protocol entity.";
      }
      leaf snmp-out-traps {
        type srl-comm:zero-based-counter32;
        description
          "The total number of SNMP Trap PDUs which have
           been generated by the SNMP protocol entity.";
      }
      leaf snmp-silent-drops {
        type srl-comm:zero-based-counter32;
        description
          "The total number of Confirmed Class PDUs (such as
           GetRequest-PDUs, GetNextRequest-PDUs,
           GetBulkRequest-PDUs, SetRequest-PDUs, and
           InformRequest-PDUs) delivered to the SNMP entity which
           were silently dropped because the size of a reply
           containing an alternate Response Class PDU (such as a
           Response-PDU) with an empty variable-bindings field
           was greater than either a local constraint or the
           maximum message size associated with the originator of
           the request.";
      }
      leaf usm-stats-unsupported-sec-levels {
        type srl-comm:zero-based-counter32;
        description
          "The total number of packets received by the SNMP
           engine which were dropped because they requested a
           securityLevel that was unknown to the SNMP engine
           or otherwise unavailable.";
      }
      leaf usm-stats-not-in-time-windows {
        type srl-comm:zero-based-counter32;
        description
          "The total number of packets received by the SNMP
           engine which were dropped because they appeared
           outside of the authoritative SNMP engine's window.";
      }
      leaf usm-stats-unknown-user-names {
        type srl-comm:zero-based-counter32;
        description
          "The total number of packets received by the SNMP
           engine which were dropped because they referenced a
           user that was not known to the SNMP engine.";
      }
      leaf usm-stats-unknown-engine-ids {
        type srl-comm:zero-based-counter32;
        description
          "The total number of packets received by the SNMP
           engine which were dropped because they referenced an
           snmpEngineID that was not known to the SNMP engine.";
      }
      leaf usm-stats-wrong-digests {
        type srl-comm:zero-based-counter32;
        description
          "The total number of packets received by the SNMP
           engine which were dropped because they didn't
           contain the expected digest value.";
      }
      leaf usm-stats-decryption-errors {
        type srl-comm:zero-based-counter32;
        description
          "The total number of packets received by the SNMP
           engine which were dropped because they could not be
           decrypted.";
      }
    }
  }

  grouping snmp-statistics-top {
    container snmp {
      description
        "Enter the snmp context

         Top-level container for SNMP statistics per network-instance";
      uses snmp-statistics;
    }
  }
}
