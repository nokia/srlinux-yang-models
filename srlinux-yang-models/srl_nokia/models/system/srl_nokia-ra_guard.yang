module srl_nokia-ra_guard {
  yang-version 1.1;
  namespace "urn:nokia.com:srlinux:fhs:ra_guard";
  prefix srl_nokia-ra_guard;

  import srl_nokia-common {
    prefix srl_nokia-comm;
  }
  import srl_nokia-extensions {
    prefix srl_nokia-ext;
  }
  import srl_nokia-interfaces {
    prefix srl_nokia-if;
  }
  import srl_nokia-interfaces-vlans {
    prefix srl_nokia-if-vlan;
  }
  import srl_nokia-system {
    prefix srl_nokia-system;
  }
  import srl_nokia-routing-policy {
    prefix srl_rpol;
  }
  import srl_nokia-features {
    prefix srl-feat;
  }

  organization
    "Nokia";
  contact
    "Nokia SR Linux Support
     Web: <http://www.nokia.com>";
  description
    "This yang file gives a description of sflow-agent
     configuration.";

  revision 2025-07-31 {
    description
      "SRLinux 25.7.1";
  }
  revision 2024-03-31 {
    description
      "SRLinux 24.3.1";
  }
  revision 2021-11-30 {
    description
      "SRLinux 21.11.1";
  }
  revision 2021-06-30 {
    description
      "SRLinux 21.6.1";
  }

  grouping ra_guard-top {
    list ra-guard-policy {
      if-feature "srl-feat:ra-guard";
      description
        "List containing RA Guard Policy and parameters";
      max-elements 64;
      key "name";
      leaf name {
        type srl_nokia-comm:name;
        description
          "RA Guard Policy name";
      }
      leaf action {
        type enumeration {
          enum accept;
          enum discard;
        }
        default "discard";
        description
          "Describes the RA Guard Policy action for RA Messages matching the specified attributes.
           RA Messages not matching the specified attributes will be handled in the opposite manner.";
      }
      leaf source-prefix-set {
        type leafref {
          path "/srl_rpol:routing-policy/srl_rpol:prefix-set/srl_rpol:name";
        }
        description
          "Reference to a prefix set to match RA source address.
           If not specified the verification is skipped.";
      }
      leaf hop-limit {
        type uint8 {
          range "1..255";
        }
        description
          "Verifies the minimum advertised hop count limit, RA message value must e equal to or greater than hop-limit.
           If not specified the verification is skipped.";
      }
      leaf managed-config-flag {
        type boolean;
        description
          "Causes the RA Guard policy to match IPv6 RA messages with the M (Managed address) flag set.
           If not specified the verification is skipped.";
      }
      leaf other-config-flag {
        type boolean;
        description
          "Causes the RA Guard policy to match IPv6 RA messages with the O (Other config) flag set.
           If not specified the verification is skipped.";
      }
      leaf advertise-prefix-set {
        type leafref {
          path "/srl_rpol:routing-policy/srl_rpol:prefix-set/srl_rpol:name";
        }
        description
          "Reference to a prefix set to match advertised address within RA message";
      }
      leaf router-preference {
        type enumeration {
          enum high;
          enum medium;
          enum low;
        }
        description
          "Verifies that the advertised default router preference parameter value is
           equal to or less than the specified limit.
           If not specified the verification is skipped.";
      }
    }
  }

  grouping interface-raguard-config {
    container ra-guard {
      if-feature "srl-feat:ra-guard";
      must "(starts-with(../../srl_nokia-if:name, 'ethernet') or starts-with(../../srl_nokia-if:name, 'lag') or starts-with(../../srl_nokia-if:name, 'mgmt0'))" {
        error-message "RA Guard not supported on the subinterface of this interface.";
      }
      presence "Context to configure RA Guard subinterface parameters";
      leaf policy {
        type leafref {
          path "/srl_nokia-system:system/srl_nokia-ra_guard:ra-guard-policy/name";
        }
        description
          "Reference to RA Guard Policy to apply to the associated subinterface";
      }
      list vlan-list {
        description
          "List of VLAN IDs that the RA policy should be matched against";
        key "vlan-id";
        leaf vlan-id {
          type uint16 {
            range "0..4095";
          }
          must "string(../../../srl_nokia-if-vlan:vlan/srl_nokia-if-vlan:encap/srl_nokia-if-vlan:single-tagged/srl_nokia-if-vlan:vlan-id) = 'optional' " {
            error-message "vlan-list not configurable when encap single-tagged optional not configured";
          }
        }
      }
    }
  }

  augment "/srl_nokia-system:system" {
    uses ra_guard-top;
  }

  augment "/srl_nokia-if:interface/srl_nokia-if:subinterface" {
    uses interface-raguard-config;
  }
}
