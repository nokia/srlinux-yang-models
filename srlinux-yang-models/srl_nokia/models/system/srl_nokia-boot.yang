module srl_nokia-boot {
  yang-version 1.1;
  namespace "urn:nokia.com:srlinux:chassis:boot";
  prefix srl-boot;

  import srl_nokia-system {
    prefix srl-system;
  }
  import srl_nokia-common {
    prefix srl-comm;
  }
  import srl_nokia-interfaces {
    prefix srl-if;
  }
  import srl_nokia-features {
    prefix srl_nokia-feat;
  }

  organization
    "Nokia";
  contact
    "Nokia SR Linux Support
     Web: <http://www.nokia.com>";
  description
    "This module defines configuration and operational state data related to the booting the system.";

  revision 2026-07-31 {
    description
      "SRLinux 26.7.1";
  }
  revision 2026-03-31 {
    description
      "SRLinux 26.3.1";
  }
  revision 2025-07-31 {
    description
      "SRLinux 25.7.1";
  }
  revision 2025-03-31 {
    description
      "SRLinux 25.3.1";
  }
  revision 2024-07-31 {
    description
      "SRLinux 24.7.1";
  }
  revision 2023-07-31 {
    description
      "SRLinux 23.7.1";
  }
  revision 2022-06-30 {
    description
      "SRLinux 22.6.1";
  }
  revision 2021-11-30 {
    description
      "SRLinux 21.11.1";
  }
  revision 2021-03-31 {
    description
      "SRLinux 21.3.1";
  }
  revision 2020-06-30 {
    description
      "SRLinux 20.6.1";
  }
  revision 2019-11-30 {
    description
      "SRLinux 19.11.1";
  }

  typedef client-id {
    type enumeration {
      enum serial {
        description
          "Use the chassis serial number as the client ID";
      }
    }
  }

  grouping boot-images-top {
    leaf-list image {
      type srl-comm:local-file-no-path;
      config false;
      max-elements 3;
      ordered-by user;
      description
        "Ordered list of local images used to boot the system

               This directly translates into boot configuration in grub, where the images are tried in the order specified by the user. Images are sourced via the internal SD card, and the value passed is the folder that contains the initramfs, kernel, and squashfs image. The search path for these directories is /mnt/nokiaos/<folder>";
    }
    leaf golden-image {
      if-feature "srl_nokia-feat:factory-reset";
      type srl-comm:local-file-no-path;
      config false;
      description
        "The local image the system reverts to when a factory reset operation is requested

         The value is the folder that contains the initramfs, kernel, and squashfs image.
         The search path for these directories is /mnt/nokiaos/<folder>";
    }
  }

  grouping boot-autoboot-top {
    container autoboot {
      description
        "Enter the autoboot context

         Top-level container for configuration and state data related to autobooting the system";
      leaf admin-state {
        type srl-comm:admin-state;
        description
          "Administratively enable or disable autoboot functionality";
      }
      leaf oper-state {
        type string;
        config false;
        description
          "The current operational status of the autoboot process";
      }
      leaf timeout {
        type uint32 {
          range "200 .. 3600";
        }
        units "seconds";
        description
          "Sets the timeout for each attempt to autoboot";
      }
      leaf attempts {
        type uint8 {
          range "1 .. 10";
        }
        description
          "Sets the amount of executions to try autoboot, before rebooting the system";
      }
      leaf-list interface {
        type leafref {
          path "/srl-if:interface/srl-if:name";
        }
        default "mgmt0";
        must "not (starts-with(. , 'mgmtA') or starts-with(. , 'mgmtB'))" {
          error-message "unsupported interface";
        }
        description
          "Sets the interface(s) to use for autoboot functionality";
      }
      leaf client-id {
        type client-id;
        description
          "The client ID to use on outgoing DHCP requests";
      }
      leaf-list mode {
        type enumeration {
          enum ztp {
            description
              "start ztp in normal mode. will attempt inband in case out of band fails";
          }
          enum secure {
            description
              "start ztp in secure mode. will attempt out of band connection to a secure bootstrap server";
          }
          enum inband {
            description
              "start ztp in inband mode. out-of-band will not run";
          }
          enum ooband {
            description
              "start ztp in out-of-band mode. inband will not run";
          }
          enum localdisk {
            description
              "start ztp using provisioning information available on a locally mounted disk";
          }
        }
      }
    }
  }

  grouping boot-fips-top {
    container fips-140 {
      description
        "Enter the fips-140 context

         Boot up the router in fips-provider mode

         In fips-provider mode only fips approved algorithms are allowed.
         In addition for fip-provider mode to take effect a reboot is of the router is needed.";
      leaf admin-state {
        type srl-comm:admin-state;
        default "disable";
        description
          "This leaf contains the configured, desired state of the fips-provider.";
      }
      leaf oper-state {
        config false;
        type srl-comm:oper-state;
        description
          "This leaf contains the operational state of fips-provider.";
      }
      leaf oper-down-reason {
        config false;
        type enumeration {
          enum unknown;
        }
        description
          "The reason for not enabling fips operational down";
      }
      leaf chassis-reboot-required {
        config false;
        type boolean;
        description
          "Reads true if the user has committed a change to configurable fips admin-state value and has not yet restarted chassis. The operational value is still the values initialized at the last chassis restart.";
      }
    }
  }

  grouping boot-password-top {
    description
      "Configuration and state for boot password.";
    leaf grub-password {
      description
        "The leaf container grub boot password";
      if-feature "srl_nokia-feat:grub-password";
      type srl-comm:grub-password;
    }
  }

  grouping boot-bootzstate-top {
    container bootz {
      description
        "Enter the bootz context

         Bootz info";
      container status {
        description
          "Enter the status context

           Bootz state ";
        leaf bootstate {
          config false;
          type string;
        }
        leaf bootstate-timestamp {
          config false;
          description
            "The timestamp of the last bootz state";
          type srl-comm:date-and-time;
        }
      }
    }
  }

  grouping boot-top {
    container boot {
      description
        "Enter the boot context

         Top-level container for configuration and state data related to booting the system";
      uses boot-images-top;
      uses boot-fips-top;
      uses boot-autoboot-top;
      uses boot-password-top;
      uses boot-bootzstate-top;
    }
  }

  augment "/srl-system:system" {
    uses boot-top;
  }
}
