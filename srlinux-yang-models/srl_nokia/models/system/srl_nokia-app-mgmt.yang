module srl_nokia-app-mgmt {
  yang-version 1.1;
  namespace "urn:nokia.com:srlinux:app:app-mgmt";
  prefix srl_nokia-app-mgmt;

  import srl_nokia-system {
    prefix srl-system;
  }
  import srl_nokia-extensions {
    prefix srl-ext;
  }
  import srl_nokia-common {
    prefix srl-comm;
  }
  import srl_nokia-features {
    prefix srl-feat;
  }

  organization
    "Nokia";
  contact
    "Nokia SR Linux Support
     Web: <http://www.nokia.com>";
  description
    "This module defines application management.";

  revision 2026-07-31 {
    description
      "SRLinux 26.7.1";
  }
  revision 2025-07-31 {
    description
      "SRLinux 25.7.1";
  }
  revision 2025-03-31 {
    description
      "SRLinux 25.3.1";
  }
  revision 2022-03-31 {
    description
      "SRLinux 22.3.1";
  }
  revision 2021-03-31 {
    description
      "SRLinux 21.3.1";
  }
  revision 2019-11-30 {
    description
      "SRLinux 19.11.1";
  }

  typedef start-type {
    type enumeration {
      enum hot {
        description
          "A hot start indicates that the application has synchronized with a redundant peer, and took over from the peer during a switchover

           This type results in least amount of disruption to the corresponding service and functionality.";
      }
      enum warm {
        description
          "A warm start indicates that the application will leave state in IDB during a restart, and recover it post restart

           This type results in less disruption to surrounding applications and functionality.";
      }
      enum cold {
        description
          "A cold start indicates that the application will not leave state in IDB during a restart

           This type is equivalent to a normal application restart, i.e. one where the application's state is purged from the system during the restart, and recreated after.";
      }
    }
  }

  typedef synchronization-state {
    type enumeration {
      enum synchronized {
        description
          "This application has synchronized

           For applications that support hot redundancy, this state indicates that the application has synchronized with its redundant peer, and is ready to take over in the event of a switchover.
           For applications that support warm redundancy, this state indicates that the application has synchronized with its IDB, and is ready to recover its state post restart.";
      }
      enum not-synchronized {
        description
          "This application supports either warm or hot redundancy, but has not synchronized yet, and is not in a state where a switchover can occur";
      }
      enum not-applicable {
        description
          "This application does not support either warm or hot restart";
      }
    }
  }

  typedef restricted-operation-type {
    type enumeration {
      enum restart {
        description
          "This application may not be restarted manually";
      }
      enum stop {
        description
          "This application may not be stopped manually";
      }
      enum start {
        description
          "This application may not be started manually";
      }
      enum reload {
        description
          "This application may not be reloaded manually";
      }
      enum quit {
        description
          "This application may not be terminated manually";
      }
      enum kill {
        description
          "This application may not be terminated ungracefully manually";
      }
    }
  }

  typedef application-state-type {
    type enumeration {
      enum running {
        description
          "Application instance is running

           This is the normal, active state of an application";
      }
      enum waiting-for-config {
        description
          "Application instance is loaded, but has no configuration

           This state requires wait-for-config true within the applications YAML configuration. This results in the application being loaded into app-mgr, but not starting until the system receives configuration for it";
      }
      enum error {
        description
          "The application has not started successfully, or has failed

           This state can be caused by an application hitting the restart backoff, or an application failing to start following triggering a system reboot";
      }
      enum starting {
        description
          "The application has been asked to start

           All applications enter this state after initial execution, after which application manager will wait five seconds before checking their status. IDB connected applications may announce their state before this five second window has passed, resulting in them transitioning from this state faster than PID-monitored applications.";
      }
      enum stopped {
        description
          "The application is not running

           This state is most likely caused by an operator action";
      }
    }
  }

  grouping app-mgmt-state-yang-top {
    description
      "YANG associated with a specific application instance";
    container yang {
      config false;
      description
        "Enter the yang context

         Top-level container for application state related to YANG";
      leaf-list modules {
        type string;
        description
          "YANG module names used by this application instance";
      }
      leaf-list source-directories {
        type string;
        description
          "Source directories searched for YANG modules to load

           These directories are used to load modules indicated in the modules leaf, and any modules imported/included within them";
      }
    }
  }

  grouping app-mgmt-state-stats-top {
    description
      "Top-level container for application statistics";
    container statistics {
      description
        "Enter the statistics context

         Top-level container for application statistics";
      leaf restart-count {
        type srl-comm:zero-based-counter32;
        description
          "The number of times this application instance has restarted";
      }
      action clear {
        if-feature "srl-feat:tools-as-modeled-actions-same-output";
        description
          "Clear statistics for this application instance";
      }
    }
  }

  grouping app-mgmt-state-top {
    description
      "State related to application management";
    leaf pid {
      srl-ext:show-importance "high";
      type uint32;
      description
        "Process ID of this application instance";
    }
    leaf state {
      srl-ext:show-importance "high";
      type application-state-type;
      description
        "Current state of this application instance";
    }
    leaf synchronization-state {
      if-feature "srl-feat:application-hot-restart";
      srl-ext:show-importance "high";
      type synchronization-state;
      description
        "Indicates if this application is available for a warm or hot restart

         An application supports either hot or warm restarts, not both.";
    }
    leaf last-change {
      srl-ext:show-importance "high";
      type srl-comm:date-and-time-delta;
      description
        "Date and time the application instance last changed state";
    }
    leaf last-start-type {
      srl-ext:show-importance "high";
      type start-type;
      description
        "Indicates the type of the most recent start or restart of this application instance";
    }
    leaf-list supported-restart-types {
      type start-type;
      description
        "Indicates the supported restart types for this application";
    }
    leaf author {
      srl-ext:show-importance "high";
      type string;
      description
        "The author of the application";
    }
    leaf failure-threshold {
      srl-ext:show-importance "low";
      type uint8 {
        range "0..255";
      }
      description
        "How many restarts within 'failure-window' are required to trigger the failure action

         Setting this value to 0 will result in no action taking place on application restarts";
    }
    leaf failure-window {
      srl-ext:show-importance "low";
      type uint32 {
        range "300..86400";
      }
      units "seconds";
      description
        "Sliding window in seconds, over which to count restarts towards failure-threshold";
    }
    leaf failure-action {
      srl-ext:show-importance "low";
      type string {
        pattern '(reboot|wait=(forever|\d*))';
      }
      description
        "The action taken after 'failure-threshold' failures within 'failure-window'

         This action can be to reboot the system, wait forever, or wait for a predefined number of seconds";
    }
    leaf path {
      srl-ext:show-importance "low";
      type string;
      description
        "The directory where the application can be found";
    }
    leaf launch-command {
      srl-ext:show-importance "low";
      type string;
      description
        "The command used to launch the application";
    }
    leaf search-command {
      srl-ext:show-importance "low";
      type string;
      description
        "The command used to search for the applications liveness";
    }
    leaf version {
      srl-ext:show-importance "low";
      type string;
      description
        "The version of the application";
    }
    leaf-list restricted-operations {
      srl-ext:show-importance "low";
      type restricted-operation-type;
      description
        "The operations that may not be manually performed on this application";
    }
    leaf oom-score-adj {
      srl-ext:show-importance "low";
      type int32;
      description
        "OOM score adj value set for this application";
    }
    leaf cgroup {
      srl-ext:show-importance "low";
      type string;
      description
        "Cgroup in with this application is started";
    }
    uses app-mgmt-state-stats-top;
    uses app-mgmt-state-yang-top;
  }

  grouping app-mgmt-signal-output {
    leaf sent-signal {
      type uint32;
      description
        "The Linux signal number that was sent to the application instance";
    }
    leaf sent-signal-name {
      type string;
      description
        "The symbolic name of the Linux signal that was sent to the application instance";
    }
  }

  grouping app-mgmt-delayed-output {
    leaf delayed {
      type boolean;
      description
        "Indicates that the (re)start of the application instance was deferred and will occur asynchronously";
    }
  }

  grouping app-mgmt-application-action {
    action stop {
      if-feature "srl-feat:tools-as-modeled-actions-same-output";
      description
        "Terminate the application instance gracefully";
      output {
        uses app-mgmt-signal-output;
      }
    }
    action start {
      if-feature "srl-feat:tools-as-modeled-actions-same-output";
      description
        "Start the application instance";
      output {
        uses app-mgmt-delayed-output;
      }
    }
    action restart {
      if-feature "srl-feat:tools-as-modeled-actions-same-output";
      description
        "Restart the application instance

         The best restart that is supported by the application is used if neither 'warm' or 'cold' is specified. If 'warm' restart is supported that will be used, or 'cold' if 'warm' is unavailable.

         A 'warm' restart will result in the application leaving its state in IDB during the restart, and recovering it post restart. This restart type results in less disruption to surrounding applications that would depend on the restarting applications state.

         A 'cold' restart will result in a normal stop/start of the application, including the purging of its state in IDB.";
      input {
        leaf warm {
          type empty;
          description
            "Perform a warm restart of the application instance";
        }
        leaf cold {
          type empty;
          description
            "Perform a cold restart of the application instance";
        }
      }
      output {
        uses app-mgmt-signal-output;
        uses app-mgmt-delayed-output;
      }
    }
    action reload {
      if-feature "srl-feat:tools-as-modeled-actions-same-output";
      description
        "Reload the configuration of the application instance";
      output {
        uses app-mgmt-signal-output;
      }
    }
    action quit {
      if-feature "srl-feat:tools-as-modeled-actions-same-output";
      description
        "Terminate the application instance, requesting it to core dump";
      output {
        uses app-mgmt-signal-output;
      }
    }
    action kill {
      if-feature "srl-feat:tools-as-modeled-actions-same-output";
      description
        "Terminate the application instance ungracefully";
      output {
        uses app-mgmt-signal-output;
      }
    }
  }

  grouping app-mgmt-top {
    container app-management {
      description
        "Enter the app-management context

         Top-level container for application configuration and state";
      config false;
      list application {
        description
          "List of all applications managed by the application manager";
        key "name";
        leaf name {
          type string;
          description
            "Unique name of this application instance";
        }
        uses app-mgmt-state-top;
        uses app-mgmt-application-action;
      }
    }
  }

  augment "/srl-system:system" {
    uses app-mgmt-top;
  }
}
