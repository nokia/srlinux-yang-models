module srl_nokia-dns {
  yang-version 1.1;
  namespace "urn:nokia.com:srlinux:linux:dns";
  prefix srl_nokia-dns;

  import srl_nokia-system {
    prefix srl-system;
  }
  import srl_nokia-network-instance {
    prefix srl-netinst;
  }
  import srl_nokia-common {
    prefix srl-comm;
  }
  import srl_nokia-extensions {
    prefix srl-ext;
  }
  import srl_nokia-features {
    prefix srl_nokia-feat;
  }

  organization
    "Nokia";
  contact
    "Nokia SR Linux Support
     Web: <http://www.nokia.com>";
  description
    "This module defines DNS configuration";

  revision 2026-07-31 {
    description
      "SRLinux 26.7.1";
  }
  revision 2026-03-31 {
    description
      "SRLinux 26.3.1";
  }
  revision 2025-03-31 {
    description
      "SRLinux 25.3.1";
  }
  revision 2024-10-31 {
    description
      "SRLinux 24.10.1";
  }
  revision 2024-03-31 {
    description
      "SRLinux 24.3.1";
  }
  revision 2022-11-30 {
    description
      "SRLinux 22.11.1";
  }
  revision 2020-06-30 {
    description
      "SRLinux 20.6.1";
  }
  revision 2019-11-30 {
    description
      "SRLinux 19.11.1";
  }

  grouping host-entry-variables {
    description
      "List of static host entries";
    leaf name {
      type srl-comm:domain-name;
      description
        "Name of host entry";
    }
    leaf-list ipv4-address {
      type srl-comm:ipv4-address;
      description
        "List of IPv4 addresses for the host entry";
    }
    leaf-list ipv6-address {
      type srl-comm:ipv6-address;
      description
        "List of IPv6 addresses for the host entry";
    }
  }

  grouping host-entry-interface {
    description
      "List of static host entries";
    list host-entry {
      key "name";
      description
        "List of static host entries";
      uses host-entry-variables;
    }
  }

  grouping dns-instance-top {
    leaf oper-state {
      type srl-comm:oper-state;
      config false;
      description
        "Details the operational state of the DNS client";
    }
    leaf-list search-list {
      type srl-comm:domain-name;
      description
        "An ordered list of domains to search when resolving a host name";
      ordered-by user;
    }
    leaf-list server-list {
      type srl-comm:ip-address;
      description
        "List of the DNS servers that the resolver should query";
      max-elements 3;
      ordered-by user;
    }
    leaf network-instance {
      if-feature "not srl_nokia-feat:platform-imgmt";
      type leafref {
        path "/srl-netinst:network-instance/srl-netinst:name";
      }
      must 'not(/srl-netinst:network-instance[srl-netinst:name=current()]/srl-netinst:type = "srl-netinst:mac-vrf")' {
        error-message "DNS client cannot be started in a network-instance of type 'mac-vrf'";
      }
      mandatory true;
      description
        "Reference to a configured network-instance to source DNS requests from";
    }
    leaf source-address {
      type srl-comm:ip-address;
      description
        "Source address for DNS to use for messages sent to a remote server";
    }
    uses host-entry-interface;
  }

  grouping dns-top {
    list dns-instance {
      key "name";
      leaf name {
        type srl-comm:restricted-name;
        srl-ext:show-importance "high";
        description
          "User-provided name for DNS instance";
      }
      unique "network-instance";
      uses dns-instance-top;
      max-elements 8;
    }
  }

  augment "/srl-system:system" {
    uses dns-top {
      if-feature "not srl_nokia-feat:platform-imgmt";
    }
  }
}
