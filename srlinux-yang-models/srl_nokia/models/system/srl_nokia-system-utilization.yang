module srl_nokia-system-utilization {
  yang-version 1.1;
  namespace "urn:nokia.com:srlinux:linux:system-utilization";
  prefix srl_nokia-sys-util;

  import srl_nokia-system {
    prefix srl-system;
  }
  import srl_nokia-common {
    prefix srl_nokia-comm;
  }
  import srl_nokia-features {
    prefix srl_nokia-feat;
  }

  organization
    "Nokia";
  contact
    "Nokia SR Linux Support
     Web: <http://www.nokia.com>";

  revision 2026-07-31 {
    description
      "SRLinux 26.7.1";
  }
  revision 2026-03-31 {
    description
      "SRLinux 26.3.1";
  }
  revision 2025-10-31 {
    description
      "SRLinux 25.10.1";
  }
  revision 2025-07-31 {
    description
      "SRLinux 25.7.1";
  }
  revision 2024-10-31 {
    description
      "SRLinux 24.10.1";
  }

  identity system-resources {
    description
      "Base type for system-wide resources managed by control plane applications";
  }

  identity acl-system-resources {
    description
      "Base type for system-wide Acl resources managed by control plane applications";
  }

  identity qos-system-resources {
    description
      "Base type for system-wide QoS resources managed by control plane applications";
  }

  identity mpls-next-hops {
    base system-resources;
    if-feature "srl_nokia-feat:system-resource-mpls-next-hops";
    description
      "MPLS next hop label forwarding entry resources

       Each MPLS next-hop that pushes an outgoing label stack uses one of these resources";
  }

  identity tunnels {
    base system-resources;
    if-feature "srl_nokia-feat:system-resource-tunnels";
    description
      "Tunnel resources

       Each IP-in-IP, GRE or MPLS tunnel uses one of these resources";
  }

  identity ip-in-ip-tunnels {
    base system-resources;
    if-feature "srl_nokia-feat:system-resource-ip-in-ip-tunnels";
    description
      "IP-in-IP tunnel resources

       Each originating IP-in-IP tunnel uses one of these resources";
  }

  identity ip-gre-tunnels {
    base system-resources;
    if-feature "srl_nokia-feat:system-resource-ip-gre-tunnels";
    description
      "IP-over-GRE tunnel resources

       Each originating IP-over-GRE tunnel uses one of these resources";
  }

  identity ip-udp-tunnels {
    base system-resources;
    if-feature "srl_nokia-feat:udp-tunnel";
    description
      "UDP tunnel resources

       Each originating UDP tunnel uses one of these resources";
  }

  identity vp-lag-groups {
    base system-resources;
    if-feature "srl_nokia-feat:system-resource-vp-lag-groups";
    description
      "VP LAG group resources

       VP LAGs are needed by a NHG when it supports EVPN multi-homing";
  }

  identity protect-groups {
    base system-resources;
    if-feature "srl_nokia-feat:system-resource-pg-groups";
    description
      "Protect group IDs

       Each primary next-hop that needs fast failover to a backup next-hop needs a protect-group ID";
  }

  identity mcast-rpf-indices {
    base system-resources;
    if-feature "srl_nokia-feat:system-resource-mcast-rpf-indices";
    description
      "P2MP RPF Index";
  }

  identity vxlan-tunnels {
    base system-resources;
    if-feature "srl_nokia-feat:system-resource-vxlan-tunnels and srl_nokia-feat:vxlan";
    description
      "VXLAN tunnel resources

       Each originating VXLAN tunnel uses one of these resources";
  }

  identity ingress-labeled-tunnel-statistics {
    base system-resources;
    if-feature "srl_nokia-feat:labeled-tunnel-statistics";
    description
      "Ingress labeled tunnel statistics resources

       Each ingress tunnel (e.g. segment-list) so as iLM forwarding entries uses one of these resources";
  }

  identity egress-labeled-tunnel-statistics {
    base system-resources;
    if-feature "srl_nokia-feat:labeled-tunnel-statistics";
    description
      "Egress labeled tunnel statistics resources

       Each engress tunnel (e.g. segment-list) so as NHLFE forwarding entries uses one of these resources";
  }

  identity multicast-ppmc-indices {
    base system-resources;
    if-feature "srl_nokia-feat:system-resource-multicast-ppmc-indices";
    description
      "PPMC indices for multicast users";
  }

  identity output-ipv4-filter-instances {
    if-feature "srl_nokia-feat:system-resource-acl-ip-filter-instances-general";
    base acl-system-resources;
    description
      "This resource is used every time an IPv4 filter instance is created and applied to egress traffic on the forwarding complex. Only one instance is used if the subinterface-specific property of the filter is set to input-only; otherwise one instance is used for every subinterface using the IPv4 filter as an egress filter.";
  }

  identity output-ipv4-filter-instances-routed {
    if-feature "srl_nokia-feat:system-resource-acl-ip-filter-instances-routed-bridged";
    base acl-system-resources;
    description
      "This resource is used every time an IPv4 filter instance is created and applied to egress traffic on routed subinterfaces. Only one instance is used if the subinterface-specific property of the filter is set to input-only; otherwise one instance is used for every routed subinterface using the IPv4 filter.";
  }

  identity output-ipv4-filter-instances-bridged {
    if-feature "srl_nokia-feat:system-resource-acl-ip-filter-instances-routed-bridged";
    base acl-system-resources;
    description
      "This resource is used every time an IPv4 filter instance is created and applied to egress traffic on bridged subinterfaces. Only one instance is used if the subinterface-specific property of the filter is set to input-only; otherwise one instance is used for every bridged subinterface using the IPv4 filter.";
  }

  identity output-ipv4-ipv6-filter-instances {
    if-feature "srl_nokia-feat:system-resource-acl-ipv4-ipv6-filter-instances";
    base acl-system-resources;
    description
      "This resource is used every time an IPv4 or IPv6 filter instance is created and applied to egress traffic on the forwarding complex. Only one instance is used if the subinterface-specific property of the filter is set to input-only; otherwise one instance is used for every subinterface using the IPv4 or IPv6 filter.";
  }

  identity output-ipv6-filter-instances {
    if-feature "srl_nokia-feat:system-resource-acl-ip-filter-instances-general";
    base acl-system-resources;
    description
      "This resource is used every time an IPv6 filter instance is created and applied to egress traffic on the forwarding complex. Only one instance is used if the subinterface-specific property of the filter is set to input-only; otherwise one instance is used for every subinterface using the IPv6 filter as an egress filter.";
  }

  identity output-ipv6-filter-instances-routed {
    if-feature "srl_nokia-feat:system-resource-acl-ip-filter-instances-routed-bridged";
    base acl-system-resources;
    description
      "This resource is used every time an IPv6 filter instance is created and applied to egress traffic on routed subinterfaces. Only one instance is used if the subinterface-specific property of the filter is set to input-only; otherwise one instance is used for every routed subinterface using the IPv6 filter.";
  }

  identity output-ipv6-filter-instances-bridged {
    if-feature "srl_nokia-feat:system-resource-acl-ip-filter-instances-routed-bridged";
    base acl-system-resources;
    description
      "This resource is used every time an IPv6 filter instance is created and applied to egress traffic on bridged subinterfaces. Only one instance is used if the subinterface-specific property of the filter is set to input-only; otherwise one instance is used for every bridged subinterface using the IPv6 filter.";
  }

  identity output-mac-filter-instances {
    if-feature "srl_nokia-feat:system-resource-acl-mac-filter-instances";
    base acl-system-resources;
    description
      "This resource is used every time an MAC filter instance is created and applied to egress traffic on the forwarding complex. Only one instance is used if the subinterface-specific property of the filter is set to input-only; otherwise one instance is used for every subinterface using the MAC filter as an egress filter.";
  }

  identity lag-bundle {
    base qos-system-resources;
    if-feature "srl_nokia-feat:qos-lag-subinterface-queuing";
    description
      "LAG bundle IDs pool resources

       Required by subinterfaces on LAGs when per-subinterface queueing QoS is configured";
  }

  identity voq-set {
    base qos-system-resources;
    if-feature "srl_nokia-feat:qos-subinterface-queuing";
    description
      "VOQ IDs resources

       Required by subinterfaces on normal ports and LAGs when per-subinterface queueing QoS is configured";
  }

  identity voq-set-statistics {
    base qos-system-resources;
    if-feature "srl_nokia-feat:qos-subinterface-queuing";
    description
      "VOQ stat IDs resources

       Required by interface and subinterface when voq statistics are enabled for normal ports and LAG";
  }

  grouping resource-state-details {
    leaf upper-threshold-set {
      type srl_nokia-comm:percentage;
      default "90";
      description
        "Sets the threshold that triggers the generation of a WARNING log and the setting of 'used-upper-threshold-exceeded' to 'true' whenever the utilization of the resource reaches this value in a rising direction";
    }
    leaf upper-threshold-clear {
      type srl_nokia-comm:percentage;
      default "70";
      description
        "Sets the threshold that triggers the generation of a NOTICE log and the setting of 'used-upper-threshold-exceeded' to 'false' whenever the utilization of the resource reaches this value in a falling direction";
    }
    leaf used-percent {
      config false;
      type srl_nokia-comm:percentage;
      description
        "The percentage of the resource that is currently used";
    }
    leaf used-entries {
      config false;
      type uint32;
      description
        "The number of entries that are currently used";
    }
    leaf free-entries {
      config false;
      type uint32;
      description
        "The number of entries that are currently free";
    }
    leaf used-high-watermark {
      config false;
      type uint32;
      description
        "A watermark of highest number of entries used for this resource";
    }
    leaf used-last-high-watermark-time {
      config false;
      type srl_nokia-comm:date-and-time-delta;
      description
        "The timestamp when the high-watermark was last updated";
    }
    leaf used-upper-threshold-exceeded {
      config false;
      type boolean;
      description
        "This value is set to true when the used percentage value (used / (used + free) * 100) has reached (in a rising direction) the configured upper-threshold-set for this resource and false when the used percentage value has reached (in a falling direction) the configured upper-threshold-clear for this resource";
    }
  }

  grouping system-resource-utilization {
    container utilization {
      description
        "Enter the utilization context

         Configuration and state for each system resource";
      container acl {
        if-feature "srl_nokia-feat:system-resource-utilization-acl";
        list resource {
          description
            "List of Acl system-wide resources";
          key "name";
          leaf name {
            type identityref {
              base acl-system-resources;
            }
            description
              "The name of the resource";
          }
          uses resource-state-details;
        }
        description
          "Enter the acl context";
      }
      container qos {
        if-feature "srl_nokia-feat:system-resource-utilization-qos";
        list resource {
          description
            "List of qos system-wide resources";
          key "name";
          leaf name {
            type identityref {
              base qos-system-resources;
            }
            description
              "The name of the resource";
          }
          uses resource-state-details;
        }
        description
          "Enter the qos context";
      }
      list resource {
        description
          "List of system-wide resources";
        key "name";
        leaf name {
          type identityref {
            base system-resources;
          }
          description
            "The name of the resource";
        }
        uses resource-state-details;
      }
    }
  }

  augment "/srl-system:system" {
    if-feature "srl_nokia-feat:system-resource-utilization";
    uses system-resource-utilization;
  }
}
