module srl_nokia-ntp-server {
  yang-version 1.1;
  namespace "urn:nokia.com:srlinux:linux:ntp-server";
  prefix srl_nokia-ntp-server;

  import srl_nokia-system {
    prefix srl-system;
  }
  import srl_nokia-network-instance {
    prefix srl-netinst;
  }
  import srl_nokia-common {
    prefix srl-comm;
  }
  import srl_nokia-extensions {
    prefix srl-ext;
  }
  import srl_nokia-features {
    prefix srl_nokia-feat;
  }

  organization
    "Nokia";
  contact
    "Nokia SR Linux Support
     Web: <http://www.nokia.com>";
  description
    "This module defines NTP server configuration and state";

  revision 2026-07-31 {
    description
      "SRLinux 26.7.1";
  }

  grouping ntp-server-instance-top {
    leaf admin-state {
      type srl-comm:admin-state;
      default "disable";
      description
        "Enable or disable the NTP server instance";
    }
    leaf oper-state {
      type srl-comm:oper-state;
      config false;
      description
        "Operational state of the NTP server instance";
    }
    leaf network-instance {
      if-feature "not srl_nokia-feat:platform-imgmt";
      type leafref {
        path "/srl-netinst:network-instance/srl-netinst:name";
      }
      mandatory true;
      must 'not(/srl-netinst:network-instance[srl-netinst:name=current()]/srl-netinst:type = "srl-netinst:mac-vrf")' {
        error-message "NTP server cannot be started in a network-instance of type 'mac-vrf'";
      }
      description
        "Network instance to run the NTP server in";
    }
    leaf local-reference {
      type boolean;
      default "false";
      description
        "NTP server will appear synchronized to downstream clients even when upstream source not available";
    }
    leaf-list source-address {
      type srl-comm:ip-address;
      description
        "List of IP addresses for the NTP server to listen on within the network-instance";
    }
    leaf-list allow-subnet {
      type srl-comm:ip-prefix;
      description
        "List of IP subnets (IP address and mask) to allow NTP requests from";
    }
    leaf port {
      type srl-comm:port-number;
      srl-ext:show-importance "high";
      default "123";
      description
        "Port the NTP server instance will listen on for incoming connections";
    }
  }

  grouping ntp-server-top {
    list ntp-server {
      key "name";
      leaf name {
        type srl-comm:restricted-name;
        srl-ext:show-importance "high";
        description
          "User-provided name of this NTP server instance";
      }
      unique "network-instance";
      uses ntp-server-instance-top;
    }
  }

  augment "/srl-system:system" {
    if-feature "srl_nokia-feat:ntp-server and not srl_nokia-feat:platform-imgmt";
    uses ntp-server-top;
  }
}
