module srl_nokia-tools-system-gnoi {
  yang-version 1.1;
  namespace "urn:nokia.com:srlinux:gnmi:tools-system-gnoi";
  prefix srl_nokia-tools-system-gnoi;

  import srl_nokia-tools-system {
    prefix srl-tools-system;
  }
  import srl_nokia-tools-system-gnoi-healthz {
    prefix srl-tools-system-gnoi-healthz;
  }
  import srl_nokia-features {
    prefix srl-feat;
  }

  organization
    "Nokia";
  contact
    "Nokia SR Linux Support
     Web: <http://www.nokia.com>";
  description
    "Model for managing gNOI";

  revision 2023-07-31 {
    description
      "SRLinux 23.7.1";
  }

  grouping tools-system-gnoi-top {
    container gnoi {
      presence "Configure tools gNOI";
      description
        "Top-level container for operational commands related to gNOI";
      uses srl-tools-system-gnoi-healthz:tools-system-gnoi-healthz-top;
    }
  }

  augment "/srl-tools-system:system" {
    if-feature "srl-feat:gnoi-healthz";
    uses tools-system-gnoi-top;
  }
}
