module srl_nokia-mpls-services-evpn-label-management {
  yang-version 1.1;
  namespace "urn:nokia.com:srlinux:evpn:mpls-services-evpn-label-management";
  prefix srl_nokia-mplsservicesbtevpnlbl;

  import srl_nokia-features {
    prefix srl_nokia-feat;
  }
  import srl_nokia-common {
    prefix srl_nokia-comm;
  }
  import srl_nokia-extensions {
    prefix srl_nokia-ext;
  }
  import srl_nokia-system {
    prefix srl_nokia-system;
  }
  import srl_nokia-mpls-label-management {
    prefix srl_nokia-mplslbl;
  }

  organization
    "Nokia";
  contact
    "Nokia SR Linux Support
     Web: <http://www.nokia.com>";
  description
    "This module defines configuration and operational state data for MPLS label management for EVPN in the system network-instance";

  revision 2025-07-31 {
    description
      "SRLinux 25.7.1";
  }
  revision 2022-03-31 {
    description
      "SRLinux 22.3.1";
  }

  grouping mpls-services-evpn-management-top {
    container evpn {
      if-feature "srl_nokia-feat:evpn-mpls";
      presence "Configure MPLS label management for EVPN in the system network-instance";
      description
        "Container for system wide Services EVPN MPLS label management";
      leaf dynamic-label-block {
        mandatory true;
        type leafref {
          path "/srl_nokia-system:system/srl_nokia-mplslbl:mpls/srl_nokia-mplslbl:label-ranges/srl_nokia-mplslbl:dynamic/srl_nokia-mplslbl:name";
        }
        description
          "The dynamic label block used by EVPN in the system network-instance

           The label block is used by all EVPN services that require MPLS labels in the
           system network-instance. For example, EVPN-MPLS multi-homing (ESI label).";
      }
    }
  }

  augment "/srl_nokia-system:system/srl_nokia-mplslbl:mpls/srl_nokia-mplslbl:services" {
    uses mpls-services-evpn-management-top;
  }
}
