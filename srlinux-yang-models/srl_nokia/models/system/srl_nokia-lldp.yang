module srl_nokia-lldp {
  yang-version 1.1;
  namespace "urn:nokia.com:srlinux:lldp:lldp";
  prefix srl_nokia-lldp;

  import srl_nokia-lldp-types {
    prefix nokia-lldp-types;
  }
  import srl_nokia-interfaces {
    prefix srl_nokia-if;
  }
  import srl_nokia-system {
    prefix srl-system;
  }
  import srl_nokia-network-instance {
    prefix srl_nokia-netinst;
  }
  import srl_nokia-common {
    prefix srl-comm;
  }
  import srl_nokia-features {
    prefix srl-feat;
  }
  import srl_nokia-extensions {
    prefix srl-ext;
  }

  organization
    "Nokia";
  contact
    "Nokia SR Linux Support
     Web: <http://www.nokia.com>";
  description
    "This module defines configuration and operational state data
     for the LLDP protocol.";

  revision 2026-07-31 {
    description
      "SRLinux 26.7.1";
  }
  revision 2026-03-31 {
    description
      "SRLinux 26.3.1";
  }
  revision 2025-10-31 {
    description
      "SRLinux 25.10.1";
  }
  revision 2024-07-31 {
    description
      "SRLinux 24.7.1";
  }
  revision 2022-03-31 {
    description
      "SRLinux 22.3.1";
  }
  revision 2021-03-31 {
    description
      "SRLinux 21.3.1";
  }
  revision 2020-06-30 {
    description
      "SRLinux 20.6.1";
  }
  revision 2019-11-30 {
    description
      "SRLinux 19.11.1";
  }

  grouping lldp-common-counters {
    description
      "Definition of global and per-interface counters";
    leaf frame-in {
      type srl-comm:zero-based-counter64;
      description
        "The number of LLDP frames received";
    }
    leaf frame-out {
      type srl-comm:zero-based-counter64;
      description
        "The number of LLDP frames transmitted";
    }
    leaf frame-error-in {
      type srl-comm:zero-based-counter64;
      description
        "The number of LLDP frames received with errors";
    }
    leaf frame-discard {
      type srl-comm:zero-based-counter64;
      description
        "The number of LLDP frames received and discarded";
    }
    leaf tlv-discard {
      type srl-comm:zero-based-counter64;
      description
        "The number of TLV frames received and discarded";
    }
    leaf tlv-unknown {
      type srl-comm:zero-based-counter64;
      description
        "The number of frames received with unknown TLV";
    }
    leaf last-clear {
      type srl-comm:date-and-time-delta;
      description
        "Indicates the last time the counters were cleared";
    }
  }

  grouping lldp-global-counters {
    description
      "Definition of global LLDP counters";
    uses lldp-common-counters;
    leaf tlv-accepted {
      type srl-comm:zero-based-counter64;
      description
        "The number of valid TLVs received.";
    }
    leaf entries-aged-out {
      type srl-comm:zero-based-counter64;
      description
        "The number of entries aged out due to timeout.";
    }
  }

  grouping lldp-interface-counters {
    description
      "Definition of per-interface LLDP counters";
    uses lldp-common-counters;
    leaf frame-error-out {
      type srl-comm:zero-based-counter64;
      description
        "The number of frame transmit errors on the interface";
    }
  }

  typedef base-subinterface-ref {
    type leafref {
      path "/srl_nokia-if:interface/srl_nokia-if:subinterface/srl_nokia-if:name";
    }
    description
      "Reusable type for by-name reference to a base subinterface.";
  }

  grouping lldp-system-info-config {
    description
      "Configuration data for system-level local and remote LLDP information";
    leaf system-name {
      config false;
      type string {
        length "0..255";
      }
      description
        "The systems administratively assigned name

         The system name field shall contain an alpha-numeric string
         that indicates the system's administratively assigned name.
         The system name should be the system's fully qualified domain
         name.";
    }
    leaf system-description {
      config false;
      type string {
        length "0..255";
      }
      description
        "Field detailing system description, including name and versions

         The system description field shall contain an alpha-numeric
         string that is the textual description of the network entity.
         The system description should include the full name and
         version identification of the system's hardware type,
         software operating system, and networking software.";
    }
    leaf chassis-id {
      config false;
      type string;
      description
        "The Chassis ID is a mandatory TLV which identifies the
         chassis component of the endpoint identifier associated with
         the transmitting LLDP agent";
    }
    leaf chassis-id-type {
      config false;
      type nokia-lldp-types:chassis-id-type;
      default "MAC_ADDRESS";
      description
        "The source for the chassis identifier string

         It is an enumerator defined by the LldpChassisIdSubtype object
         from IEEE 802.1AB MIB.";
    }
    list management-address {
      key "subinterface";
      description
        "List of subinterfaces to source management addresses from

         This list is sent in the management address TLV by LLDP.";
      leaf subinterface {
        type srl-comm:subinterface-all;
        must "/srl_nokia-if:interface[srl_nokia-if:name=substring-before(current(), '.')]/srl_nokia-if:subinterface[srl_nokia-if:index=substring-after(current(), '.')]" {
          error-message "Must be an existing subinterface name";
        }
        description
          "Reference to the subinterface to source management addresses";
      }
      leaf-list type {
        type nokia-lldp-types:management-address-type;
        description
          "Types of addresses sent in the management address TLV

           The enumerated value for the network address type
           identified in this TLV. This enumeration is defined in the
           'Assigned Numbers' RFC [RFC3232] and the
           ianaAddressFamilyNumbers object.";
      }
    }
  }

  grouping lldp-system-info-state {
    description
      "Operational state data reported for the local and remote systems";
  }

  grouping lldp-neighbor-config {
    description
      "Configuration data for LLDP neighbors";
  }

  grouping lldp-neighbor-state {
    description
      "Operational state data for LLDP neighbors";
    leaf id {
      type string;
      description
        "System generated identifier for the remote neighbor";
    }
    leaf first-message {
      type srl-comm:date-and-time-delta;
      description
        "Date and time of the first message from neighbor";
    }
    leaf last-update {
      type srl-comm:date-and-time-delta;
      description
        "Date and time of the last update from neighbor";
    }
    leaf system-name {
      config false;
      type string {
        length "0..255";
      }
      description
        "The administratively assigned name of the remote neighbor

         The system name field shall contain an alpha-numeric string
         that indicates the system's administratively assigned name.
         The system name should be the system's fully qualified domain
         name. If implementations support IETF RFC 3418, the sysName
         object should be used for this field.";
    }
    leaf system-description {
      config false;
      type string {
        length "0..255";
      }
      description
        "The system description of the remote neighbor

         The system description field shall contain an alpha-numeric
         string that is the textual description of the network entity.
         The system description should include the full name and
         version identification of the system's hardware type,
         software operating system, and networking software. If
         implementations support IETF RFC 3418, the sysDescr object
         should be used for this field.";
    }
    leaf chassis-id {
      config false;
      type string;
      description
        "The chassis ID of the remote neighbor

         The Chassis ID is a mandatory TLV which identifies the
         chassis component of the endpoint identifier associated with
         the transmitting LLDP agent";
    }
    leaf chassis-id-type {
      config false;
      type nokia-lldp-types:chassis-id-type;
      default "MAC_ADDRESS";
      description
        "The type of identifier used in the chassis-id field

         This field identifies the format and source of the chassis
         identifier string. It is an enumerator defined by the
         LldpChassisIdSubtype object from IEEE 802.1AB MIB.";
    }
    leaf port-id {
      type nokia-lldp-types:string-or-binary;
      description
        "The Port ID of the remote neighbor

         The Port ID is a mandatory TLV which identifies the port
         component of the endpoint identifier associated with the
         transmitting LLDP agent. If the specified port is an IEEE
         802.3 Repeater port, then this TLV is optional.";
    }
    leaf port-id-type {
      type nokia-lldp-types:port-id-type;
      description
        "The type of identifier used in the port-id field

         This field identifies the format and source of the port
         identifier string. It is an enumerator defined by the
         PtopoPortIdType object from RFC2922.";
      reference
        "RFC2922";
    }
    leaf port-description {
      type string;
      description
        "The description of the port referenced in the port-id field

         The binary string containing the actual port identifier for
         the port which this LLDP PDU was transmitted. The source and
         format of this field is defined by PtopoPortId from
         RFC2922.";
      reference
        "RFC2922";
    }
    list management-address {
      key "address";
      description
        "List of management addresses received from the remote LLDP neighbor";
      leaf address {
        type string;
        description
          "The management address received from the remote LLDP neighbor

           The Management Address is a mandatory TLV which identifies a
           network address associated with the LLDP agent, which
           can be used to reach the agent on the port identified in the
           Port ID TLV.";
      }
      leaf type {
        type nokia-lldp-types:management-address-type;
        description
          "The type of management address referenced in the address field

           The enumerated value for the network address type
           identified in this TLV. This enumeration is defined in the
           'Assigned Numbers' RFC [RFC3232] and the
           ianaAddressFamilyNumbers object.";
      }
    }
    container bgp-auto-discovery {
      if-feature "srl-feat:bgp-auto-discovery-using-lldp";
      presence "Configure BGP auto discovery";
      description
        "Enclosing container for BGP auto discovery";
      leaf-list bgp-peer-addresses {
        type string;
        description
          "List of IP address learned from neighbor for BGP auto discovery";
      }
      leaf group-id {
        type uint32;
        description
          "A four byte integer to send on outgoing LLDPDUs, this value can be used on the remote
           end to do peer group association. This sub-TLV is not sent by default";
      }
    }
  }

  grouping lldp-capabilities-config {
    description
      "Configuration data for LLDP capabilities";
  }

  grouping lldp-capabilities-state {
    description
      "Operational state data for LLDP capabilities";
    leaf name {
      type identityref {
        base nokia-lldp-types:LLDP_SYSTEM_CAPABILITY;
      }
      description
        "Name of the system capability advertised by the neighbor

         Capabilities are represented in a bitmap that defines the
         primary functions of the system. The capabilities are
         defined in IEEE 802.1AB.";
      reference
        "IEEE 802.1AB";
    }
    leaf enabled {
      type boolean;
      description
        "Indicates whether the corresponding system capability is enabled on the neighbor";
      reference
        "Sec 8.5.8.2 of IEEE 802.1AB-2009";
    }
  }

  grouping lldp-capabilities-top {
    description
      "Top-level grouping for LLDP capabilities";
    list capability {
      config false;
      key "name";
      description
        "List of LLDP system capabilities advertised by the neighbor";
      uses lldp-capabilities-state;
    }
  }

  grouping lldp-custom-tlv-config {
    description
      "Configuration data for custom LLDP TLVs";
  }

  grouping lldp-custom-tlv-state {
    description
      "Operational state data for custom LLDP TLVs";
    leaf type {
      type int32;
      description
        "The integer value identifying the type of information
         contained in the value field.";
    }
    leaf oui {
      type string;
      description
        "The organizationally unique identifier field from the custom TLV

         This field shall contain the organization's OUI as defined in
         Clause 9 of IEEE Std 802. The high-order octet is 0 and the
         low-order 3 octets are the SMI Network Management Private Enterprise
         Code of the Vendor in network byte order, as defined in the
         'Assigned Numbers' RFC [RFC3232].";
      reference
        "RFC3232";
    }
    leaf oui-subtype {
      type string;
      description
        "The subtype value defined by the OUI for this custom TLV

         The organizationally defined subtype field shall contain a
         unique subtype value assigned by the defining organization.";
    }
    leaf value {
      type binary;
      description
        "A variable-length octet-string containing the value for this TLV";
    }
    container ue-link-neg-options {
      if-feature "srl-feat:lldp-ue-link-negotiation";
      leaf version {
        type uint8;
      }
      container link-options {
        leaf csig-capability {
          type identityref {
            base nokia-lldp-types:CSIG_CAPABALE;
          }
        }
        description
          "Enter the link-options context";
      }
      description
        "Enter the ue-link-neg-options context";
    }
    leaf port-id-vlan {
      if-feature "srl-feat:lldp-vlan";
      type uint16 {
        range "0..4094";
      }
      description
        "VLAN ID associated with the native VLAN

         Conditionally displayed for OUI 00:80:C2 subtype 01";
    }
    list vlan-id-name-map {
      if-feature "srl-feat:lldp-vlan";
      description
        "VLAN ID to VLAN Name mapping

         Conditionally displayed for OUI 00:80:C2 subtype 03";
      key "id name";
      leaf id {
        type uint16 {
          range "0..4094";
        }
        description
          "VLAN ID associated with the name";
      }
      leaf name {
        type string;
        description
          "Name associated with the VLAN ID";
      }
    }
    leaf maximum-frame-size {
      if-feature "srl-feat:lldp-component";
      type uint16;
      description
        "Maximum frame size capability of the MAC/PHY

         Conditionally displayed for OUI 00:12:0F subtype 04";
    }
    container aggregation {
      if-feature "srl-feat:lldp-component";
      description
        "Enter the aggregation context

         Context for aggregation capabilities and status";
      leaf capable {
        type boolean;
        description
          "Whether the port is capable of aggregation

           Conditionally displayed for OUI 00:80:C2 subtype 7";
      }
      leaf status {
        type identityref {
          base nokia-lldp-types:LINK_AGGREGATION_STATUS;
        }
        description
          "Whether the port is currently aggregated or not aggregated";
      }
      leaf port-type {
        type identityref {
          base nokia-lldp-types:LINK_AGGREGATION_PORT_TYPE;
        }
        description
          "Aggregation status port type";
      }
      leaf aggregated-port-id {
        type uint32;
        description
          "Integer representation of the aggregated-port-id";
      }
    }
  }

  grouping lldp-custom-tlv-top {
    description
      "Top-level grouping for custom LLDP TLVs";
    list custom-tlv {
      config false;
      key "type oui oui-subtype";
      description
        "List of custom LLDP TLVs from a neighbor";
      uses lldp-custom-tlv-state;
    }
  }

  grouping lldp-neighbor-top {
    description
      "Top-level grouping for the LLDP neighbor list";
    list neighbor {
      config false;
      key "id";
      description
        "List of LLDP neighbors on this interface";
      uses lldp-system-info-state;
      uses lldp-neighbor-state;
      uses lldp-custom-tlv-top;
      uses lldp-capabilities-top;
      uses lldp-med-neighbor-state;
    }
  }

  grouping lldp-bgp-auto-discovery-interface {
    description
      "Top-level grouping for LLDP BGP auto discovery per interface";
    container bgp-auto-discovery {
      if-feature "srl-feat:bgp-auto-discovery-using-lldp";
      presence "Configure LLDP BGP auto discovery";
      description
        "Configuration and state related to LLDP BGP auto discovery on the interface";
      leaf admin-state {
        type srl-comm:admin-state;
        default "enable";
        description
          "Enable or disable LLDP BGP auto discovery on this interface";
      }
      leaf-list peering-address {
        type srl-comm:ip-address;
        description
          "List of IP addresses to be sent for BGP auto discovery

           Default values for this sub-TLV is to populate the addresses
           of the first subinterface of the interface the LLDPDU is being
           generated from, along with a unicast AFI/SAFI for IPv4 if an IPv4
           address exists, and/or IPv6 if an IPv6 address exists.

           If neither of these exist in the system, LLDP will not add the TLV
           to outgoing LLDPDUs, unless the peering-address is manually configured
           on a per-LLDP-port basis.";
      }
      leaf group-id {
        type uint32;
        description
          "A four byte integer to send on outgoing LLDPDUs

           This value can be used on the remote end to do peer group association.
           This sub-TLV is not sent by default.";
      }
    }
  }

  typedef base-interface-ref {
    type leafref {
      path "/srl_nokia-if:interface/srl_nokia-if:name";
    }
    description
      "Reusable type for by-name reference to a base interface
       This type may be used in cases where ability to reference
       a subinterface is not required.";
  }

  grouping lldp-interface-config {
    description
      "Configuration data for LLDP on each interface";
    leaf name {
      type base-interface-ref;
      description
        "Reference to the LLDP Ethernet interface";
    }
    leaf admin-state {
      type srl-comm:admin-state;
      default "enable";
      description
        "Enable or disable LLDP on the interface";
    }
    uses lldp-bgp-auto-discovery-interface;
    container vlan {
      if-feature "srl-feat:lldp-vlan";
      description
        "Enter the vlan context

         Administrative configuration for organizational LLDP VLAN TLVs (PORT_VLAN_ID and VLAN_NAME)";
      leaf native-vlan {
        type uint16 {
          range "0..4094";
        }
        description
          "LLDP TLV PORT ID VLAN value";
      }
      list id-name-map {
        description
          "The list of VLAN ID to NAME mappings";
        key "id";
        leaf id {
          type uint16 {
            range "0..4094";
          }
          description
            "LLDP TLV VLAN NAME ID value";
        }
        leaf name {
          type string {
            length "1..32";
          }
          description
            "LLDP TLV VLAN NAME name value";
        }
      }
    }
  }

  grouping lldp-med-interface-config {
    description
      "Configuration data for LLDP-MED on each interface";
    leaf admin-state {
      type srl-comm:admin-state;
      default "disable";
      description
        "Enable or disable LLDP-MED on the interface

         When 'enable' the capability TLV will be transmitted.  Other LLDP-MED TLVs must be included
         in the lldp-med-tlv list to be transmitted to an endpoint.  Value 'disable' stops the
         transmission and processing of LLDP-MED TLVs.  The base LLDP protocol admin-state must be 'enable'
         for LLDP-MED to be operationally up.";
    }
    leaf-list network-policy {
      type leafref {
        path "../../../lldp-med/network-policy/name";
      }
      description
        "Name of the network policy for a specific application type

         Multiple network policies can be assigned to a single interface, one per application type.";
    }
    leaf-list lldp-med-tlvs {
      type identityref {
        base nokia-lldp-types:LLDP_MED_TLV;
      }
      description
        "List of supported LLDP-MED tlvs on the interface";
    }
    container location {
      description
        "Enter the location context

         Selection of location information to transmit when the endpoint supports location capability";
      leaf system-coordinates {
        type boolean;
        default "false";
        description
          "Transmit the configured system coordinate values

           All values will be included in the LLDPDU location TLV.  If no /system/location/coordinates are configured
           the location TLV will not include coordinate information";
      }
      leaf elin {
        type string {
          length "10..25";
        }
        description
          "Emergency Location Identification Number

           Included in the location TLV using civic-address encoded as CA-type 128.  The ../system-civic-address does
           not have to be configured or enabled to send this value.";
      }
    }
  }

  grouping lldp-med-interface-state {
    description
      "State information for LLDP-MED interface";
    leaf oper-state {
      type srl-comm:oper-state;
      config false;
      description
        "Details the operational state of LLDP MED on the interface

         Global lldp, interface lldp and interface lldp-med must be admin-state 'enable' to achieve oper-state 'up'";
    }
    container mac-phy-configuration-status {
      config false;
      description
        "Enter the mac-phy-configuration-status context

         MAC/PHY Configuration/Status TLV information";
      container interface {
        leaf auto-negotiation-support {
          type nokia-lldp-types:auto-negotiation-support;
          description
            "Support of auto-negotiation";
        }
        leaf auto-negotiation-enabled {
          type nokia-lldp-types:auto-negotiation-enabled;
          description
            "Enable state of auto-negotiation";
        }
        leaf-list auto-negotiation-capabilities {
          type nokia-lldp-types:auto-negotiation-capabilities;
          description
            "List of auto-negotiation capabilities advertised";
        }
        description
          "Enter the interface context";
      }
      container peer {
        leaf auto-negotiation-support {
          type nokia-lldp-types:auto-negotiation-support;
          description
            "Support of auto-negotiation";
        }
        leaf auto-negotiation-enabled {
          type nokia-lldp-types:auto-negotiation-enabled;
          description
            "Enable state of auto-negotiation";
        }
        leaf-list auto-negotiation-capabilities {
          type nokia-lldp-types:auto-negotiation-capabilities;
          description
            "List of auto-negotiation capabilities advertised";
        }
        leaf mau-type {
          type nokia-lldp-types:interface-mau-type;
          description
            "Operational MAU type";
        }
        description
          "Enter the peer context";
      }
    }
  }

  grouping lldp-med-neighbor-capabilities-state {
    description
      "Neighbor state for LLDP-MED capabilities";
    list capabilities {
      key "name";
      description
        "List name";
      leaf name {
        type identityref {
          base nokia-lldp-types:LLDP_MED_CAPABILITIES;
        }
        description
          "Neighbor supported capabilities";
      }
    }
  }

  grouping lldp-med-neighbor-application-state {
    description
      "Neighbor state for LLDP-MED network policy";
    list network-policy-application-type {
      key "name";
      description
        "List name";
      leaf name {
        type identityref {
          base nokia-lldp-types:LLDP_MED_NETWORK_POLICY_APPLICATIONS;
        }
        description
          "Application name in received network policy TLV";
      }
      leaf policy-flag {
        type enumeration {
          enum unknown {
            value 0;
            description
              "Network policy unknown";
          }
          enum known {
            value 1;
            description
              "Network policy known";
          }
        }
        description
          "State of the network policy received from the endpoint";
      }
      leaf vlan-tagging {
        type boolean;
        description
          "VLAN tagging for the specified application";
      }
      leaf vlan-id {
        type uint16 {
          range "0..4094";
        }
        description
          "VLAN ID used for tagged applications, conditional leaf";
      }
      leaf dot1p {
        type uint8 {
          range "0..7";
        }
        default "0";
        description
          "L2 QoS dot1p priority";
      }
      leaf dscp {
        type srl-comm:dscp;
        default "CS0";
        description
          "L3 QoS DSCP value";
      }
    }
  }

  grouping lldp-med-neighbor-inventory-state {
    description
      "State information for LLDP-MED inventory neighbor";
    container inventory {
      leaf hardware-revision {
        type string {
          length "0..32";
        }
      }
      leaf firmware-revision {
        type string {
          length "0..32";
        }
      }
      leaf software-revision {
        type string {
          length "0..32";
        }
      }
      leaf serial-number {
        type string {
          length "0..32";
        }
      }
      leaf manufacturer-number {
        type string {
          length "0..32";
        }
      }
      leaf model-name {
        type string {
          length "0..32";
        }
      }
      leaf asset-id {
        type string {
          length "0..32";
        }
      }
      description
        "Enter the inventory context";
    }
  }

  grouping lldp-med-neighbor-state {
    description
      "State information for LLDP-MED neighbor";
    container lldp-med {
      if-feature "srl-feat:lldp-med";
      config false;
      description
        "Enter the lldp-med context

         LLDP-MED neighbor state";
      uses lldp-med-neighbor-capabilities-state;
      uses lldp-med-neighbor-application-state;
      uses lldp-med-neighbor-inventory-state;
    }
  }

  grouping lldp-interface-state {
    description
      "Operational state data for LLDP on each interface";
    leaf oper-state {
      type srl-comm:oper-state;
      config false;
      description
        "Details the operational state of LLDP on the interface";
    }
    container statistics {
      srl-ext:delivery-node-override "true";
      presence "State LLDP counters";
      config false;
      description
        "LLDP counters on each interface";
      uses lldp-interface-counters;
    }
  }

  grouping lldp-interface-top {
    description
      "Top-level grouping for LLDP interfaces";
    list interface {
      key "name";
      description
        "List of interfaces on which LLDP can be enabled";
      uses lldp-interface-config;
      container lldp-med {
        if-feature "srl-feat:lldp-med";
        uses lldp-med-interface-config;
        uses lldp-med-interface-state;
        description
          "Enter the lldp-med context";
      }
      uses lldp-interface-state;
      uses lldp-neighbor-top;
    }
  }

  grouping lldp-bgp-auto-discovery-top {
    description
      "Top-level grouping for global BGP auto discovery";
    container bgp-auto-discovery {
      if-feature "srl-feat:bgp-auto-discovery-using-lldp";
      presence "Configure LLDP BGP auto discovery";
      description
        "Top-level container for global LLDP BGP auto discovery";
      leaf admin-state {
        type srl-comm:admin-state;
        default "disable";
        description
          "Enable or disable LLDP BGP auto discovery at the system level

           Setting this to disable will override any per-interface LLDP
           BGP autodiscovery configuration";
      }
      leaf-list network-instance {
        type leafref {
          path "/srl_nokia-netinst:network-instance/srl_nokia-netinst:name";
        }
        description
          "List of network instances to enable LLDP BGP auto discovery in

           Default is to run LLDP BGP auto discovery in all network instances";
      }
      leaf group-id {
        type uint32;
        description
          "A four byte integer to send on outgoing LLDPDUs

           This value can be used on the remote end to do peer group association.
           This sub-TLV is not sent by default";
      }
    }
  }

  grouping lldp-config {
    description
      "Global LLDP configuration";
    leaf admin-state {
      type srl-comm:admin-state;
      default "enable";
      description
        "Enable or disable LLDP at the system level";
    }
    leaf hello-timer {
      type uint64;
      default "30";
      units "seconds";
      description
        "System level hello timer for the LLDP protocol";
    }
    leaf hold-multiplier {
      type uint8;
      default "4";
      description
        "System level hold multiplier, used to define neighbor aging

         This field defines how many hellos need to be missed before
         a neighbor is aged out.

         This field also is used along with the 'hello-timer' field
         to define the TTL TLV in outgoing LLDPDUs.";
    }
    uses lldp-bgp-auto-discovery-top;
    leaf-list suppress-tlv-advertisement {
      if-feature "srl-feat:lldp-suppress-tlv";
      type identityref {
        base nokia-lldp-types:LLDP_TLV;
      }
      description
        "Indicates whether the local system should suppress the
         advertisement of particular TLVs with the LLDP PDUs that it
         transmits. Where a TLV type is specified within this list, it
         should not be included in any LLDP PDU transmitted by the
         local agent.";
    }
  }

  grouping lldp-med-system-config {
    description
      "Global LLDP MED configuration";
    leaf med-fast-transmit-interval {
      type uint32 {
        range "1..3600";
      }
      default "1";
      description
        "Transmit interval activated whenever an LLDP-MED Capabilities TLV received is not associated with a remote system";
    }
    leaf med-fast-transmit-repeat-count {
      type uint32 {
        range "1..8";
      }
      default "4";
      description
        "Duration of the fast-start process, in number of packets";
    }
    leaf topology-change-notification {
      type boolean;
      default "false";
      description
        "Indicate whether to generate topology change notifications for endpoints

         Used to track the movement of portable equipment using of events.";
    }
    list network-policy {
      key "name";
      description
        "Network policy distribution of configuration attributes based on application type";
      leaf name {
        type srl-comm:restricted-name;
        description
          "List name";
      }
      leaf application-type {
        type identityref {
          base nokia-lldp-types:LLDP_MED_NETWORK_POLICY_APPLICATIONS;
        }
        description
          "Application type for network policy";
      }
      leaf vlan-id {
        type union {
          type uint16 {
            range "0..4094";
          }
          type enumeration {
            enum untagged {
              value 0;
            }
          }
        }
        description
          "VLAN tagging requirements for the application type, VLAN-ID (range 0..4094) or untagged";
        default "untagged";
      }
      leaf dot1p {
        type uint8 {
          range "0..7";
        }
        default "0";
        description
          "L2 QoS dot1p priority";
      }
      leaf dscp {
        type srl-comm:dscp;
        default "CS0";
        description
          "L3 QoS DSCP value";
      }
    }
  }

  grouping lldp-state {
    description
      "Operational state data for global LLDP parameters";
    container statistics {
      presence "State global LLDP counters";
      config false;
      description
        "Global LLDP counters";
      uses lldp-global-counters;
    }
  }

  grouping lldp-traceoptions {
    description
      "Top-level grouping for LLDP trace options";
    leaf-list trace-options {
      description
        "LLDP trace options";
      type enumeration {
        enum received;
        enum transmitted;
        enum common;
      }
    }
  }

  grouping lldp-top {
    description
      "Top-level grouping for LLDP model";
    container lldp {
      presence "Configure LLDP";
      description
        "Top-level container for LLDP configuration and state data";
      uses lldp-traceoptions;
      uses lldp-config;
      uses lldp-system-info-config;
      container lldp-med {
        if-feature "srl-feat:lldp-med";
        uses lldp-med-system-config;
        description
          "Enter the lldp-med context";
      }
      uses lldp-state;
      uses lldp-interface-top;
    }
  }

  augment "/srl-system:system" {
    uses lldp-top;
  }
}
