module srl_nokia-mcast-cac-types {
  yang-version 1.1;
  prefix srl_nokia-mcast-cac-types;
  namespace "urn:nokia.com:srlinux:mcast-cac:mcast-cac-types";

  organization
    "Nokia";
  contact
    "Nokia SR Linux Support
     Web: <http://www.nokia.com>";
  description
    "This yang file contains common Multicast Connection Access Control (MCAC) types and identities";

  revision 2026-03-31 {
    description
      "SRLinux 26.3.1";
  }

  typedef router-application {
    description
      ".";
    type enumeration {
      enum igmp {
        value 1;
      }
      enum pim {
        value 2;
      }
      enum mld {
        value 4;
      }
    }
  }

  typedef service-application {
    description
      ".";
    type enumeration {
      enum igmp-snooping {
        value 3;
      }
    }
  }

  typedef policy-action {
    type enumeration {
      enum accept {
        value 1;
      }
      enum discard {
        value 2;
      }
    }
  }

  typedef channel-type {
    type enumeration {
      enum best-effort {
        value 1;
      }
      enum guaranteed {
        value 2;
      }
    }
  }

  typedef bandwidth-limit {
    description
      "Bandwidth limit in kilobps";
    type int32 {
      range "0..max";
    }
  }

  typedef bandwidth {
    description
      ".";
    type uint32;
    units "kilobps";
  }
}
