module srl_nokia-dhcp-server {
  yang-version 1.1;
  namespace "urn:nokia.com:srlinux:dhcp:dhcp-server";
  prefix srl-dhcp-server;

  import srl_nokia-common {
    prefix srl-comm;
  }
  import srl_nokia-system {
    prefix srl-system;
  }
  import srl_nokia-network-instance {
    prefix srl-netinst;
  }
  import srl_nokia-extensions {
    prefix srl-ext;
  }
  import srl_nokia-features {
    prefix srl_nokia-feat;
  }

  organization
    "Nokia";
  contact
    "Nokia SR Linux Support
     Web: <http://www.nokia.com>";
  description
    "This module defines configuration and operational state data related to the dhcp server.";

  revision 2026-07-31 {
    description
      "SRLinux 26.7.1";
  }
  revision 2026-03-31 {
    description
      "SRLinux 26.3.1";
  }
  revision 2025-10-31 {
    description
      "SRLinux 25.10.1";
  }
  revision 2025-03-31 {
    description
      "SRLinux 25.3.1";
  }
  revision 2022-03-31 {
    description
      "SRLinux 22.3.1";
  }
  revision 2021-11-30 {
    description
      "SRLinux 21.11.1";
  }
  revision 2021-06-30 {
    description
      "SRLinux 21.6.1";
  }

  identity dhcp-option-encoding {
    description
      "Base identity for DHCP option encoding types";
  }

  identity string {
    base dhcp-option-encoding;
    description
      "DHCP option encoding type for strings";
  }

  grouping dhcpv4-relay-information {
    list relay-information {
      if-feature "srl_nokia-feat:dhcp-svr-boot-compute";
      key "circuit-id remote-id";
      srl-ext:show-importance "high";
      description
        "DHCPv4 relay information";
      leaf circuit-id {
        type string {
          length "1..255";
        }
        description
          "The circuit ID of the DHCPv4 relay agent";
      }
      leaf remote-id {
        type string {
          length "1..255";
        }
        description
          "The remote ID of the DHCPv4 relay agent";
      }
      leaf ip-address {
        type srl-comm:ipv4-prefix-with-host-bits;
        must "not(starts-with(.,'0.') or starts-with(.,'127.') or re-match(.,'22[4-9]\\..*') or re-match(.,'2[3-5][0-9]\\..*'))" {
          error-message "Not a valid IPv4 unicast address prefix";
        }
      }
      uses dhcp-server-v4-options;
    }
  }

  grouping dhcpv4-custom-options-common {
    list custom {
      if-feature "srl_nokia-feat:dhcp-svr-boot-compute";
      key "code";
      description
        "List of custom DHCP options";
      srl-ext:show-importance "high";
      leaf code {
        type uint8 {
          range "1..254";
        }
        description
          "The code of the DHCP option";
      }
      leaf value {
        type string {
          length "1..255" {
            error-message "Value length can not be more than 255 characters";
          }
        }
        mandatory true;
        description
          "The value of the DHCP option";
      }
      leaf always-send {
        type boolean;
        default "false";
        description
          "If true, the option will always be sent to the client, even if it is not configured in the client request";
      }
      leaf encoding {
        description
          "The encoding of the value of the DHCP option";
        type identityref {
          base dhcp-option-encoding;
        }
        default "string";
      }
    }
  }

  grouping dhcp-common {
    leaf admin-state {
      type srl-comm:admin-state;
      srl-ext:show-importance "high";
      default "disable";
      description
        "Administratively enable or disable the dhcp server";
    }
    leaf oper-state {
      config false;
      type srl-comm:oper-state;
      srl-ext:show-importance "high";
      description
        "Details if the dhcp server is operationally available";
    }
    container trace-options {
      description
        "Enter the trace-options context

         Container for tracing DHCP server operations instance";
      leaf-list trace {
        type enumeration {
          enum messages {
            description
              "Capture all DHCP server messages sent and received";
          }
        }
        description
          "List of events to trace";
      }
    }
    container statistics {
      config false;
      leaf client-packets-received {
        type srl-comm:zero-based-counter64;
        description
          "Total received dhcp packets from dhcp client(s)";
      }
      leaf client-packets-discarded {
        type srl-comm:zero-based-counter64;
        description
          "Total discarded dhcp packets from dhcp client(s)";
      }
      leaf server-packets-sent {
        type srl-comm:zero-based-counter64;
        description
          "Total dhcp packets sent from DHCP server towards dhcp client(s)";
      }
      description
        "Enter the statistics context";
    }
  }

  grouping static-allocation-v4 {
    container static-allocation {
      list host {
        key "mac";
        description
          "host name for static ip allocations";
        leaf mac {
          type srl-comm:mac-address;
        }
        leaf ip-address {
          type srl-comm:ipv4-prefix-with-host-bits;
          must "not(starts-with(.,'0.') or starts-with(.,'127.') or re-match(.,'22[4-9]\\..*') or re-match(.,'2[3-5][0-9]\\..*'))" {
            error-message "Not a valid IPv4 unicast address prefix";
          }
        }
        uses dhcp-server-v4-options;
      }
      uses dhcpv4-relay-information;
      description
        "Enter the static-allocation context";
    }
  }

  grouping static-allocation-v6 {
    container static-allocation {
      list host {
        key "mac";
        description
          "host name for static ip allocations";
        leaf mac {
          type srl-comm:mac-address;
        }
        leaf ip-address {
          type srl-comm:ipv6-prefix-with-host-bits;
          must "not(.='::/128' or .='::1/128' or starts-with(.,'ff') or starts-with(.,'fe80'))" {
            error-message "Not a global unicast IPv6 address prefix";
          }
        }
        uses dhcp-server-v6-options;
      }
      description
        "Enter the static-allocation context";
    }
  }

  grouping dhcp-server-v4-options {
    container options {
      leaf bootfile-name {
        type string {
          length "1..128";
        }
        description
          "The name of the configuration file the client will use during booting - option 67";
      }
      leaf-list dns-server {
        type srl-comm:ipv4-address;
        must "not(starts-with(.,'0.') or starts-with(.,'127.') or re-match(.,'22[4-9]\\..*') or re-match(.,'2[3-5][0-9]\\..*'))" {
          error-message "Not a valid IPv4 unicast address";
        }
        max-elements 4;
        description
          "An Ordered List of DNS servers to return to the dhcp client - option 6";
      }
      leaf domain-name {
        type srl-comm:domain-name;
        description
          "The domain name to return to the dhcp client that the client should use when resolving hostnames via the Domain Name System - option 15";
      }
      leaf-list domain-search-list {
        if-feature "srl_nokia-feat:dhcp-svr-boot-compute";
        type srl-comm:domain-name;
        max-elements 4;
        description
          "An ordered list of domains to return to the dhcp client that the client should search when resolving hostnames - option 119";
      }
      leaf hostname {
        type string {
          length "1..63";
          pattern '(([a-zA-Z]|[a-zA-Z][a-zA-Z0-9._-]*[a-zA-Z0-9]))*([A-Za-z]|[A-Za-z][A-Za-z0-9._-]*[A-Za-z0-9])';
        }
        description
          "Host Name option of the dhcp client - option 12";
      }
      leaf interface-mtu {
        if-feature "srl_nokia-feat:dhcp-svr-option-26";
        type uint16 {
          range "68..9412";
        }
        description
          "This option specifies the MTU to use on this interface - option 26";
      }
      leaf-list ntp-server {
        type srl-comm:ipv4-address;
        must "not(starts-with(.,'0.') or starts-with(.,'127.') or re-match(.,'22[4-9]\\..*') or re-match(.,'2[3-5][0-9]\\..*'))" {
          error-message "Not a valid IPv4 unicast address";
        }
        max-elements 4;
        description
          "List of NTP Servers to return to the dhcp client - option 42";
      }
      leaf router {
        type srl-comm:ipv4-address;
        must "not(starts-with(.,'0.') or starts-with(.,'127.') or re-match(.,'22[4-9]\\..*') or re-match(.,'2[3-5][0-9]\\..*'))" {
          error-message "Not a valid IPv4 unicast address";
        }
        description
          "IPv4 address of the gateway for the dhcp client - option 3";
      }
      leaf server-id {
        type srl-comm:ipv4-address;
        must "not(starts-with(.,'0.') or starts-with(.,'127.') or re-match(.,'22[4-9]\\..*') or re-match(.,'2[3-5][0-9]\\..*'))" {
          error-message "Not a valid IPv4 unicast address";
        }
        description
          "IP address the dhcp server must match any address within the network_instance e.g. sub-interface primary address, loopback address,
           anycast gateway address in case of multihoming - option 54";
      }
      list static-route {
        if-feature "srl_nokia-feat:dhcp-svr-option-121";
        key "destination";
        description
          "This option can contain one or more static routes, each of which consists of a destination descriptor and the IP address of the router that should be used to reach that destination - option 121";
        max-elements 16;
        leaf destination {
          type srl-comm:ipv4-prefix;
          description
            "A destination descriptor";
        }
        leaf router {
          type srl-comm:ipv4-address;
          description
            "IP address of the router that should be used to reach that destination";
        }
      }
      leaf-list tftp-server-address {
        type srl-comm:ipv4-address;
        must "not(starts-with(.,'0.') or starts-with(.,'127.') or re-match(.,'22[4-9]\\..*') or re-match(.,'2[3-5][0-9]\\..*'))" {
          error-message "Not a valid IPv4 unicast address";
        }
        description
          "List of IP address of the TFTP servers the client will use to download bootfile/configuration script - option 150";
        max-elements 2;
      }
      leaf tftp-server-name {
        type string {
          length "1..63";
          pattern '(([a-zA-Z]|[a-zA-Z][a-zA-Z0-9._-]*[a-zA-Z0-9]))*([A-Za-z]|[A-Za-z][A-Za-z0-9._-]*[A-Za-z0-9])';
        }
        description
          "FQDN of the TFTP server the client will use to download bootfile/configuration script - option 66";
      }
      leaf lease-time {
        if-feature "srl_nokia-feat:dhcp-svr-boot-compute";
        type uint32 {
          range "60..4294967295";
        }
        units "seconds";
        default "86400";
        description
          "The time in seconds that the client should use the IP address before it must renew its lease - option 51";
      }
      leaf next-server {
        if-feature "srl_nokia-feat:dhcp-svr-boot-compute";
        type srl-comm:ipv4-address;
        must "not(starts-with(.,'0.') or starts-with(.,'127.') or re-match(.,'22[4-9]\\..*') or re-match(.,'2[3-5][0-9]\\..*'))" {
          error-message "Not a valid IPv4 unicast address";
        }
        description
          "The IP address of the next server to use for booting - option 54";
      }
      uses dhcpv4-custom-options-common;
      description
        "Enter the options context";
    }
  }

  grouping dhcp-server-v6-options {
    container options {
      leaf-list dns-server {
        type srl-comm:ipv6-address;
        must "not(.='::' or .='::1' or starts-with(.,'ff') or starts-with(.,'fe80'))" {
          error-message "Not a valid global unicast IPv6 address";
        }
        max-elements 4;
        description
          "An Ordered List of DNS servers to return to the dhcp client";
      }
      leaf-list domain-search-list {
        if-feature "srl_nokia-feat:dhcp-svr-boot-compute";
        type srl-comm:domain-name;
        max-elements 4;
        description
          "An ordered list of domains to return to the dhcp client that the client should search when resolving hostnames";
      }
      description
        "Enter the options context";
    }
  }

  grouping dhcp-server-v4 {
    container dhcpv4 {
      uses dhcp-common;
      uses dhcp-server-v4-options;
      uses static-allocation-v4;
      description
        "Enter the dhcpv4 context";
    }
  }

  grouping dhcp-server-v6 {
    container dhcpv6 {
      uses dhcp-common;
      uses dhcp-server-v6-options;
      uses static-allocation-v6;
      description
        "Enter the dhcpv6 context";
    }
  }

  grouping dhcp-netinst {
    list network-instance {
      description
        "List of network instances to run a dhcp server in";
      key "name";
      leaf name {
        type leafref {
          path "/srl-netinst:network-instance/srl-netinst:name";
        }
        must 'not(/srl-netinst:network-instance[srl-netinst:name=current()]/srl-netinst:type = "srl-netinst:mac-vrf")' {
          error-message "dhcp server cannot be started in a network-instance of type 'mac-vrf'";
        }
        description
          "Reference to a configured network instance";
      }
      uses dhcp-server-v4;
      uses dhcp-server-v6;
    }
  }

  grouping dhcp-server-top {
    container dhcp-server {
      presence "Performs DHCP server function";
      description
        "Configures the dhcp server";
      leaf admin-state {
        type srl-comm:admin-state;
        default "disable";
        srl-ext:show-importance "high";
        description
          "Globally enable or disable the dhcp server
           Disabling this will disable all dhcp servers.";
      }
      uses dhcp-netinst;
    }
  }

  augment "/srl-system:system" {
    if-feature "srl_nokia-feat:dhcp-server";
    srl-ext:first-released "21.6.1";
    uses dhcp-server-top;
  }
}
