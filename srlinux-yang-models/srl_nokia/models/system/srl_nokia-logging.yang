module srl_nokia-logging {
  yang-version 1.1;
  namespace "urn:nokia.com:srlinux:log:logging";
  prefix srl_nokia-logging;

  import srl_nokia-system {
    prefix srl-system;
  }
  import srl_nokia-common {
    prefix srl-comm;
  }
  import srl_nokia-tls {
    prefix srl-tls;
  }
  import srl_nokia-network-instance {
    prefix srl-netinst;
  }
  import srl_nokia-features {
    prefix srl-feat;
  }
  import srl_nokia-extensions {
    prefix srl-ext;
  }

  organization
    "Nokia";
  contact
    "Nokia SR Linux Support
     Web: <http://www.nokia.com>";
  description
    "This module describes a YANG model for system logging.";

  revision 2026-07-31 {
    description
      "SRLinux 26.7.1";
  }
  revision 2026-03-31 {
    description
      "SRLinux 26.3.1";
  }
  revision 2025-10-31 {
    description
      "SRLinux 25.10.1";
  }
  revision 2025-07-31 {
    description
      "SRLinux 25.7.1";
  }
  revision 2025-03-31 {
    description
      "SRLinux 25.3.1";
  }
  revision 2024-10-31 {
    description
      "SRLinux 24.10.1";
  }
  revision 2024-07-31 {
    description
      "SRLinux 24.7.1";
  }
  revision 2024-03-31 {
    description
      "SRLinux 24.3.1";
  }
  revision 2023-10-31 {
    description
      "SRLinux 23.10.1";
  }
  revision 2023-07-31 {
    description
      "SRLinux 23.7.1";
  }
  revision 2023-03-31 {
    description
      "SRLinux 23.3.1";
  }
  revision 2022-11-30 {
    description
      "SRLinux 22.11.1";
  }
  revision 2022-06-30 {
    description
      "SRLinux 22.6.1";
  }
  revision 2022-03-31 {
    description
      "SRLinux 22.3.1";
  }
  revision 2021-11-30 {
    description
      "SRLinux 21.11.1";
  }
  revision 2021-06-30 {
    description
      "SRLinux 21.6.1";
  }
  revision 2021-03-31 {
    description
      "SRLinux 21.3.1";
  }
  revision 2020-06-30 {
    description
      "SRLinux 20.6.1";
  }
  revision 2019-11-30 {
    description
      "SRLinux 19.11.1";
  }

  identity srlinux-subsystem {
    description
      "Base identity for SR Linux subsystems";
  }

  identity aaa {
    base srlinux-subsystem;
    description
      "Messages generated by aaa_mgr (not including accounting)";
  }

  identity accounting {
    base srlinux-subsystem;
    description
      "Accounting messages generated by aaa_mgr";
  }

  identity acl {
    if-feature "not srl-feat:platform-imgmt";
    base srlinux-subsystem;
    description
      "Messages generated through an acl_mgr log action";
  }

  identity alarm {
    base srlinux-subsystem;
    description
      "Messages generated by alarm_mgr";
  }

  identity app {
    base srlinux-subsystem;
    description
      "Messages generated by app_mgr";
  }

  identity arpnd {
    if-feature "not srl-feat:platform-imgmt";
    base srlinux-subsystem;
    description
      "Messages generated by arp_nd_mgr";
  }

  identity bfd {
    if-feature "not srl-feat:platform-imgmt";
    base srlinux-subsystem;
    description
      "Messages generated by bfd_mgr";
  }

  identity bgp {
    if-feature "not srl-feat:platform-imgmt";
    base srlinux-subsystem;
    description
      "Messages generated by bgp_mgr";
  }

  identity bridgetable {
    if-feature "not srl-feat:platform-imgmt";
    base srlinux-subsystem;
    description
      "Messages generated by fdb_mgr";
  }

  identity cflowd {
    if-feature "not srl-feat:platform-imgmt";
    base srlinux-subsystem;
    description
      "Messages generated by cflowd_mgr";
  }

  identity chassis {
    if-feature "not srl-feat:platform-imgmt";
    base srlinux-subsystem;
    description
      "Messages generated by chassis_mgr";
  }

  identity debug {
    base srlinux-subsystem;
    description
      "Messages generated by application debug";
  }

  identity dhcp {
    if-feature "not srl-feat:platform-imgmt";
    base srlinux-subsystem;
    description
      "Messages generated by dhcp_client_mgr";
  }

  identity ethcfm {
    if-feature "not srl-feat:platform-imgmt";
    base srlinux-subsystem;
    description
      "Messages generated by ethcfm_mgr";
  }

  identity evpn {
    if-feature "not srl-feat:platform-imgmt";
    base srlinux-subsystem;
    description
      "Messages generated by evpn_mgr";
  }

  identity fib {
    if-feature "not srl-feat:platform-imgmt";
    base srlinux-subsystem;
    description
      "Messages generated by fib_mgr";
  }

  identity gnmi {
    base srlinux-subsystem;
    description
      "Messages generated by gnmi_server";
  }

  identity gnoi {
    if-feature "not srl-feat:platform-imgmt";
    base srlinux-subsystem;
    description
      "Messages generated by gnoi_mgr";
  }

  identity gnpsi {
    if-feature "not srl-feat:platform-imgmt";
    base srlinux-subsystem;
    description
      "Messages generated by gnpsi_mgr";
  }

  identity gnsi {
    if-feature "not srl-feat:platform-imgmt";
    base srlinux-subsystem;
    description
      "Messages generated by gnsi_mgr";
  }

  identity gribi {
    if-feature "not srl-feat:platform-imgmt";
    base srlinux-subsystem;
    description
      "Messages generated by gribi_server";
  }

  identity grpc {
    base srlinux-subsystem;
    description
      "Messages generated by grpc_mgr";
  }

  identity igmp {
    if-feature "not srl-feat:platform-imgmt";
    base srlinux-subsystem;
    description
      "Messages generated by igmp_mgr";
  }

  identity isis {
    if-feature "not srl-feat:platform-imgmt";
    base srlinux-subsystem;
    description
      "Messages generated by isis_mgr";
  }

  identity json {
    if-feature "not srl-feat:platform-imgmt";
    base srlinux-subsystem;
    description
      "Messages generated by json_rpc_server";
  }

  identity lag {
    if-feature "not srl-feat:platform-imgmt";
    base srlinux-subsystem;
    description
      "Messages generated by lag_mgr";
  }

  identity ldp {
    if-feature "not srl-feat:platform-imgmt";
    base srlinux-subsystem;
    description
      "Messages generated by ldp_mgr";
  }

  identity license {
    base srlinux-subsystem;
    description
      "Messages generated by license_mgr";
  }

  identity linux {
    base srlinux-subsystem;
    description
      "Messages generated by linux_mgr";
  }

  identity lldp {
    if-feature "not srl-feat:platform-imgmt";
    base srlinux-subsystem;
    description
      "Messages generated by lldp_mgr";
  }

  identity log {
    base srlinux-subsystem;
    description
      "Messages generated by log_mgr";
  }

  identity mgmt {
    base srlinux-subsystem;
    description
      "Messages generated by mgmt_server";
  }

  identity mirror {
    if-feature "not srl-feat:platform-imgmt";
    base srlinux-subsystem;
    description
      "Messages generated by mirror_mgr";
  }

  identity mld {
    if-feature "not srl-feat:platform-imgmt";
    base srlinux-subsystem;
    description
      "Messages generated by mld_mgr";
  }

  identity mpls {
    if-feature "not srl-feat:platform-imgmt";
    base srlinux-subsystem;
    description
      "Messages generated by mpls_mgr";
  }

  identity msdp {
    if-feature "not srl-feat:platform-imgmt";
    if-feature "srl-feat:msdp";
    base srlinux-subsystem;
    description
      "Messages generated by msdp_mgr";
  }

  identity netconf {
    base srlinux-subsystem;
    description
      "Messages generated by netconf_mgr";
  }

  identity netinst {
    if-feature "not srl-feat:platform-imgmt";
    base srlinux-subsystem;
    description
      "Messages generated by net_inst_mgr";
  }

  identity oam_pm {
    base srlinux-subsystem;
    description
      "Messages generated by oam_pm_mgr";
  }

  identity ospf {
    if-feature "not srl-feat:platform-imgmt";
    base srlinux-subsystem;
    description
      "Messages generated by ospf_mgr";
  }

  identity p4rt {
    if-feature "not srl-feat:platform-imgmt";
    base srlinux-subsystem;
    description
      "Messages generated by p4rt_server";
  }

  identity pcc {
    if-feature "not srl-feat:platform-imgmt";
    base srlinux-subsystem;
    description
      "Messages generated by pcc_mgr";
  }

  identity pim {
    if-feature "not srl-feat:platform-imgmt";
    base srlinux-subsystem;
    description
      "Messages generated by pim_mgr";
  }

  identity platform {
    if-feature "not srl-feat:platform-imgmt";
    base srlinux-subsystem;
    description
      "Messages generated by chassis_mgr";
  }

  identity policy {
    if-feature "not srl-feat:platform-imgmt";
    base srlinux-subsystem;
    description
      "Messages generated by policy_mgr";
  }

  identity pw {
    if-feature "not srl-feat:platform-imgmt";
    base srlinux-subsystem;
    description
      "Messages generated by pw_mgr";
  }

  identity qos {
    if-feature "not srl-feat:platform-imgmt";
    base srlinux-subsystem;
    description
      "Messages generated by qos_mgr";
  }

  identity sath {
    if-feature "not srl-feat:platform-imgmt";
    base srlinux-subsystem;
    description
      "Messages generated by sath_mgr";
  }

  identity sdk {
    if-feature "not srl-feat:platform-imgmt";
    base srlinux-subsystem;
    description
      "Messages generated by sdk_mgr";
  }

  identity sflow {
    if-feature "not srl-feat:platform-imgmt";
    base srlinux-subsystem;
    description
      "Messages generated by sflow_sample_mgr";
  }

  identity staticroute {
    if-feature "not srl-feat:platform-imgmt";
    base srlinux-subsystem;
    description
      "Messages generated by static_route_mgr";
  }

  identity stp {
    if-feature "not srl-feat:platform-imgmt";
    base srlinux-subsystem;
    description
      "Messages generated by stp_mgr";
  }

  identity sync {
    if-feature "not srl-feat:platform-imgmt";
    base srlinux-subsystem;
    description
      "Messages generated by sync_mgr";
  }

  identity tls {
    if-feature "not srl-feat:platform-imgmt";
    base srlinux-subsystem;
    description
      "Messages generated by tls_mgr";
  }

  identity twamp {
    if-feature "not srl-feat:platform-imgmt";
    base srlinux-subsystem;
    description
      "Messages generated by twamp_mgr";
  }

  identity usrcontainer {
    base srlinux-subsystem;
    description
      "Messages identified as user container executed operations";
  }

  identity vxlan {
    if-feature "not srl-feat:platform-imgmt";
    base srlinux-subsystem;
    description
      "Messages generated by vxlan_mgr";
  }

  identity xdp {
    if-feature "not srl-feat:platform-imgmt";
    base srlinux-subsystem;
    description
      "Messages generated by xdp_mgr";
  }

  grouping logging-top {
    typedef priority-type {
      type enumeration {
        enum emergency;
        enum alert;
        enum critical;
        enum error;
        enum warning;
        enum notice;
        enum informational;
        enum debug;
      }
      description
        "In increasing severity, they are: debug, informational, notice, warning, error, critical, emergency";
    }

    typedef subsystem-name-type {
      description
        "Subsystems that produce syslog input, and can be forwarded to output entities";
      type identityref {
        base srlinux-subsystem;
      }
    }

    typedef facility-name-type {
      type enumeration {
        enum all;
        enum audit;
        enum auth;
        enum authpriv;
        enum console;
        enum cron;
        enum daemon;
        enum ftp;
        enum kern;
        enum lpr;
        enum mail;
        enum news;
        enum ntp;
        enum syslog;
        enum user;
        enum uucp;
        enum local0;
        enum local1;
        enum local2;
        enum local3;
        enum local4;
        enum local5;
        enum local6;
        enum local7;
      }
      description
        "Name of a Linux entity that can produce messages

         Some are generic and many programs produce them.";
    }

    typedef facility-name-type-subset {
      type facility-name-type {
        enum auth;
        enum authpriv;
        enum cron;
        enum daemon;
        enum ftp;
        enum kern;
        enum lpr;
        enum mail;
        enum news;
        enum ntp;
        enum syslog;
        enum user;
        enum uucp;
        enum local0;
        enum local1;
        enum local2;
        enum local3;
        enum local4;
        enum local5;
        enum local6;
        enum local7;
      }
      description
        "Linux entity that identifies messages from applications";
    }

    typedef transport-type {
      type enumeration {
        enum udp;
        enum tcp;
        enum tls;
      }
      description
        "Type of IP transport protocol used between local rsyslogd and a remote one";
    }

    typedef usage-capacity-size-type {
      type string {
        pattern '[1-9][0-9]{0,15}(K|M|G){0,1}';
      }
      description
        "Maximum number of bytes budgeted for an individual file

         The rotate feature can create several individual files.";
    }

    typedef restricted-file-name-type {
      type string {
        length "1..255";
        pattern '([^./][^/]*)|(\.[^\./]+)|(\.\.[^/])+';
      }
    }

    typedef directory-name-type {
      type string {
        pattern '/(.)*';
      }
    }

    typedef rsyslog-local-format-template {
      type enumeration {
        enum RSYSLOG_FileFormat;
        enum RSYSLOG_TraditionalFileFormat;
        enum RSYSLOG_DebugFormat;
      }
      description
        "Rsyslog predefined format templates for local files, buffers and console";
    }

    typedef rsyslog-remote-format-template {
      type enumeration {
        enum RSYSLOG_ForwardFormat;
        enum RSYSLOG_SyslogProtocol23Format;
        enum RSYSLOG_TraditionalForwardFormat;
      }
      description
        "Rsyslog predefined format templates for messaging to remote servers";
    }

    grouping local-format-grouping {
      leaf format {
        type union {
          type string {
            length "1..255";
          }
          type rsyslog-local-format-template;
        }
        default "RSYSLOG_FileFormat";
        description
          "Text format of syslog messages to a local output (buffer, file or console), in legacy rsyslog $template style or one of the predefined templates

           The default presents a date timestamp according to rfc3339.
           The predefined templates are the ones supported by rsyslogd.";
      }
    }

    grouping remote-format-grouping {
      leaf format {
        type union {
          type string {
            length "1..255";
          }
          type rsyslog-remote-format-template;
        }
        default "RSYSLOG_SyslogProtocol23Format";
        description
          "Text format of syslog messages to a remote server, in legacy rsyslog $template style or one of the predefined templates

           The default presents a date timestamp according to rfc3339.
           The predefined templates are the ones supported by rsyslogd.";
      }
    }

    grouping priority-match-grouping {
      container priority {
        leaf match-above {
          type priority-type;
          description
            "At a given severity and above";
        }
        leaf-list match-exact {
          type priority-type;
          description
            "Individually specified severities";
        }
        description
          "Enter the priority context

           Narrows the capture to a given severity, a range or a specific set of severities";
      }
    }

    grouping facility-grouping {
      list facility {
        description
          "List of facilities to source messages from";
        key "facility-name";
        leaf facility-name {
          description
            "Name of a Linux syslog facility";
          type facility-name-type;
        }
        uses priority-match-grouping;
      }
    }

    grouping subsystem-grouping {
      list subsystem {
        key "subsystem-name";
        leaf subsystem-name {
          type subsystem-name-type;
          description
            "Reference to an available subsystem to source messages from";
        }
        description
          "Entity or entities that may produce messages to be captured";
        uses priority-match-grouping;
      }
    }

    grouping filter-reference-grouping {
      leaf-list filter {
        type leafref {
          path "/srl-system:system/logging/filter/filter-name";
        }
        description
          "A set of all-matching criteria that messages must fulfill in order to be captured";
      }
    }

    grouping retention-grouping {
      leaf rotate {
        type uint16;
        default "4";
        description
          "Number of files to keep in rotation when a maximum file size is reached";
      }
      leaf rotations {
        config false;
        type srl-comm:zero-based-counter64;
        description
          "Number of file rotations occurred";
      }
      leaf size {
        type usage-capacity-size-type;
        default "10M";
        description
          "Number of bytes an individual output file cannot exceed

           The field allows the 'K, M, or G' suffixes as shorthand.
           When reaching that size, a rotation happens and subsequent data is stored
           in a new file with the same base name.";
      }
    }

    grouping composition-operator-grouping {
      leaf composition-operator {
        type enumeration {
          enum or;
          enum and;
        }
        default "or";
        description
          "Logical operation between filters";
      }
    }

    container logging {
      description
        "Enter the logging context

         System logging provides the interface to syslog services
         to setup output entities on a selection of log sources.";
      container console {
        description
          "Enter the console context

           Hardware serial device normally used for bring-up and diagnostics";
        uses local-format-grouping;
        uses facility-grouping;
        uses subsystem-grouping;
        uses filter-reference-grouping;
      }
      list filter {
        key "filter-name";
        description
          "Describes a set of critieria that captured messages are required to fulfill";
        leaf filter-name {
          description
            "Name of the filter";
          type string {
            length "1..255";
            pattern '([0-9a-zA-Z\-_.@!%^*()\[\]{}|\\/<>,;])+';
          }
        }
        leaf prefix {
          type string;
          description
            "Text to be present at the beginning of the MSG property of a message
             This is a fast lookup.";
        }
        leaf not-prefix {
          type string;
          if-feature "srl-feat:log-filter-for-negation";
          description
            "Text to be not present at the beginning of the MSG property of a message
             This is a fast lookup.";
        }
        leaf contains {
          type string;
          description
            "Text to find in the MSG property of messages to capture from the stream
             This is slower than prefix.";
        }
        leaf not-contains {
          type string;
          if-feature "srl-feat:log-filter-for-negation";
          description
            "Text to not find in the MSG property of messages to capture from the stream
             This is slower than prefix.";
        }
        leaf tag {
          type string;
          description
            "Text to be searched in the SYSLOGTAG property of messages
             Usually a program name or part of it.";
        }
        leaf regex {
          type string;
          description
            "Extended regular expression to search in the MSG property of messages";
        }
        leaf not-regex {
          type string;
          if-feature "srl-feat:log-filter-for-negation";
          description
            "Extended regular expression to not have in the MSG property of messages";
        }
        uses facility-grouping;
        uses subsystem-grouping;
        uses composition-operator-grouping;
      }
      list buffer {
        key "buffer-name";
        description
          "Log files maintained in memory, non-persistent across system reboots

           These files are stored at directory /var/log/srlinux/buffer. Rotation into multiple files is available.";
        leaf buffer-name {
          type restricted-file-name-type;
          description
            "Base name of the file(s) to be stored in memory";
        }
        leaf persist {
          type uint32 {
            range "0 | 60..604800";
          }
          description
            "Time in seconds to shadow the buffer to persistent storage

             Setting this field to 0 results in the buffer not being persisted. A value other than 0 will result in the log being persisted to disk based on the configured value. Logs with a non-zero persist value are persisted automatically on rollover, or at the configured value.";
          units "seconds";
          default "0";
        }
        uses local-format-grouping;
        uses retention-grouping;
        uses facility-grouping;
        uses subsystem-grouping;
        uses filter-reference-grouping;
      }
      list file {
        key "file-name";
        description
          "Log files maintained on disk, persistent across system reboots

           When a maximum file size is reached, the file is renamed and a maximum
           rotate number of them are kept.";
        leaf file-name {
          type restricted-file-name-type;
          description
            "Base name of the file(s) to be stored on disk";
        }
        leaf directory {
          type directory-name-type;
          default "/var/log/srlinux/file";
          description
            "Fully qualified path of a directory where the log file(s) shall be maintained";
        }
        uses local-format-grouping;
        uses retention-grouping;
        uses facility-grouping;
        uses subsystem-grouping;
        uses filter-reference-grouping;
      }
      list remote-server {
        key "host";
        description
          "List of output remote syslog servers";
        leaf host {
          type srl-comm:host-ietf;
          description
            "Domain or IP address of a remote syslog server destination";
        }
        leaf transport {
          type transport-type;
          default "udp";
          description
            "Transport protocol for syslog to use for messages sent to a remote server";
        }
        leaf tls-profile {
          type leafref {
            path "/srl-system:system/srl-tls:tls/srl-tls:profile/srl-tls:name";
            require-instance false;
          }
          must "../transport = 'tls'" {
            error-message "transport must be set to tls to assign a tls-profile.";
          }
          srl-ext:show-importance "high";
          if-feature "srl-feat:log-tls";
          description
            "Reference to a TLS profile to use for the transport of syslog messages

             If none is specified, then TLS is not used.

             The configuration of a cipher-list in the TLS profile will not be used by syslog.
             Using the __default__ TLS profile is not supported as there is no trust-anchor configured.";
        }
        leaf remote-port {
          type uint32 {
            range "0..65535";
          }
          description
            "Transport port for syslog to use for messages sent to a remote server
             By default, UDP/TCP uses port 514 and TLS uses port 6514.";
        }
        leaf source-address {
          if-feature "not srl-feat:platform-imgmt";
          type srl-comm:ip-address;
          description
            "Source address for syslog to use for messages sent to a remote server

             If no source address is provided, then packets will be sent to the remote server using the source address indicated by the routing table.";
        }
        leaf network-instance {
          if-feature "not srl-feat:platform-imgmt";
          type leafref {
            path "/srl-netinst:network-instance/srl-netinst:name";
          }
          must 'not(/srl-netinst:network-instance[srl-netinst:name=current()]/srl-netinst:type = "srl-netinst:mac-vrf")' {
            error-message "Syslog server cannot be started in a network-instance of type 'mac-vrf'";
          }
          description
            "Reference to a configured network-instance to run rsyslogd in

             This network-instance will be used as a source for requests to remote syslog servers.";
        }
        uses remote-format-grouping;
        uses facility-grouping;
        uses subsystem-grouping;
        uses filter-reference-grouping;
      }
      leaf subsystem-facility {
        type facility-name-type-subset;
        default "local6";
        description
          "Linux facility that internal application subsystems will use";
      }
      leaf network-instance {
        if-feature "not srl-feat:platform-imgmt";
        type leafref {
          path "/srl-netinst:network-instance/srl-netinst:name";
        }
        must 'not(/srl-netinst:network-instance[srl-netinst:name=current()]/srl-netinst:type = "srl-netinst:mac-vrf")' {
          error-message "Syslog server cannot be started in a network-instance of type 'mac-vrf'";
        }
        description
          "Reference to a configured network-instance to run rsyslogd in

           This network-instance will be used as a source for requests to remote syslog servers.";
      }
      leaf use-fqdn {
        if-feature "not srl-feat:platform-imgmt";
        type boolean;
        default "false";
        description
          "Use the FQDN instead of only the hostname for logging messages";
      }
    }
  }

  augment "/srl-system:system" {
    uses logging-top;
  }
}
