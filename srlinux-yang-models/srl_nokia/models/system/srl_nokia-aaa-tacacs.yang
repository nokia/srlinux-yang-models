module srl_nokia-aaa-tacacs {
  yang-version 1.1;
  namespace "urn:nokia.com:srlinux:general:aaa-tacacs";
  prefix srl-aaa-tacacs;

  import srl_nokia-aaa-types {
    prefix srl-aaa-types;
  }
  import srl_nokia-features {
    prefix srl-feat;
  }
  import srl_nokia-system {
    prefix srl-system;
  }
  import srl_nokia-common {
    prefix srl-comm;
  }
  import srl_nokia-extensions {
    prefix srl-ext;
  }

  organization
    "Nokia";
  contact
    "Nokia SR Linux Support
     Web: <http://www.nokia.com>";
  description
    "This module defines configuration and operational state data
     related to the TACACS+ protocol for authentication,
     authorization, and accounting.";

  revision 2026-07-31 {
    description
      "SRLinux 26.7.1";
  }
  revision 2025-07-31 {
    description
      "SRLinux 25.7.1";
  }
  revision 2025-03-31 {
    description
      "SRLinux 25.3.1";
  }
  revision 2024-03-31 {
    description
      "SRLinux 24.3.1";
  }
  revision 2023-03-31 {
    description
      "SRLinux 23.3.1";
  }
  revision 2021-06-30 {
    description
      "SRLinux 21.6.1";
  }
  revision 2021-03-31 {
    description
      "SRLinux 21.3.1";
  }
  revision 2019-11-30 {
    description
      "SRLinux 19.11.1";
  }

  grouping aaa-tacacs-server-config {
    description
      "Configuration data for a TACACS+ server";
    leaf port {
      type srl-comm:port-number;
      default "49";
      must '. = 49 or ../../../type = "srl-aaa-types:tacacs"' {
        error-message "TACACS+ port configuration supported for 'tacacs' server type only";
      }
      description
        "The port number on which to contact the TACACS+ server";
    }
    leaf secret-key {
      type srl-comm:routing-password;
      must '../../../type = "srl-aaa-types:tacacs"' {
        error-message "TACACS+ secret-key configuration supported for 'tacacs' server type only";
      }
      description
        "The unencrypted shared key used between the system and server, up to 128 characters cleartext";
    }
    leaf source-address {
      if-feature "srl-feat:tacacs-source-address and not srl-feat:platform-imgmt";
      type srl-comm:ip-address;
      must '../../../type = "srl-aaa-types:tacacs"' {
        error-message "TACACS+ source-address configuration supported for 'tacacs' server type only";
      }
      description
        "Source address for TACACS to use for messages sent to a remote server";
    }
  }

  grouping aaa-tacacs-server-top {
    description
      "Top-level grouping for TACACS+ server data";
    container tacacs {
      description
        "Enter the tacacs context

         Top-level container for TACACS+ server data";
      uses aaa-tacacs-server-config;
    }
  }
}
