module srl_nokia-event-handler {
  yang-version 1.1;
  namespace "urn:nokia.com:srlinux:event:event-handler";
  prefix srl-event-handler;

  import srl_nokia-common {
    prefix srl-comm;
  }
  import srl_nokia-system {
    prefix srl-system;
  }
  import srl_nokia-aaa {
    prefix srl-aaa;
  }
  import srl_nokia-extensions {
    prefix srl-ext;
  }
  import srl_nokia-features {
    prefix srl-feat;
  }

  organization
    "Nokia";
  contact
    "Nokia SR Linux Support
     Web: <http://www.nokia.com>";
  description
    "This module defines configuration and operational state data related to the event handler";

  revision 2026-07-31 {
    description
      "SRLinux 26.7.1";
  }
  revision 2025-10-31 {
    description
      "SRLinux 25.10.1";
  }
  revision 2025-07-31 {
    description
      "SRLinux 25.7.1";
  }
  revision 2022-11-30 {
    description
      "SRLinux 22.11.1";
  }
  revision 2022-06-30 {
    description
      "SRLinux 22.6.1";
  }
  revision 2022-03-31 {
    description
      "SRLinux 22.3.1";
  }

  typedef eh-instance-oper-reason {
    type enumeration {
      enum admin-disabled {
        description
          "Event handler instance is admin-disabled";
      }
      enum failed-to-compile {
        description
          "Event handler failed to compile the script, indicating that the script likely has a syntax error";
      }
      enum exception {
        description
          "Event handler caught an exception in the last execution of the script";
      }
      enum timeout {
        description
          "Last execution of the script did not complete before a timeout occurred";
      }
      enum subscription-failed {
        description
          "Event handler was unable to subscribe to the provided paths";
      }
      enum script-unavailable {
        description
          "Event handler was unable to find the script on the filesystem";
      }
      enum script-error {
        description
          "Script returned something invalid";
      }
      enum missing-function {
        description
          "Event handler was unable to find a function named event_handler_main() in the provided script";
      }
      enum system-error {
        description
          "Failure in setting up the python environment";
      }
      enum ephemeral-action-failed {
        description
          "Event handler was unable to perform an ephemeral-path action in the previous execution";
      }
      enum cfg-action-failed {
        description
          "Event handler was unable to perform a cfg-path action in the previous execution";
      }
      enum tools-action-failed {
        description
          "Event handler was unable to perform a tools-path action in the previous execution";
      }
      enum state-action-failed {
        description
          "Event handler was unable to perform a state-path action in the previous execution";
      }
      enum script-action-failed {
        description
          "Event handler was unable to perform a script action in the previous execution";
      }
    }
  }

  grouping eh-statistics-top {
    container statistics {
      config false;
      description
        "Enter the statistics context

         Top-level container for event handler statistics";
      leaf upython-duration {
        type uint64;
        units "milliseconds";
        description
          "Total time taken for all executions of this script to return output";
      }
      leaf execution-count {
        type srl-comm:zero-based-counter64;
        description
          "Total number of executions of this script";
      }
      leaf execution-successes {
        type srl-comm:zero-based-counter64;
        description
          "Total number of successful executions of this script";
      }
      leaf execution-timeouts {
        type srl-comm:zero-based-counter64;
        description
          "Total number of timeouts in executions of this script";
      }
      leaf execution-errors {
        type srl-comm:zero-based-counter64;
        description
          "Total number of errors in executions of this script";
      }
    }
  }

  grouping eh-execution-state {
    leaf oper-down-reason {
      type eh-instance-oper-reason;
      config false;
      srl-ext:show-importance "low";
      description
        "Reason this instance is or was in its last operational state";
    }
    leaf oper-down-reason-detail {
      srl-ext:show-importance "low";
      type string;
      description
        "Any additional detail event handler can provide around the last operational state of this instance";
    }
    leaf start-time {
      type srl-comm:date-and-time-delta;
      srl-ext:show-importance "high";
      description
        "Time this instance last started execution";
    }
    leaf end-time {
      type srl-comm:date-and-time-delta;
      srl-ext:show-importance "high";
      description
        "Time this instance last finished execution

         This timestamp includes any actions provided as output from the execution";
    }
    leaf upython-duration {
      type uint64;
      units "microseconds";
      description
        "Time taken for the instance to return output";
    }
    leaf input {
      type string;
      description
        "Input provided to the script";
    }
    leaf output {
      type string;
      description
        "Output received from the script

         If empty, no response was received.";
    }
    leaf stdout-stderr {
      type string;
      description
        "Output printed on STDOUT or STDERR during this execution";
    }
  }

  grouping eh-state-top {
    leaf oper-state {
      config false;
      type srl-comm:oper-state;
      srl-ext:show-importance "high";
      description
        "Details if this event handler instance is operationally available";
    }
    container last-execution {
      config false;
      description
        "Enter the last-execution context

         Operational state of the last execution of this instance";
      uses eh-execution-state;
    }
    container last-errored-execution {
      config false;
      description
        "Enter the last-errored-execution context

         Operational state of the last errored execution of this instance";
      uses eh-execution-state;
    }
  }

  grouping eh-top {
    container event-handler {
      presence "Start the event handler";
      description
        "Top-level container for configuration and state of event handler and event handling instances";
      leaf run-as-user {
        description
          "User configured to run event handler instances

           If no user is configured, scripts are executed as the 'admin' user.";
        type leafref {
          path "/srl-system:system/srl-aaa:aaa/srl-aaa:authentication/srl-aaa:user/srl-aaa:username";
        }
      }
      list instance {
        max-elements 20;
        description
          "List of all event handler instances

           An event handler instance consists of a set of paths monitored for changes and a Python script to execute if changes occur.";
        key "name";
        leaf name {
          type srl-comm:name;
          description
            "User-defined name for this event handler instance";
        }
        leaf admin-state {
          type srl-comm:admin-state;
          srl-ext:show-importance "high";
          default "disable";
          description
            "Administratively enable or disable this event handler instance";
        }
        leaf trigger-on {
          if-feature "srl-feat:event-handler-cron";
          type enumeration {
            enum all;
            enum cron;
            enum change;
          }
          srl-ext:show-importance "high";
          default "all";
          description
            "Indicates which triggers should be used to execute the script

             'all' can be used to allow both cron (if configured) and change triggers, whereas 'cron' and 'change' allow a script to be executed only on a specific trigger type.";
        }
        leaf cron {
          if-feature "srl-feat:event-handler-cron";
          type string;
          srl-ext:show-importance "high";
          must "not(../trigger-on = 'change')" {
            error-message "cron cannot be used with trigger-on set to change";
          }
          description
            "Cron expression describing the interval at which to run the script

             This expression is in the Linux cron format of five fields separated by whitespace - '<minutes> <hours> <days-of-month> <months> <days-of-week>'.

             Certain special characters can be used to assist in describing an interval:
             '?' can be used to specify one field and leave another unspecified, e.g. '11 11 11 11 ?' meaning to run on every November 11th at 11:11 AM.
             '*' can be used as a wildcard, e.g. '* * * * ?' meaning to run every minute of every hour of every day of the month of every month.
             '-' can be used to specify a range, e.g. '1-50' in the <minutes> field indicating to run every minute between and including 1-50.
             ',' can be used to provide a list of values within a field, e.g. '1,3,5'.
             '/' can be used to specify increments, e.g. '*/5 * * * ?' meaning every 5 minutes.
             'L' can be used to specify the last day of the month or week. e.g. '15 10 L * ?' meaning to run at 10:15 AM on the last day of every month.

             Keywords can also be used:
             '@yearly' resulting in '0 0 1 1 *', or run at midnight on the 1st of January.
             '@monthly' resulting in '0 0 1 * *' or run at midnight on the 1st of every month.
             '@weekly' resulting in '0 0 * * 0', or run at midnight on Sunday every week.
             '@daily' resulting in '0 0 * * *', or run at midnight every day.
             '@hourly' resulting in '0 * * * *', or run at the top of every hour.
             '@reboot' resulting in execution at startup.

             Valid values for fields outside of the above special characters are:
             <minutes>: 0-59
             <hours>: 0-23
             <days-of-month>: 1-31, ?, L
             <months>: 1-12
             <days-of-week>: 0-6 (0 is Sunday), ?, L, SUN-SAT";
        }
        leaf-list paths {
          srl-ext:no-globbing;
          description
            "List of valid YANG paths in CLI notation to monitor for changes

             If any events are received on any of the provided paths, the configured script will be executed.

             This path may include keys, wildcards, ranges, and other management server supported constructs.

             E.g.
                 \"interface * oper-state\"
                 \"acl ipv4-filter foo* description\"";
          type string {
            pattern '[A-Za-z0-9 !@#$%^&()|+=`~.,/_:;?\-{}*\\\\"\[\]]+';
          }
        }
        container options {
          description
            "Enter the options context

             Options to be passed on each execution of the script";
          list object {
            key "name";
            leaf name {
              type srl-comm:name;
              description
                "Name of this object";
            }
            choice object {
              leaf-list values {
                srl-ext:no-globbing;
                ordered-by user;
                description
                  "List of values to associate with this object

                   These are serialized as a JSON array when provided as input to the script.";
                type string;
              }
              leaf value {
                srl-ext:no-globbing;
                description
                  "Single value to associate with this object";
                type string;
              }
            }
          }
        }
        leaf upython-script {
          description
            "File name of a MicroPython script, including .py suffix

             This script should already exist in /etc/opt/srlinux/eventmgr or /opt/srlinux/eventmgr directories.
             Explicit paths outside of these two directories are not permitted.";
          type string {
            pattern '([^./][^/]*)|(\.[^\./]+)|(\.\.[^/])+';
          }
        }
        uses eh-state-top;
        uses eh-statistics-top;
      }
    }
  }

  augment "/srl-system:system" {
    srl-ext:first-released "22.3.1";
    if-feature "srl-feat:event-handler";
    uses eh-top;
  }
}
