module srl_nokia-tools-oam {
  yang-version 1.1;
  namespace "urn:nokia.com:srlinux:oam:tools-oam";
  prefix srl_nokia-tools-oam;

  import srl_nokia-features {
    prefix srl_nokia-feat;
  }

  organization
    "Nokia";
  contact
    "Nokia SR Linux Support
     Web: <http://www.nokia.com>";
  description
    "Model for operational commands on OAM.";

  revision 2021-03-15 {
    description
      "SRLinux 21.06.1";
  }

  container oam {
    presence "Configure tools OAM";
    description
      "Enclosing container for OAM management.";
    container performance-monitoring {
      if-feature "srl_nokia-feat:oam-pm";
      presence "Configure tools OAM-PM";
      description
        "OAM Performance Monitoring";
    }
  }
}
