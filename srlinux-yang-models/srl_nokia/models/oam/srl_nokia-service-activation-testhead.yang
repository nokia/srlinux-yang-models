module srl_nokia-service-activation-testhead {
  yang-version 1.1;
  namespace "urn:nokia.com:srlinux:sath:service-activation-testhead";
  prefix srl_nokia-service-activation-testhead;

  import srl_nokia-common {
    prefix srl_nokia-comm;
  }
  import srl_nokia-ethcfm {
    prefix srl_nokia-ethcfm;
  }
  import srl_nokia-ethcfm-types {
    prefix srl_nokia-ethcfm-types;
  }
  import srl_nokia-features {
    prefix srl_nokia-feat;
  }
  import srl_nokia-network-instance {
    prefix srl_nokia-net-inst;
  }
  import srl_nokia-interfaces {
    prefix srl_nokia-if;
  }
  import srl_nokia-oam {
    prefix srl_nokia-oam;
  }
  import srl_nokia-service-activation-testhead-types {
    prefix srl_nokia-sath-types;
  }

  organization
    "Nokia";
  contact
    "Nokia SR Linux Support
     Web: <http://www.nokia.com>";
  description
    "This module contains configuration and state data definitions for service activation testead (SAT)";

  revision 2024-10-31 {
    description
      "SRLinux 24.10.1";
  }

  grouping state-testoam-service-activation-testhead {
    container results {
      description
        "Enter the service-activation-testhead context";
      list service-test {
        key "test-name";
        description
          "Enter the service-test list instance";
        leaf test-name {
          type srl_nokia-comm:name {
            length "1..64";
          }
          description
            "Service activation test name";
        }
      }
      container statistics {
        config false;
        description
          "Enter the statistics context";
        list service-test {
          key "test-name test-run";
          description
            "Enter the service-test list instance";
          leaf test-name {
            type srl_nokia-comm:name {
              length "1..64";
            }
            description
              "The name of the Service Activation Test";
          }
          leaf test-run {
            type uint32 {
              range "1..4294967295";
            }
            description
              "The run number of the OAM Service Activation service-test run to be read";
          }
          leaf description {
            type srl_nokia-comm:description;
            description
              "Configure the description of the service test";
          }
          leaf oper-state {
            type srl_nokia-sath-types:sath-statistics-test-run-oper-state;
            description
              "Indicates the operational state of the service-test run";
          }
          leaf accounting-oper-state {
            type enumeration {
              enum none {
                value 1;
              }
              enum ready-to-send {
                value 2;
              }
              enum sent {
                value 3;
              }
              enum unable-to-send {
                value 4;
              }
            }
            description
              "Indicates the operational status of the transfer of the service-test run's results
               to the accounting log";
          }
          leaf time-start {
            type union {
              type srl_nokia-comm:date-and-time;
              type enumeration {
                enum not-started {
                  value -1;
                }
              }
            }
            description
              "Indicates the start time (in UTC) of the specified service-test run";
          }
          leaf time-end {
            type union {
              type srl_nokia-comm:date-and-time;
              type enumeration {
                enum n/a {
                  value -1;
                }
              }
            }
            description
              "Indicates the end time (in UTC) of the specified service-test run";
          }
          leaf service-test-completion-notification {
            type boolean;
            description
              "Enable SNMP trap generation upon test completion";
          }
          leaf stream-run-type {
            type enumeration {
              enum sequential {
                value 1;
              }
              enum parallel {
                value 2;
              }
            }
            description
              "Service stream run order";
          }
          container test-duration {
            description
              "Enter the test-duration context";
            container cir {
              description
                "Enter the cir context";
              leaf minutes-seconds {
                type srl_nokia-sath-types:sath-mm-ss-string;
                description
                  "Duration of the service test CIR tests";
              }
            }
            container cir-pir {
              description
                "Enter the cir-pir context";
              leaf minutes-seconds {
                type srl_nokia-sath-types:sath-mm-ss-string;
                description
                  "Duration of the service test CIR-PIR tests";
              }
            }
            container policing {
              description
                "Enter the policing context";
              leaf minutes-seconds {
                type srl_nokia-sath-types:sath-mm-ss-string;
                description
                  "Duration of policing tests belonging to the test";
              }
            }
            container performance {
              description
                "Enter the performance context";
              leaf hours-minutes-seconds {
                type srl_nokia-sath-types:sath-hh-mm-ss-string;
                description
                  "Duration of performance tests belonging to the test";
              }
            }
          }
          list service-stream {
            key "stream-id";
            description
              "Enter the service-stream list instance";
            leaf stream-id {
              type uint32 {
                range "1..8";
              }
              description
                "The number of the service stream to be configured or read";
            }
            leaf description {
              type srl_nokia-comm:description;
              description
                "Configure the description of the service test";
            }
            leaf oper-state {
              type srl_nokia-sath-types:sath-statistics-test-run-oper-state;
              description
                "Indicates the operational state of the service stream run";
            }
            leaf network-instance {
              type leafref {
                path "/srl_nokia-net-inst:network-instance/srl_nokia-net-inst:name";
              }
              description
                "Indicates the router which hosts the Eth-CFM MEP, Domain, and
                 Association configured for the service stream";
            }
            leaf interface {
              type srl_nokia-net-inst:network-instance-subintf-name;
              description
                "The interface name

                 This can be configured in one of two forms.  Fully qualified reference to an interface subinterface,
                 example ethernet-1/1.1, or symbolic alias, example interface-1.  When the fully qualified name is
                 specified the 'interface-ref' should not be configured.  When the symbolic alias is specified the
                 'interface-ref' must be configured.";
              must '(. or ../interface-ref/interface)' {
                error-message "Interface name must be configured";
              }
            }
            container interface-ref {
              if-feature "srl_nokia-feat:interface-references";
              description
                "Reference to interface subinterface when symbolic alias is configured under the interface list";
              leaf interface {
                type leafref {
                  path "/srl_nokia-if:interface/srl_nokia-if:name";
                }
                description
                  "Reference to a base interface";
                must "starts-with(.,'eth') or starts-with(.,'lag')" {
                  error-message "Link measurement is supported for Ethernet interfaces only";
                }
                must 'not(/srl_nokia-if:interface[srl_nokia-if:name=current()]/srl_nokia-if:breakout-mode)' {
                  error-message "Breakout interfaces are not supported";
                }
                must '../subinterface >= 0' {
                  error-message "subinterface must be configured when interface is set";
                }
              }
              leaf subinterface {
                type leafref {
                  path "/srl_nokia-if:interface[srl_nokia-if:name=current()/../interface]/srl_nokia-if:subinterface/srl_nokia-if:index";
                }
                description
                  "Reference to the associated subinterface in network-instance";
                must '../interface' {
                  error-message "interface must be configured when subinterface is set";
                }
              }
            }
            leaf source-mac-address {
              type srl_nokia-comm:unicast-mac-address;
              description
                "Indicates the source MAC address for the service stream

                 00:00:00:00:00:00 is returned if a source MAC address is not available";
            }
            leaf acceptance-criteria-template {
              type srl_nokia-comm:name {
                length "1..64";
              }
              description
                "Configure the acceptance criteria template for the service stream";
            }
            leaf rate-cir {
              type uint32 {
                range "0..400000000";
              }
              units "kilobps";
              description
                "CIR packet transmit rate for the service stream";
            }
            leaf rate-pir {
              type uint32 {
                range "0..400000000";
              }
              units "kilobps";
              description
                "PIR packet transmit rate for the service stream";
            }
            leaf service-stream-completion-notification {
              type boolean;
              description
                "Enable SNMP trap generation upon test completion";
            }
            leaf size-a {
              type uint32 {
                range "64..9212";
              }
              units "bytes";
              description
                "Size-a";
            }
            leaf size-b {
              type uint32 {
                range "64..9212";
              }
              units "bytes";
              description
                "Size-b";
            }
            leaf size-c {
              type uint32 {
                range "64..9212";
              }
              units "bytes";
              description
                "Size-c";
            }
            leaf size-d {
              type uint32 {
                range "64..9212";
              }
              units "bytes";
              description
                "Size-d";
            }
            leaf size-e {
              type uint32 {
                range "64..9212";
              }
              units "bytes";
              description
                "Size-e";
            }
            leaf size-f {
              type uint32 {
                range "64..9212";
              }
              units "bytes";
              description
                "Size-f";
            }
            leaf size-g {
              type uint32 {
                range "64..9212";
              }
              units "bytes";
              description
                "Size-g";
            }
            leaf size-h {
              type uint32 {
                range "64..9212";
              }
              units "bytes";
              description
                "Size-h";
            }
            leaf size-u {
              type uint32 {
                range "64..9212";
              }
              units "bytes";
              description
                "Size-u";
            }
            leaf cir-threshold {
              type uint32 {
                range "0..400000000";
              }
              units "kilobps";
              description
                "Indicates the value of
                 /test-oam/service-activation-testhead/acceptance-criteria-template/cir-threshold
                 when the test run started";
            }
            leaf pir-threshold {
              type uint32 {
                range "0..400000000";
              }
              units "kilobps";
              description
                "Indicates the value of
                 /test-oam/service-activation-testhead/acceptance-criteria-template/pir-threshold
                 when the test run started";
            }
            leaf loss-threshold {
              type srl_nokia-sath-types:sath-loss-percent-union;
              description
                "Indicates the value of
                 /test-oam/service-activation-testhead/acceptance-criteria-template/loss-threshold
                 when the test run started";
            }
            leaf loss-threshold-policing {
              type srl_nokia-sath-types:sath-loss-percent-union;
              description
                "Indicates the value of
                 /test-oam/service-activation-testhead/acceptance-criteria-template/loss-threshold-policing
                 when the test run started";
            }
            leaf delay-threshold {
              type uint32 {
                range "0..100000000";
              }
              units "microseconds";
              description
                "Indicates the value of
                 /test-oam/service-activation-testhead/acceptance-criteria-template/delay-threshold
                 when the test run started";
            }
            leaf delay-var-threshold {
              type uint32 {
                range "0..100000000";
              }
              units "microseconds";
              description
                "Indicates the value of
                 /test-oam/service-activation-testhead/acceptance-criteria-template/delay-var-threshold
                 when the test run started";
            }
            leaf m-factor {
              type uint32 {
                range "0..400000000";
              }
              units "kilobps";
              description
                "Indicates the value of
                 /test-oam/service-activation-testhead/acceptance-criteria-template/m-factor
                 when the test run started";
            }
            container frame-mix {
              description
                "Enter the frame-mix context";
              leaf frame-size-template {
                type srl_nokia-comm:name {
                  length "1..64";
                }
                description
                  "Configure the frame size template for the service stream";
              }
              leaf sequence {
                type string {
                  length "1..16";
                }
                description
                  "Configure the sequence of frame sizes for the service stream";
              }
            }
            container test-types {
              description
                "Enter the test-types context";
              leaf cir {
                type boolean;
                description
                  "CIR test for the service stream";
              }
              leaf cir-pir {
                type boolean;
                description
                  "CIR-PIR test for the service stream";
              }
              leaf policing {
                type boolean;
                description
                  "Policing test for the service stream";
              }
              leaf performance {
                type boolean;
                description
                  "Performance test for the service stream";
              }
            }
            container frame-payload {
              description
                "Enter the frame-payload context";
              container data-pattern {
                description
                  "Enter the data-pattern context";
                leaf repeat {
                  type union {
                    type srl_nokia-comm:hex-string;
                    type uint16;
                  }
                  description
                    "Repeated 4-byte pattern to pad each packet sent";
                }
              }
              container ethernet {
                description
                  "Enter the ethernet context";
                leaf destination-mac-address {
                  type srl_nokia-comm:unicast-mac-address;
                  description
                    "Destination MAC address of Ethernet frames";
                }
                container eth-cfm {
                  description
                    "Enter the eth-cfm context";
                  container source {
                    description
                      "Enter the source context";
                    leaf mep-id {
                      type srl_nokia-ethcfm-types:mep-id-type;
                      description
                        "Source Ethernet maintenance association end point";
                    }
                    leaf domain-id {
                      type string;
                      description
                        "Source Ethernet maintenance domain name";
                    }
                    leaf association-id {
                      type string;
                      description
                        "Source Ethernet maintenance association name";
                    }
                  }
                }
                container s-tag {
                  description
                    "Enter the s-tag context";
                  leaf dot1p {
                    type uint32 {
                      range "0..7";
                    }
                    description
                      "PCP of Ethernet frames for service stream";
                  }
                  leaf discard-eligible {
                    type boolean;
                    description
                      "Enable marking of the DEI bit in the VLAN header";
                  }
                }
                container c-tag {
                  description
                    "Enter the c-tag context";
                  leaf dot1p {
                    type uint32 {
                      range "0..7";
                    }
                    description
                      "PCP of Ethernet frames for service stream";
                  }
                  leaf discard-eligible {
                    type boolean;
                    description
                      "Enable marking of the DEI bit in the VLAN header";
                  }
                }
              }
            }
            list test-results {
              key "test-type";
              description
                "Enter the test-results list instance";
              leaf test-type {
                type enumeration {
                  enum cir {
                    value 1;
                  }
                  enum cir-pir {
                    value 2;
                  }
                  enum policing {
                    value 3;
                  }
                  enum performance {
                    value 4;
                  }
                }
                description
                  "The test type to be read";
              }
              leaf oper-state {
                type srl_nokia-sath-types:sath-statistics-test-run-oper-state;
                description
                  "Indicates the operational state of the test run";
              }
              leaf time-start {
                type union {
                  type srl_nokia-comm:date-and-time;
                  type enumeration {
                    enum not-started {
                      value -1;
                    }
                  }
                }
                description
                  "Indicates the start time (in UTC) of the test run";
              }
              leaf time-end {
                type union {
                  type srl_nokia-comm:date-and-time;
                  type enumeration {
                    enum n/a {
                      value -1;
                    }
                  }
                }
                description
                  "Indicates the end time (in UTC) of the test run";
              }
              leaf time-left {
                type uint32;
                units "seconds";
                description
                  "Indicates the execution time remaining for the test run";
              }
              leaf oper-status-throughput {
                type srl_nokia-sath-types:sath-statistics-test-oper-state;
                description
                  "Indicates the test run's operational status, with respect to the throughput
                   acceptance criteria";
              }
              leaf oper-status-frame-loss-ratio {
                type srl_nokia-sath-types:sath-statistics-test-oper-state;
                description
                  "Indicates the test run's operational status, with respect to the FLR acceptance
                   criteria";
              }
              leaf oper-status-delay {
                type srl_nokia-sath-types:sath-statistics-test-oper-state;
                description
                  "Indicates the test run's operational status, with respect to the delay acceptance
                   criteria";
              }
              leaf oper-status-delay-var {
                type srl_nokia-sath-types:sath-statistics-test-oper-state;
                description
                  "Indicates the test run's operational status, with respect to the delay variation
                   acceptance criteria";
              }
              leaf measured-delay-min {
                type int32;
                units "microseconds";
                description
                  "Indicates the minimum delay measured for the test run";
              }
              leaf measured-delay-max {
                type int32;
                units "microseconds";
                description
                  "Indicates the maximum delay measured for the test run";
              }
              leaf measured-delay-avg {
                type int32;
                units "microseconds";
                description
                  "Indicates the average delay measured for the test run";
              }
              leaf measured-delay-var-min {
                type int32;
                units "microseconds";
                description
                  "Indicates the minimum delay variation measured for the test run";
              }
              leaf measured-delay-var-max {
                type int32;
                units "microseconds";
                description
                  "Indicates the maximum delay variation measured for the test run";
              }
              leaf measured-delay-var-avg {
                type int32;
                units "microseconds";
                description
                  "Indicates the average delay variation measured for the test run";
              }
              leaf measured-throughput {
                type uint32;
                units "kilobps";
                description
                  "Indicates the measured throughput for the test run";
              }
              leaf measured-frame-loss-ratio {
                type srl_nokia-sath-types:sath-loss-percent-decimal64;
                units "percent";
                description
                  "Indicates the measured FLR for the test run";
              }
              leaf measured-frame-tx {
                type srl_nokia-comm:zero-based-counter64;
                units "frames";
                description
                  "Indicates the number of frames transmitted during the test run";
              }
              leaf measured-frame-rx {
                type srl_nokia-comm:zero-based-counter64;
                units "frames";
                description
                  "Indicates the number of frames received during the test run";
              }
            }
          }
        }
      }
    }
  }

  grouping testoam-service-activation-testhead {
    container service-activation-testhead {
      presence "Service activation testhead service testing and reporting";
      description
        "Enter the service-activation-testhead context";
      list acceptance-criteria-template {
        key "ac-template-name";
        max-elements 100;
        description
          "Enter the acceptance-criteria-template list instance";
        leaf ac-template-name {
          type srl_nokia-comm:name {
            length "1..64";
          }
          description
            "Acceptance criteria template name";
        }
        leaf description {
          type srl_nokia-comm:description;
          description
            "Text description";
        }
        leaf cir-threshold {
          type uint32 {
            range "1..400000000";
          }
          units "kilobps";
          description
            "CIR threshold";
        }
        leaf pir-threshold {
          type uint32 {
            range "1..400000000";
          }
          units "kilobps";
          description
            "PIR threshold";
        }
        leaf loss-threshold {
          type srl_nokia-sath-types:sath-loss-percent-decimal64;
          description
            "Loss threshold for acceptance criteria template";
        }
        leaf loss-threshold-policing {
          type srl_nokia-sath-types:sath-loss-percent-decimal64;
          description
            "Frame loss ratio for a policing test";
        }
        leaf delay-threshold {
          type uint32 {
            range "1..100000000";
          }
          units "microseconds";
          description
            "Delay threshold configuration for acceptance criteria template";
        }
        leaf delay-var-threshold {
          type uint32 {
            range "1..100000000";
          }
          units "microseconds";
          description
            "Delay variation threshold configuration for acceptance criteria template";
        }
        leaf m-factor {
          type uint32 {
            range "1..400000000";
          }
          units "kilobps";
          description
            "Throughput margin configuration";
        }
      }
      list frame-size-template {
        key "fs-template-name";
        max-elements 100;
        description
          "Enter the frame-size-template list instance";
        leaf fs-template-name {
          type srl_nokia-comm:name {
            length "1..64";
          }
          description
            "Frame size template name";
        }
        leaf size-a {
          type uint32 {
            range "64..9212";
          }
          units "bytes";
          default "64";
          description
            "Size-a";
        }
        leaf size-b {
          type uint32 {
            range "64..9212";
          }
          units "bytes";
          default "128";
          description
            "Size-b";
        }
        leaf size-c {
          type uint32 {
            range "64..9212";
          }
          units "bytes";
          default "256";
          description
            "Size-c";
        }
        leaf size-d {
          type uint32 {
            range "64..9212";
          }
          units "bytes";
          default "512";
          description
            "Size-d";
        }
        leaf size-e {
          type uint32 {
            range "64..9212";
          }
          units "bytes";
          default "1024";
          description
            "Size-e";
        }
        leaf size-f {
          type uint32 {
            range "64..9212";
          }
          units "bytes";
          default "1280";
          description
            "Size-f";
        }
        leaf size-g {
          type uint32 {
            range "64..9212";
          }
          units "bytes";
          default "1518";
          description
            "Size-g";
        }
        leaf size-h {
          type uint32 {
            range "64..9212";
          }
          units "bytes";
          default "9212";
          description
            "Size-h";
        }
        leaf size-u {
          type uint32 {
            range "64..9212";
          }
          units "bytes";
          default "2000";
          description
            "Size-u";
        }
      }
      list service-test {
        key "test-name";
        max-elements 500;
        description
          "Enter the service-test list instance";
        leaf test-name {
          type srl_nokia-comm:name {
            length "1..64";
          }
          description
            "Service activation test name";
        }
        leaf admin-state {
          type srl_nokia-comm:admin-state;
          default "disable";
          description
            "Administrative state of the service test";
        }
        leaf description {
          type srl_nokia-comm:description;
          description
            "Text description";
        }
        leaf service-test-completion-notification {
          type boolean;
          default "false";
          description
            "Enable SNMP trap generation upon test completion";
        }
        leaf stream-run-type {
          type enumeration {
            enum sequential {
              value 1;
            }
            enum parallel {
              value 2;
            }
          }
          default "parallel";
          description
            "Service stream run order";
        }
        container test-duration {
          description
            "Enter the test-duration context";
          container cir {
            description
              "Enter the cir context";
            leaf minutes-seconds {
              type srl_nokia-sath-types:sath-mm-ss-string;
              default "05:00";
              description
                "Duration of the service test CIR tests";
            }
          }
          container cir-pir {
            description
              "Enter the cir-pir context";
            leaf minutes-seconds {
              type srl_nokia-sath-types:sath-mm-ss-string;
              default "10:00";
              description
                "Duration of the service test CIR-PIR tests";
            }
          }
          container policing {
            description
              "Enter the policing context";
            leaf minutes-seconds {
              type srl_nokia-sath-types:sath-mm-ss-string;
              default "10:00";
              description
                "Duration of policing tests belonging to the test";
            }
          }
          container performance {
            description
              "Enter the performance context";
            leaf hours-minutes-seconds {
              type srl_nokia-sath-types:sath-hh-mm-ss-string;
              default "00:15:00";
              description
                "Duration of performance tests belonging to the test";
            }
          }
        }
        list service-stream {
          key "stream-id";
          description
            "Enter the service-stream list instance";
          leaf stream-id {
            type uint32 {
              range "1..8";
            }
            description
              "Service stream ID";
          }
          leaf admin-state {
            type srl_nokia-comm:admin-state;
            default "disable";
            description
              "Administrative state of the service stream";
          }
          leaf description {
            type srl_nokia-comm:description;
            description
              "Text description";
          }
          leaf acceptance-criteria-template {
            type leafref {
              path "../../../acceptance-criteria-template/ac-template-name";
            }
            description
              "Acceptance criteria association to a service stream";
          }
          leaf rate-cir {
            type uint32 {
              range "0..400000000";
            }
            units "kilobps";
            default "0";
            description
              "CIR packet transmit rate for the service stream";
          }
          leaf rate-pir {
            type uint32 {
              range "0..400000000";
            }
            units "kilobps";
            default "0";
            description
              "PIR packet transmit rate for the service stream";
          }
          leaf service-stream-completion-notification {
            type boolean;
            default "false";
            description
              "Enable SNMP trap generation upon test completion";
          }
          container frame-mix {
            description
              "Enter the frame-mix context";
            leaf frame-size-template {
              type leafref {
                path "../../../../frame-size-template/fs-template-name";
              }
              description
                "Frame size template for the service stream";
            }
            leaf sequence {
              type string {
                length "1..16";
                pattern '[a-hu]';
              }
              default "a";
              description
                "Sequence of frame sizes for the service stream";
            }
          }
          container test-types {
            description
              "Enter the test-types context";
            leaf cir {
              type boolean;
              default "false";
              description
                "CIR test for the service stream";
            }
            leaf cir-pir {
              type boolean;
              default "false";
              description
                "CIR-PIR test for the service stream";
            }
            leaf policing {
              type boolean;
              default "false";
              description
                "Policing test for the service stream";
            }
            leaf performance {
              type boolean;
              default "false";
              description
                "Performance test for the service stream";
            }
          }
          container frame-payload {
            description
              "Enter the frame-payload context";
            container data-pattern {
              description
                "Enter the data-pattern context";
              leaf repeat {
                type union {
                  type srl_nokia-comm:hex-string;
                  type uint16;
                }
                description
                  "Repeated 4-byte pattern to pad each packet sent";
              }
            }
            container ethernet {
              description
                "Enter the ethernet context";
              leaf dst-mac {
                type srl_nokia-comm:unicast-mac-address;
                description
                  "Destination MAC address of Ethernet frames";
              }
              container eth-cfm {
                description
                  "Enter the eth-cfm context";
                container source {
                  leaf domain-id {
                    description
                      "The maintenance domain identifier";
                    type leafref {
                      path "/srl_nokia-oam:oam/srl_nokia-ethcfm:ethcfm/srl_nokia-ethcfm:domain/srl_nokia-ethcfm:domain-id";
                    }
                  }
                  leaf association-id {
                    description
                      "The maintenance association identifier specific to the domain identifier";
                    type leafref {
                      path "/srl_nokia-oam:oam/srl_nokia-ethcfm:ethcfm/srl_nokia-ethcfm:domain[srl_nokia-ethcfm:domain-id=current()/../domain-id]/srl_nokia-ethcfm:association/srl_nokia-ethcfm:association-id";
                    }
                  }
                  leaf mep-id {
                    description
                      "The MEP identifier specific to the domain and association identifier";
                    type leafref {
                      path "/srl_nokia-oam:oam/srl_nokia-ethcfm:ethcfm/srl_nokia-ethcfm:domain[srl_nokia-ethcfm:domain-id=current()/../domain-id]/srl_nokia-ethcfm:association[srl_nokia-ethcfm:association-id=current()/../association-id]/srl_nokia-ethcfm:mep/srl_nokia-ethcfm:mep-id";
                    }
                  }
                }
              }
              container s-tag {
                description
                  "Enter the s-tag context";
                leaf dot1p {
                  type uint32 {
                    range "0..7";
                  }
                  default "7";
                  description
                    "PCP of Ethernet frames for service stream";
                }
                leaf discard-eligible {
                  type boolean;
                  default "false";
                  description
                    "Enable marking of the DEI bit in the VLAN header";
                }
              }
              container c-tag {
                description
                  "Enter the c-tag context";
                leaf dot1p {
                  type uint32 {
                    range "0..7";
                  }
                  default "7";
                  description
                    "PCP of Ethernet frames for service stream";
                }
                leaf discard-eligible {
                  type boolean;
                  default "false";
                  description
                    "Enable marking of the DEI bit in the VLAN header";
                }
              }
            }
          }
        }
      }
      uses state-testoam-service-activation-testhead;
    }
  }

  augment "/srl_nokia-oam:oam" {
    if-feature "srl_nokia-feat:sath";
    uses testoam-service-activation-testhead;
  }
}
