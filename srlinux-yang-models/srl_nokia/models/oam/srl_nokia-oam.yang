module srl_nokia-oam {
  yang-version 1.1;
  namespace "urn:nokia.com:srlinux:oam:oam";
  prefix srl_nokia-oam;

  import srl_nokia-features {
    prefix srl-feat;
  }

  organization
    "Nokia";
  contact
    "Nokia SR Linux Support
     Web: <http://www.nokia.com>";
  description
    "This module defines configuration and operational state data
     related to OAM (Operations, Administration and Maintenance)
     functionality.";

  revision 2026-07-31 {
    description
      "SRLinux 26.7.1";
  }
  revision 2024-03-31 {
    description
      "SRLinux 24.3.1";
  }
  revision 2023-07-31 {
    description
      "SRLinux 23.7.1";
  }
  revision 2021-11-30 {
    description
      "SRLinux 21.11.1";
  }

  container oam {
    if-feature "srl-feat:oam";
    description
      "Enter the oam context

       Enclosing container for OAM";
    container performance-monitoring {
      presence "OAM Performance monitoring";
      if-feature "srl-feat:oam-pm";
      description
        "OAM Performance Monitoring";
    }
  }
}
