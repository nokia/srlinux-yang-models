module srl_nokia-service-activation-testhead-types {
  yang-version 1.1;
  namespace "urn:nokia.com:srlinux:sath:service-activation-testhead-types";
  prefix srl_nokia-service-activation-testhead-types;

  organization
    "Nokia";
  contact
    "Nokia SR Linux Support
     Web: <http://www.nokia.com>";
  description
    "This module contains configuration and state data definitions for service activation testead (SAT)";

  revision 2024-10-31 {
    description
      "SRLinux 24.10.1";
  }

  typedef sath-mm-ss-string {
    type string {
      length "5";
      pattern '[0-5][0-9]:[0-5][0-9]';
    }
    description
      "String used to represent minutes and seconds in format 'mm:ss'.
          minutes range: 00..59
          seconds range: 00..59";
  }

  typedef sath-hh-mm-ss-string {
    type string {
      length "8";
      pattern '([2][0-4]|[0-1][0-9]):[0-5][0-9]:[0-5][0-9]';
    }
    description
      "String used to represent hours, minutes, and seconds in format 'hh:mm:ss'.
          hours range:   00..24
          minutes range: 00..59
          seconds range: 00..59";
  }

  typedef sath-statistics-test-run-oper-state {
    type enumeration {
      enum none {
        value 1;
      }
      enum running {
        value 2;
      }
      enum stopped-by-user {
        value 3;
      }
      enum passed {
        value 4;
      }
      enum failed {
        value 5;
      }
      enum stopped-by-fault {
        value 6;
      }
    }
    description
      "In the context of Service Activation TestHead (SATH):

       Indicates the operational state of a run for a service test, service stream, or test.

       stopped-by-fault indicates the service-test was stopped because
       a fatal error occurred.
       For example:
       1.  A CPM activity switch occurred after the test started.
       2.  The IOM hosting one of the service-test's service streams
           was extracted.";
  }

  typedef sath-statistics-test-oper-state {
    type enumeration {
      enum unknown {
        value 1;
      }
      enum pass {
        value 2;
      }
      enum fail {
        value 3;
      }
    }
    description
      "In the context of Service Activation TestHead (SATH):

       Indicates the operational state of a test with respect to a particular acceptance
       criteria.";
  }

  typedef sath-loss-percent-decimal64 {
    type decimal64 {
      range "0.0000..100.0000";
      fraction-digits 4;
    }
    units "percent";
    description
      "A percentage that has four decimal places of specificity.

       Assumes -1 is used to indicate uninitialized percentage.";
  }

  typedef sath-positive-percent-four-decimal-places {
    type decimal64 {
      range "0.0000..100.0000";
      fraction-digits 4;
    }
    units "percent";
    default "0.0000";
    description
      "A percentage that has four decimal places of precision.";
  }

  typedef sath-loss-percent-union {
    type union {
      type sath-positive-percent-four-decimal-places;
      type enumeration {
        enum none {
          value -1;
        }
      }
    }
    description
      "A union of a decimal64 percentage that has four decimal places of specificity and an
       enumeration, 'none'.

       Assumes -1 is used to indicate no percentage and will be mapped to the enumeration.";
  }
}
