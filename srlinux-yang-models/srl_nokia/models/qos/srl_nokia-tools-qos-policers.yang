module srl_nokia-tools-qos-policers {
  yang-version 1.1;
  namespace "urn:nokia.com:srlinux:qos:tools-qos-policers";
  prefix srl_nokia-tools-qos-policers;

  import srl_nokia-tools-qos {
    prefix srl_nokia-tools-qos;
  }
  import srl_nokia-features {
    prefix srl-feat;
  }

  organization
    "Nokia";
  contact
    "Nokia SR Linux Support
     Web: <http://www.nokia.com>";

  revision 2026-07-31 {
    description
      "SRLinux 26.7.1";
  }
  revision 2024-07-31 {
    description
      "SRLinux 24.7.1";
  }
  revision 2024-03-31 {
    description
      "SRLinux 24.3.1";
  }
  revision 2023-10-31 {
    description
      "SRLinux 23.10.1";
  }
  revision 2023-07-31 {
    description
      "SRLinux 23.7.1";
  }
  revision 2023-03-31 {
    description
      "SRLinux 23.3.1";
  }
  revision 2022-06-30 {
    description
      "SRLinux 22.6.1";
  }

  grouping tools-policer-policies-top {
    container policer-policies {
      leaf clear {
        type empty;
      }
      list policer {
        description
          "The list of policer instances belonging to the policer-policy definition";
        key "policer-id";
        leaf policer-id {
          type uint8 {
            range "0..31";
          }
        }
        leaf clear {
          type empty;
        }
      }
      description
        "Enter the policer-policies context";
    }
  }

  augment "/srl_nokia-tools-qos:qos/srl_nokia-tools-qos:interfaces/srl_nokia-tools-qos:interface/srl_nokia-tools-qos:input" {
    uses tools-policer-policies-top {
      if-feature "srl-feat:qos-policer-policies";
    }
  }
}
