module srl_nokia-qos {
  yang-version 1.1;
  namespace "urn:nokia.com:srlinux:qos:qos";
  prefix srl_nokia-qos;

  import srl_nokia-common {
    prefix srl_nokia-comm;
  }
  import srl_nokia-extensions {
    prefix srl_nokia-ext;
  }
  import srl_nokia-interfaces {
    prefix srl_nokia-if;
  }
  import srl_nokia-system {
    prefix srl_nokia-system;
  }
  import srl_nokia-interfaces-vlans {
    prefix srl_nokia-if-vlans;
  }
  import srl_nokia-features {
    prefix srl-feat;
  }
  import srl_nokia-qos-policers {
    prefix srl_nokia-qos-policers;
  }
  import srl_nokia-platform {
    prefix srl_nokia-platform;
  }
  import srl_nokia-platform-qos {
    prefix srl_nokia-platform-qos;
  }

  organization
    "Nokia";
  contact
    "Nokia SR Linux Support
     Web: <http://www.nokia.com>";

  revision 2026-07-31 {
    description
      "SRLinux 26.7.1";
  }
  revision 2026-03-31 {
    description
      "SRLinux 26.3.1";
  }
  revision 2025-10-31 {
    description
      "SRLinux 25.10.1";
  }
  revision 2025-07-31 {
    description
      "SRLinux 25.7.1";
  }
  revision 2025-03-31 {
    description
      "SRLinux 25.3.1";
  }
  revision 2024-10-31 {
    description
      "SRLinux 24.10.1";
  }
  revision 2024-07-31 {
    description
      "SRLinux 24.7.1";
  }
  revision 2024-03-31 {
    description
      "SRLinux 24.3.1";
  }
  revision 2023-10-31 {
    description
      "SRLinux 23.10.1";
  }
  revision 2023-07-31 {
    description
      "SRLinux 23.7.1";
  }
  revision 2023-03-31 {
    description
      "SRLinux 23.3.1";
  }
  revision 2022-11-30 {
    description
      "SRLinux 22.11.1";
  }
  revision 2022-06-30 {
    description
      "SRLinux 22.6.1";
  }
  revision 2022-03-31 {
    description
      "SRLinux 22.3.1";
  }
  revision 2021-11-30 {
    description
      "SRLinux 21.11.1";
  }
  revision 2021-06-30 {
    description
      "SRLinux 21.6.1";
  }
  revision 2021-03-31 {
    description
      "SRLinux 21.3.1";
  }
  revision 2020-06-30 {
    description
      "SRLinux 20.6.1";
  }
  revision 2019-11-30 {
    description
      "SRLinux 19.11.1";
  }

  typedef traffic-class {
    type uint8 {
      range "0..7";
    }
  }

  typedef dot1p-value {
    type uint8 {
      range "0..7";
    }
  }

  typedef wred-drop-probability {
    description
      "The various drop probability classifications that can apply to an Wred slope";
    type enumeration {
      enum low {
        value 1;
        description
          "Traffic that should be dropped last when there is congestion. Internally this is traffic that is colored green";
      }
      enum medium {
        value 2;
        description
          "Traffic that should be dropped before green traffic but after red traffic when there is congestion. Internally this is traffic that is colored yellow";
      }
      enum high {
        value 3;
        description
          "Traffic that should be dropped first when there is congestion. Internally this is traffic that is colored red";
      }
      enum all {
        value 4;
        description
          "All traffic, consisting of traffic marked low, medium and high drop-probability";
      }
    }
  }

  typedef wred-traffic-type {
    type enumeration {
      enum tcp {
        value 1;
        if-feature "srl-feat:qos-wred-traffic-type-tcp";
        description
          "Refers to IPv4/IPv6 packets with a protocol/next-header indicating a value of 6";
      }
      enum non-tcp {
        value 2;
        if-feature "srl-feat:qos-wred-traffic-type-tcp";
        description
          "Refers to all packets that are not IPv4/IPv6 packets with a protocol/next-header indicating a value of 6";
      }
      enum all {
        value 3;
        description
          "Refers to all traffic, whether it is TCP or non-TCP";
      }
    }
  }

  typedef wred-profile {
    type enumeration {
      enum in {
        value 1;
        description
          "The key for wred-slope corresponding to packets with profile 'in'";
      }
      enum out {
        value 2;
        description
          "The key for wred-slope corresponding to packets with profile 'out'";
      }
      enum exceed {
        value 3;
        description
          "The key for wred-slope corresponding to packets with profile 'exceed'";
      }
    }
  }

  grouping qos-top {
    description
      "Top-level grouping for QoS model";
    container qos {
      srl_nokia-ext:first-released "19.11.1";
      if-feature "srl-feat:qos";
      description
        "Enter the qos context

         Top-level container for QoS data";
      uses ecn-top;
      uses queue-names-config;
      uses forwarding-classes-config;
      uses fpcx-global-tables {
        if-feature "srl-feat:fpcx";
      }
      uses input-class-map-config {
        if-feature "srl-feat:qos-input-class-map";
      }
      uses output-class-map-config {
        if-feature "srl-feat:qos-output-class-map";
      }
      uses packet-trimming-top {
        if-feature "srl-feat:qos-packet-trimming";
      }
      uses pfc-profile-config {
        if-feature "srl-feat:qos-pfc";
      }
      uses srl_nokia-qos-policers:policer-policies-top;
      uses qos-classifier-top;
      uses qos-rewrite-top;
      uses scheduler-policies-top;
      uses preserve-dscp-top {
        if-feature "srl-feat:qos-preserve-dscp";
      }
      uses qos-interfaces;
      uses qos-buffer-management;
      uses forwarding-complexes {
        if-feature "srl-feat:qos-forwarding-complexes";
      }
    }
  }

  grouping qos-interface-queue-state {
    leaf transmitted-packets {
      config false;
      type srl_nokia-comm:zero-based-counter64;
      description
        "Number of packets transmitted by this queue";
    }
    leaf transmitted-octets {
      config false;
      type srl_nokia-comm:zero-based-counter64;
      description
        "Number of octets trasmitted by this queue";
    }
    leaf dropped-packets {
      config false;
      type srl_nokia-comm:zero-based-counter64;
      description
        "Number of packets dropped by the queue due to overrun";
    }
    leaf dropped-octets {
      config false;
      type srl_nokia-comm:zero-based-counter64;
      description
        "Number of octets dropped by the queue due to overrun";
    }
  }

  grouping qos-interface-queue-root-top {
    container queues {
      description
        "Enter the queues context

         Container for a list of queues that are instantiated on an interface";
      list queue {
        key "queue-name";
        leaf queue-name {
          type leafref {
            path "/srl_nokia-qos:qos/srl_nokia-qos:queues/srl_nokia-qos:queue/srl_nokia-qos:name";
          }
          description
            "The queue name";
          must 'string(../../../../interface-ref/subinterface) = "" or /srl_nokia-platform:platform/srl_nokia-platform-qos:qos/srl_nokia-platform-qos:traffic-management-mode = "two-priorities"' {
            error-message "configuring of a queue only permitted for interfaces";
            srl_nokia-ext:if-feature "srl_nokia-features:qos-subinterface-queuing";
          }
          must 'string(../../../../interface-ref/subinterface) = "" or not(starts-with(../../../../interface-ref/interface, "lag"))' {
            error-message "configuring of a queue not permitted for LAG sub-interfaces";
            srl_nokia-ext:if-feature "srl_nokia-features:qos-subinterface-queuing and not srl_nokia-features:qos-lag-subinterface-queuing";
          }
        }
        description
          "List of queues";
        leaf queue-management-profile {
          if-feature "srl-feat:qos-queue-management-profile";
          type leafref {
            path "../../../../../../buffer-management/queue-management-profile/name";
          }
          description
            "The queue management profile that is to be used for the queue on the interface.

             For example, the system may use a profile which specifies that WRED curves are used for setting an ECN mark in the IP header instead of dropping a packet in order to signal impending congestion and for determining when there is sufficient congestion to tail drop packets";
          must "string(../../../buffer-allocation-profile) != '' and
                /qos/buffer-management/buffer-allocation-profile[name=current()/../../../buffer-allocation-profile]/queues/queue[queue-name=current()/../queue-name]/queue-name = ../queue-name and
                (/qos/buffer-management/buffer-allocation-profile[name=current()/../../../buffer-allocation-profile]/queues/queue[queue-name=current()/../queue-name]/maximum-burst-size != 0 or
                 boolean(/qos/buffer-management/buffer-allocation-profile[name=current()/../../../buffer-allocation-profile]/queues/queue[queue-name=current()/../queue-name]/maximum-burst-size-delay))" {
            error-message "cannot be configured without setting maximum burst size";
          }
        }
        leaf-list forwarding-class {
          config false;
          type string;
          description
            "The list of forwarding classes that map to this queue";
        }
        leaf queue-type {
          if-feature "srl-feat:qos-subinterface-queue-type";
          config false;
          description
            "Indicates whether given queue is local to subinterface or interface-queue";
          type enumeration {
            enum local;
            enum interface-queue;
          }
        }
        container active-queue-management {
          if-feature "srl-feat:qos-queue-management-profile";
          config false;
          list wred-slope {
            description
              "List of WRED slopes";
            key "traffic-type drop-probability enable-ecn";
            leaf traffic-type {
              description
                "The traffic type to which the WRED slope applies";
              type wred-traffic-type;
            }
            leaf drop-probability {
              description
                "The drop probability to which the WRED slope applies";
              type wred-drop-probability;
            }
            leaf drop {
              description
                "Indicates that packets will be dropped based on WRED slope policy";
              type boolean;
            }
            leaf enable-ecn {
              description
                "Indicates that packets should be marked with ecn-bit when the result of wred-slope would discard the packet. It is mutually exclusive with 'drop' flag";
              type boolean;
            }
            leaf min-threshold-bytes {
              type uint32;
              units "bytes";
              description
                "The queue depth in bytes that corresponds to the WRED mininum threshold parameter";
            }
            leaf max-threshold-bytes {
              type uint32;
              units "bytes";
              description
                "The queue depth in bytes that corresponds to the WRED maximum threshold parameter";
            }
            leaf max-probability {
              type srl_nokia-comm:percentage;
              description
                "The maximum probability of dropping a packet (at or above the max-threshold).

                 On 7250 IXR-6/10 there can be a significant difference between the configured value and the operational value";
            }
          }
          description
            "Enter the active-queue-management context";
        }
        container queue-depth {
          config false;
          srl_nokia-ext:first-released "20.12.1";
          leaf maximum-burst-size {
            type uint32;
            units "bytes";
            description
              "Maximum queue depth in bytes";
          }
          leaf committed-burst-size {
            if-feature "srl-feat:qos-queue-committed-burst-size or srl-feat:qos-subinterface-queuing";
            type uint32;
            units "bytes";
            description
              "Committed queue length in bytes";
          }
          leaf last-high-threshold-time {
            if-feature "srl-feat:qos-queue-high-threshold";
            description
              "The last time the queue depth exceeded the high-threshold in a rising direction";
            type srl_nokia-comm:date-and-time-delta;
          }
          leaf high-threshold-bytes {
            if-feature "srl-feat:qos-queue-high-threshold";
            type uint32;
            units "bytes";
            description
              "The operational hardware value of the high threshold in bytes";
          }
          leaf average-1 {
            if-feature "srl-feat:qos-queue-depth-sampling";
            type uint32;
            units "bytes";
            description
              "The average queue depth in the last 1 minutes using samples taken every polling-interval milliseconds";
          }
          leaf average-5 {
            if-feature "srl-feat:qos-queue-depth-sampling";
            type uint32;
            units "bytes";
            description
              "The average queue depth in the last 5 minutes using samples taken every polling-interval milliseconds";
          }
          leaf average-15 {
            if-feature "srl-feat:qos-queue-depth-sampling";
            type uint32;
            units "bytes";
            description
              "The average queue depth in the last 15 minutes using samples taken every polling-interval milliseconds";
          }
          leaf high-watermark-1 {
            if-feature "srl-feat:qos-queue-depth-sampling";
            type uint32;
            units "bytes";
            description
              "The highest queue depth in the last 1 minutes using samples taken every polling-interval milliseconds";
          }
          leaf high-watermark-5 {
            if-feature "srl-feat:qos-queue-depth-sampling";
            type uint32;
            units "bytes";
            description
              "The highest queue depth in the last 5 minutes using samples taken every polling-interval milliseconds";
          }
          leaf high-watermark-15 {
            if-feature "srl-feat:qos-queue-depth-sampling";
            type uint32;
            units "bytes";
            description
              "The highest queue depth in the last 15 minutes using samples taken every polling-interval milliseconds";
          }
          leaf missed-polling-intervals {
            if-feature "srl-feat:qos-queue-depth-sampling";
            type uint32;
            description
              "The number of samples that were expected, but did not arrive fast enough to be included in the average and high-watermark calculations";
          }
          description
            "Enter the queue-depth context";
        }
        container scheduling {
          description
            "Enter the scheduling context

             Container for queue scheduling parameters";
          config false;
          leaf peak-rate-percent {
            srl_nokia-ext:first-released "20.6.1";
            if-feature "srl-feat:qos-scheduler-policies";
            type uint8 {
              range "1..100";
            }
            description
              "The maximum percentage of port bandwidth that is available to the traffic in this queue during the PIR scheduling loop. The default is 100";
          }
          leaf peak-rate-bps {
            srl_nokia-ext:first-released "20.6.1";
            if-feature "srl-feat:qos-scheduler-policies";
            type uint64;
            description
              "The actual/operational peak rate in bits per second";
          }
          leaf committed-rate-percent {
            if-feature "srl-feat:qos-scheduler-policies and srl-feat:qos-subinterface-queuing";
            type uint8 {
              range "0..100";
            }
            description
              "The maximum percentage of port bandwidth that is available to the traffic in this queue during the CIR scheduling loop. The default is 0";
          }
          leaf committed-rate-bps {
            if-feature "srl-feat:qos-scheduler-policies and srl-feat:qos-subinterface-queuing";
            type uint64;
            description
              "The actual/operational committed rate in bits per second";
          }
          leaf strict-priority {
            if-feature "srl-feat:qos-scheduler-policies";
            type boolean;
            description
              "When set to true the queue is serviced as a strict priority queue, regardless of whether a weight is configured or its value. When set to false the queue is serviced using WRR, even if the queue does not have a configured weight; in this case the default weight value of 1 is used";
          }
          leaf priority-level {
            if-feature "srl-feat:qos-scheduler-policies and srl-feat:qos-subinterface-queuing";
            type uint8;
            description
              "The priority level for the queue when scheduled as part of strict scheduler";
          }
          leaf weight {
            type uint8 {
              range "1..255";
            }
            description
              "Configures the relative weight of a queue.

               For DWRR, this is determined by the scheduler policy
               For Strict Priority the weight is as follows

               J2:
               unicast-0..unicast-7 -> weight 9..16
               multicast-0..multicast-7 -> weight 1..8

               TD3 (D2/D3/D5):
               unicast-0..unicast-7 -> weight 1..8
               multicast-0..multicast-7 -> weight 1..8

               TH3:
               unicast-0 -> weight 2
               unicast-1 -> weight 3
               unicast-2 -> weight 5
               unicast-3 -> weight 6
               unicast-4 -> weight 8
               unicast-5 -> weight 9
               unicast-6 -> weight 11
               unicast-7 -> weight 12
               multicast-0 -> weight 1
               multicast-1 -> weight 4
               multicast-2 -> weight 7
               multicast-3 -> weight 10
              ";
          }
          leaf scheduling-class {
            if-feature "srl-feat:qos-sched-class-scheduling-policy";
            description
              "The scheduling-class for output-queue";
            type uint8 {
              range "0|2|4|6";
            }
          }
        }
        container queue-statistics {
          config false;
          container aggregate-statistics {
            srl_nokia-ext:delivery-node-override "true";
            description
              "Enter the aggregate-statistics context

               Aggregate queue statistics per interface-queue or subinterface-queue";
            leaf last-clear {
              type srl_nokia-comm:date-and-time-delta;
              description
                "Timestamp of the last time the statistics associated with this queue were cleared";
            }
            uses fpcx-queue-stats {
              if-feature "srl-feat:qos-queue-profile-stats";
            }
            uses single-queue-stats {
              if-feature "not srl-feat:qos-queue-profile-stats";
            }
          }
          container per-lag-member-statistics {
            description
              "Enter the per-lag-member-statistics context

               Queue statistics per-LAG member. These statistics are relevant only for LAG";
            list member-interface {
              key "member-interface-name";
              leaf member-interface-name {
                type srl_nokia-comm:interface-name;
              }
              uses fpcx-queue-stats {
                if-feature "srl-feat:qos-queue-profile-stats";
              }
              uses single-queue-stats {
                if-feature "not srl-feat:qos-queue-profile-stats";
              }
            }
          }
          description
            "Enter the queue-statistics context";
        }
      }
    }
  }

  grouping qos-virtual-interface-sched-class-scheduling-policy-pending-top {
    leaf-list sched-class-scheduling-policy-pending {
      config false;
      description
        "List of interfaces, related to this virtual-interface, where the configured sched-class-scheduling-policy is not yet operational";
      type leafref {
        path "/srl_nokia-if:interface/srl_nokia-if:name";
      }
    }
  }

  grouping qos-interface-scheduler-top {
    container scheduler {
      srl_nokia-ext:first-released "20.12.1";
      description
        "Enter the scheduler context

         Output traffic scheduler options";
      container scheduling-resources-pools {
        config false;
        if-feature "srl-feat:qos-queue-scheduling-policy";
        description
          "Enter the scheduling-resources-pools context

           Lists the scheduling resources pools that the given interface is using";
        leaf resource-set-pool {
          type uint8 {
            range "0..1";
          }
          description
            "Resource-set-pool from which the interface obtains scheduling resources";
        }
        leaf interface-group-resource-pool {
          type uint8 {
            range "0..15";
          }
          description
            "Interface-group-resource-pool from which the interface obtains scheduling resources";
        }
      }
      leaf queue-scheduling-policy {
        if-feature "srl-feat:qos-queue-scheduling-policy";
        description
          "Queue level scheduling policy";
        type leafref {
          path "/srl_nokia-qos:qos/srl_nokia-qos:scheduler-policies/srl_nokia-qos:queue-scheduling-policy/srl_nokia-qos:name";
        }
      }
      list queue-scheduler {
        if-feature "srl-feat:qos-queue-scheduling-policy";
        description
          "List of queue-schedulers created at the interface";
        config false;
        key "sequence-id";
        leaf sequence-id {
          description
            "Sequence-id of the scheduler as configured in the respective queue-scheduling-policy";
          type uint8;
        }
        leaf-list queue-inputs {
          description
            "List of queues feeding the tier-0 queue-scheduler";
          type string;
        }
        leaf-list scheduler-inputs {
          description
            "List of tier-0 queue-schedulers feeding the tier-1 queue-scheduler";
          type uint32;
        }
        list interface-instance {
          description
            "List of interface instances";
          key "interface-name";
          leaf interface-name {
            type srl_nokia-comm:interface-name;
          }
          leaf peak-rate-kbps {
            type uint64;
          }
        }
      }
      leaf sched-class-scheduling-policy {
        if-feature "srl-feat:qos-sched-class-scheduling-policy";
        description
          "Interface level scheduling policy";
        type leafref {
          path "/srl_nokia-qos:qos/srl_nokia-qos:scheduler-policies/srl_nokia-qos:sched-class-scheduling-policy/srl_nokia-qos:name";
        }
        must 'string(../../../interface-ref/subinterface) = ""' {
          error-message "Attachment of a sched-class-scheduling-policy not permitted for sub-interfaces";
        }
      }
      list sched-class-scheduler {
        if-feature "srl-feat:qos-sched-class-scheduling-policy";
        description
          "List of scheduling-class-schedulers created at the interface";
        config false;
        key "sequence-id";
        leaf sequence-id {
          description
            "Sequence-id of the scheduler as configured in the respective sched-class-scheduling-policy";
          type uint8;
        }
        leaf-list sched-class-inputs {
          description
            "List of scheduling-classes feeding the tier-0 sched-class-scheduler";
          type uint8;
        }
        leaf-list scheduler-inputs {
          description
            "List of tier-0 sched-class-schedulers feeding the tier-1 sched-class-scheduler";
          type uint32;
        }
        list interface-instance {
          description
            "List of interface instances";
          key "interface-name";
          leaf interface-name {
            type srl_nokia-comm:interface-name;
          }
          leaf peak-rate-kbps {
            type uint64;
          }
        }
      }
      list virtual-interface {
        if-feature "srl-feat:qos-virtual-interface";
        description
          "Virtual interface for the purpose of SVLAN level scheduling";
        key "name";
        max-elements 128;
        leaf name {
          description
            "Virtual interface name";
          type srl_nokia-comm:name;
        }
        must 'string(../../../interface-ref/interface) != ""' {
          error-message "interface must have an interface reference before virtual-interfaces can be created";
        }
        must 'string(../../../interface-ref/subinterface) = ""' {
          error-message "Virtual-interfaces are only permitted under interfaces";
        }
        leaf sched-class-scheduling-policy {
          if-feature "srl-feat:qos-sched-class-scheduling-policy";
          mandatory true;
          description
            "Interface level scheduling policy";
          type leafref {
            path "/srl_nokia-qos:qos/srl_nokia-qos:scheduler-policies/srl_nokia-qos:sched-class-scheduling-policy/srl_nokia-qos:name";
          }
        }
        container inputs {
          description
            "Enter the inputs context

             List of subinterface inputs";
          list interface {
            key "interface-id";
            leaf interface-id {
              type leafref {
                path "/srl_nokia-qos:qos/srl_nokia-qos:interfaces/srl_nokia-qos:interface/srl_nokia-qos:interface-id";
              }
              must '/srl_nokia-qos:qos/interfaces/interface[interface-id=current()]/interface-ref/interface = ../../../../../../interface-ref/interface' {
                error-message "Subinterface must have the same interface-ref interface as parent interface";
              }
            }
          }
        }
        uses qos-virtual-interface-sched-class-scheduling-policy-pending-top {
          if-feature "srl-feat:qos-virtual-interface";
        }
      }
      leaf scheduler-policy {
        if-feature "srl-feat:qos-scheduler-policies";
        description
          "The scheduler policy to be applied to traffic on this interface";
        type leafref {
          path "/srl_nokia-qos:qos/srl_nokia-qos:scheduler-policies/srl_nokia-qos:scheduler-policy/srl_nokia-qos:name";
        }
        must 'string(../../../interface-ref/subinterface) = "" or /srl_nokia-platform:platform/srl_nokia-platform-qos:qos/srl_nokia-platform-qos:traffic-management-mode = "two-priorities"' {
          error-message "Attachment of a scheduler not permitted for sub-interface when traffic-management is set to eight-priorities";
          srl_nokia-ext:if-feature "srl_nokia-features:qos-subinterface-queuing";
        }
        must 'string(../../../interface-ref/subinterface) != "" or not(boolean(/srl_nokia-qos:qos/srl_nokia-qos:scheduler-policies/srl_nokia-qos:scheduler-policy[srl_nokia-qos:name=current()]/srl_nokia-qos:scheduler[srl_nokia-qos:sequence=1]/srl_nokia-qos:output/srl_nokia-qos:peak-rate-percent))' {
          error-message "Scheduler policy with output peak-rate-percent configured can only be attached to sub-interfaces";
          srl_nokia-ext:if-feature "srl_nokia-features:qos-subinterface-queuing";
        }
        must 'string(../../../interface-ref/subinterface) = "" or not(starts-with(../../../interface-ref/interface, "lag"))' {
          error-message "Attachment of scheduler-policy not permitted for LAG sub-interfaces";
          srl_nokia-ext:if-feature "srl_nokia-features:qos-subinterface-queuing and not srl_nokia-features:qos-lag-subinterface-queuing";
        }
      }
    }
  }

  grouping fpcx-subinterface-qos-input {
    leaf input-class-map {
      if-feature "srl-feat:qos-input-class-map";
      type leafref {
        path "/srl_nokia-qos:qos/srl_nokia-qos:input-class-map/srl_nokia-qos:name";
      }
      description
        "Reference to the name of input-class-map that applies to subinterface";
      must 'string(../../interface-ref/subinterface) != ""' {
        error-message "Attachment of input-class-map, not permitted for interfaces";
      }
    }
    container policer-policies {
      if-feature "srl-feat:qos-policer-policies";
      leaf policer-policy {
        type leafref {
          path "/srl_nokia-qos:qos/srl_nokia-qos:policer-policies/srl_nokia-qos:policer-policy/srl_nokia-qos:name";
        }
        description
          "Policer-policy assigned to this subinterface";
        must 'string(../../../interface-ref/subinterface) != ""' {
          error-message "Attachment of policer-polices, not permitted for interfaces";
        }
      }
      container parent-policer {
        config false;
        description
          "Enter the parent-policer context

           Parent-policer operational parameters";
        leaf rate-kbps {
          description
            "Operational rate of the parent policer";
          type uint32;
        }
        leaf burst-allowance {
          description
            "Operational value of the burst-allowance for the parent-policer";
          type uint32;
        }
        leaf threshold-separation {
          description
            "Operational value of the threshold-separation for the parent-policer";
          type uint32;
        }
      }
      list policer {
        config false;
        key "policer-id";
        leaf policer-id {
          type leafref {
            path "/srl_nokia-qos:qos/srl_nokia-qos:policer-policies/srl_nokia-qos:policer-policy/srl_nokia-qos:policer/srl_nokia-qos:policer-id";
          }
        }
        uses srl_nokia-qos-policers:policer-instance-state;
      }
      description
        "Enter the policer-policies context";
    }
  }

  grouping qos-subinterface-classifier-top {
    container default {
      must 'string(../../../interface-ref/subinterface) != ""' {
        error-message "Attachment of subinterface input defaults, not permitted for interfaces";
      }
      presence "subinterface-classifier-default";
      leaf forwarding-class {
        type leafref {
          path "/srl_nokia-qos:qos/srl_nokia-qos:forwarding-classes/srl_nokia-qos:forwarding-class/srl_nokia-qos:name";
        }
        description
          "The forwarding class";
      }
      must "/srl_nokia-if:interface[srl_nokia-if:name=current()/../../../interface-ref/interface]/srl_nokia-if:subinterface[srl_nokia-if:index=current()/../../../interface-ref/subinterface]/srl_nokia-if:type = 'srl_nokia-if:bridged' or not (./forwarding-class)" {
        error-message "default-forwarding-class allowed with type bridged only";
        srl_nokia-ext:if-feature "not srl_nokia-features:fpcx";
      }
      leaf drop-probability {
        if-feature "srl-feat:qos-drop-probability";
        description
          "The default drop-probability for packets arriving on this subinterface that do not match any classification rule";
        type srl_nokia-comm:drop-probability;
        must "/srl_nokia-if:interface[srl_nokia-if:name=current()/../../../../interface-ref/interface]/srl_nokia-if:subinterface[srl_nokia-if:index=current()/../../../../interface-ref/subinterface]/srl_nokia-if:type = 'srl_nokia-if:bridged' " {
          error-message "default-drop-probability allowed with type bridged only";
        }
      }
      leaf profile {
        if-feature "srl-feat:qos-classify-profile";
        description
          "The default profile for packets arriving on this subinterface that do not match any classification rule";
        type srl_nokia-comm:classify-profile;
        default "out";
      }
    }
    leaf ipv4-dscp-policy {
      if-feature "srl-feat:qos-ipv4-dscp-classifier-policy";
      type leafref {
        path "/srl_nokia-qos:qos/srl_nokia-qos:classifiers/srl_nokia-qos:dscp-policy/srl_nokia-qos:name";
      }
      description
        "Reference to the name of a DSCP mapping policy that applies only to IPv4 traffic";
      must 'boolean(/srl_nokia-qos:qos/srl_nokia-qos:preserve-dscp) = false()' {
        error-message "Non-default DSCP classifier not supported with preserve-dscp option";
      }
    }
    leaf ipv6-dscp-policy {
      if-feature "srl-feat:qos-ipv6-dscp-classifier-policy";
      type leafref {
        path "/srl_nokia-qos:qos/srl_nokia-qos:classifiers/srl_nokia-qos:dscp-policy/srl_nokia-qos:name";
      }
      description
        "Reference to the name of a DSCP mapping policy that applies only to IPv6 traffic";
      must 'boolean(/srl_nokia-qos:qos/srl_nokia-qos:preserve-dscp) = false()' {
        error-message "Non-default DSCP classifier not supported with preserve-dscp option";
      }
    }
    leaf dscp-policy {
      srl_nokia-ext:first-released "20.6.1";
      if-feature "srl-feat:qos-dscp-classifier-policy";
      type leafref {
        path "/srl_nokia-qos:qos/srl_nokia-qos:classifiers/srl_nokia-qos:dscp-policy/srl_nokia-qos:name";
      }
      description
        "Reference to the name of a DSCP mapping policy that applies to both IPv4 and IPv6 traffic";
    }
    leaf dot1p-policy {
      srl_nokia-ext:first-released "22.6.1";
      if-feature "srl-feat:qos-dot1p-classifier-policy";
      type leafref {
        path "/srl_nokia-qos:qos/srl_nokia-qos:classifiers/srl_nokia-qos:dot1p-policy/srl_nokia-qos:name";
      }
      description
        "Reference to the name of a dot1p mapping policy";
      must "/srl_nokia-if:interface[srl_nokia-if:name=current()/../../../interface-ref/interface]/srl_nokia-if:subinterface[srl_nokia-if:index=current()/../../../interface-ref/subinterface]/srl_nokia-if:type = 'srl_nokia-if:bridged' " {
        error-message "dot1p classifiers allowed with type bridged only";
        srl_nokia-ext:if-feature "not srl_nokia-features:fpcx";
      }
    }
    leaf mpls-traffic-class-policy {
      if-feature "srl-feat:qos-mpls-classifier-policy";
      type leafref {
        path "/srl_nokia-qos:qos/srl_nokia-qos:classifiers/srl_nokia-qos:mpls-traffic-class-policy/name";
      }
      description
        "Reference to the name of an MPLS traffic-class mapping policy";
    }
    leaf ler-use-dscp {
      if-feature "srl-feat:qos-ler-use-dscp";
      description
        "Enables short-pipe model for all lsp-bindings terminated on the subinterface";
      type boolean;
      default "false";
    }
    leaf match-qinq-dot1p {
      if-feature "srl-feat:qos-match-qinq-dot1p";
      description
        "Defines which dot1p bits will be used for dot1p-classification in case of QinQ encapsulation";
      type enumeration {
        enum inner {
          value 1;
        }
        enum outer {
          value 2;
        }
      }
      default "outer";
    }
    leaf tos-rewrite-state {
      if-feature "srl-feat:qos-tos-rewrite";
      description
        "Defines whether given subinterface is considered as trusted/untrusted for ToS rewrite purpose";
      type enumeration {
        enum trusted {
          value 1;
        }
        enum untrusted {
          value 2;
        }
      }
      default "trusted";
    }
  }

  grouping qos-subinterface-input-top {
    container classifiers {
      presence "classifier policies";
      description
        "Classifiers to be applied to the subinterface";
      uses qos-subinterface-classifier-top;
      must 'string(../../interface-ref/subinterface) != ""' {
        error-message "Attachment of classifiers, not permitted for interfaces";
      }
    }
    uses fpcx-subinterface-qos-input;
  }

  grouping qos-subinterface-output-top {
    leaf dscp-reclassify-policy {
      if-feature "srl-feat:qos-dscp-reclassifier-policy";
      type leafref {
        path "/srl_nokia-qos:qos/srl_nokia-qos:classifiers/srl_nokia-qos:dscp-reclassify-policy/srl_nokia-qos:name";
      }
      description
        "Reference to egress dscp-reclassification policy";
      must 'string(../../interface-ref/subinterface) != ""' {
        error-message "Attachment of dscp-reclassification, only permitted for subinterfaces";
      }
    }
    leaf output-class-map {
      if-feature "srl-feat:qos-output-class-map";
      type leafref {
        path "/srl_nokia-qos:qos/srl_nokia-qos:output-class-map/srl_nokia-qos:name";
      }
      description
        "Reference to the name of output-class-map that applies to subinterface";
      must 'string(../../interface-ref/subinterface) != ""' {
        error-message "Attachment of output-class-map, only permitted for subinterfaces";
      }
    }
    container rewrite-rules {
      presence "rewrite-rules";
      must 'string(../../interface-ref/subinterface) != ""' {
        error-message "Attachment of rewrite-rules only permitted for subinterfaces";
      }
      leaf ipv4-dscp-policy {
        if-feature "srl-feat:qos-ipv4-dscp-rewrite-policy";
        type leafref {
          path "/srl_nokia-qos:qos/srl_nokia-qos:rewrite-rules/srl_nokia-qos:dscp-policy/srl_nokia-qos:name";
        }
        description
          "Reference to the name of a DSCP rewrite-rule policy that applies only to IPv4 traffic";
        must 'boolean(/srl_nokia-qos:qos/srl_nokia-qos:preserve-dscp) = false()' {
          error-message "DSCP rewrite not supported with preserve-dscp option";
        }
        must "/srl_nokia-if:interface[srl_nokia-if:name=current()/../../../interface-ref/interface]/srl_nokia-if:subinterface[srl_nokia-if:index=current()/../../../interface-ref/subinterface]/srl_nokia-if:type != 'srl_nokia-if:bridged' " {
          error-message "rewrite-rules not allowed with type bridged";
        }
      }
      leaf ipv6-dscp-policy {
        if-feature "srl-feat:qos-ipv6-dscp-rewrite-policy";
        type leafref {
          path "/srl_nokia-qos:qos/srl_nokia-qos:rewrite-rules/srl_nokia-qos:dscp-policy/srl_nokia-qos:name";
        }
        description
          "Reference to the name of a DSCP rewrite-rule policy that applies only to IPv6 traffic";
        must 'boolean(/srl_nokia-qos:qos/srl_nokia-qos:preserve-dscp) = false()' {
          error-message "DSCP rewrite not supported with preserve-dscp option";
        }
        must "/srl_nokia-if:interface[srl_nokia-if:name=current()/../../../interface-ref/interface]/srl_nokia-if:subinterface[srl_nokia-if:index=current()/../../../interface-ref/subinterface]/srl_nokia-if:type != 'srl_nokia-if:bridged' " {
          error-message "rewrite-rules not allowed with type bridged";
        }
      }
      leaf dscp-policy {
        srl_nokia-ext:first-released "20.6.1";
        if-feature "srl-feat:qos-dscp-rewrite-policy";
        type leafref {
          path "/srl_nokia-qos:qos/srl_nokia-qos:rewrite-rules/srl_nokia-qos:dscp-policy/srl_nokia-qos:name";
        }
        description
          "Reference to the name of a DSCP rewrite-rule policy that applies to both IPv4 and IPv6 traffic";
        must "/srl_nokia-if:interface[srl_nokia-if:name=current()/../../../interface-ref/interface]/srl_nokia-if:subinterface[srl_nokia-if:index=current()/../../../interface-ref/subinterface]/srl_nokia-if:type != 'srl_nokia-if:bridged' " {
          error-message "rewrite-rules not allowed with type bridged";
          srl_nokia-ext:if-feature "not srl_nokia-features:fpcx";
        }
      }
      leaf dot1p-policy {
        srl_nokia-ext:first-released "22.6.1";
        if-feature "srl-feat:qos-dot1p-rewrite-policy";
        type leafref {
          path "/srl_nokia-qos:qos/srl_nokia-qos:rewrite-rules/srl_nokia-qos:dot1p-policy/srl_nokia-qos:name";
        }
        description
          "Reference to the name of a dot1p rewrite policy";
        must "not(starts-with(../../../interface-ref/interface,'lo'))" {
          error-message "rewrite-rules not allowed on loopback subinterface";
        }
        must "/srl_nokia-if:interface[srl_nokia-if:name=current()/../../../interface-ref/interface]/srl_nokia-if:subinterface[srl_nokia-if:index=current()/../../../interface-ref/subinterface]/srl_nokia-if:type = 'srl_nokia-if:bridged' " {
          error-message "dot1p rewrite-rules allowed with type bridged only";
          srl_nokia-ext:if-feature "srl_nokia-features:trident4";
        }
      }
      leaf mpls-traffic-class-policy {
        if-feature "srl-feat:qos-mpls-rewrite-policy";
        type leafref {
          path "/srl_nokia-qos:qos/srl_nokia-qos:rewrite-rules/srl_nokia-qos:mpls-traffic-class-policy/name";
        }
        description
          "Reference to the name of an MPLS traffic-class rewrite-rule policy";
      }
      container dscp-rewrite {
        if-feature "srl-feat:qos-subinterface-dscp-rewrite";
        presence "dscp-rewrite";
        leaf force-rewrite-trusted {
          type boolean;
          default "false";
          description
            "Enables remarking packets incomming on trusted interfaces";
        }
      }
      leaf qinq-rewrite-outer-only {
        if-feature "srl-feat:qos-subinterface-dot1p-rewrite";
        type boolean;
        default "true";
        description
          "Enables remarking only outer-dot1p bits";
      }
    }
  }

  grouping qos-subinterface-output-class-map-pending-top {
    leaf-list output-class-map-pending {
      config false;
      description
        "List of interfaces, related to this subinterface, where the configured output-class-map is not yet operational";
      type leafref {
        path "/srl_nokia-if:interface/srl_nokia-if:name";
      }
    }
  }

  grouping qos-subinterface-output-pending-top {
    leaf-list voq-set-pending {
      if-feature "srl-feat:qos-subinterface-queuing";
      config false;
      description
        "List of member interfaces, related to this subinterface, where the VoQ-set
         (voq-id or voq-connector-id) resource has not yet been allocated";
      type leafref {
        path "/srl_nokia-if:interface/srl_nokia-if:name";
      }
    }
    leaf-list voq-set-statistics-pending {
      if-feature "srl-feat:qos-subinterface-queuing and srl-feat:qos-voq-stats-enable";
      config false;
      description
        "List of member interfaces, related to this subinterface, where the VoQ
         statistics resource (voq-stat-id) has not yet been allocated.
         Only populated when voq-statistics is enabled on the subinterface";
      type leafref {
        path "/srl_nokia-if:interface/srl_nokia-if:name";
      }
    }
    leaf lag-bundle-pending {
      if-feature "srl-feat:qos-lag-subinterface-queuing";
      config false;
      type boolean;
      default "false";
      description
        "True when the LAG bundle-id for this LAG sub-interface has not yet
         been allocated. A LAG bundle-id is a precondition for allocating
         voq-set and voq-connector-set on a LAG sub-interface; while this
         leaf reads true, voq-set-pending will also be empty because the
         downstream voq-set allocation is intentionally not attempted.
         Only meaningful on LAG sub-interfaces with per-subinterface
         queueing QoS configured; reads false on all other sub-interfaces.";
    }
  }

  grouping qos-interface-input-top {
    container input {
      description
        "Enter the input context

         Top-level container for QoS configuration and state relating to ingress traffic on the subinterface";
      uses qos-subinterface-input-top;
      leaf pfc-buffer-allocation-profile {
        if-feature "srl-feat:qos-pfc";
        description
          "Buffer-allocation-profile for pfc queues";
        type leafref {
          path "/srl_nokia-qos:qos/srl_nokia-qos:buffer-management/srl_nokia-qos:buffer-allocation-profile/srl_nokia-qos:name";
        }
        must 'string(../../interface-ref/subinterface) = ""' {
          error-message "Attachment of pfc-buffer-allocation-profile, not permitted for sub-interfaces";
        }
        must 'not(../../output/buffer-allocation-profile) or . != ../../output/buffer-allocation-profile' {
          error-message "cannot use same buffer allocation profile for pfc and output queues";
        }
        must '/srl_nokia-platform:platform/srl_nokia-platform-qos:qos/srl_nokia-platform-qos:traffic-management-mode = "eight-priorities"' {
          error-message "Attachment of pfc-buffer-allocation-profile, not permitted for interface when traffic-management is set to two-priorities";
          srl_nokia-ext:if-feature "srl_nokia-features:qos-subinterface-queuing";
        }
      }
    }
  }

  grouping qos-interface-buffer-allocation {
    leaf buffer-allocation-profile {
      description
        "Buffer-allocation-profile for interface output queues";
      type leafref {
        path "/srl_nokia-qos:qos/srl_nokia-qos:buffer-management/srl_nokia-qos:buffer-allocation-profile/srl_nokia-qos:name";
      }
      must 'string(../../interface-ref/subinterface) = ""' {
        error-message "Attachment of buffer-allocation-profile, not permitted for sub-interfaces";
        srl_nokia-ext:if-feature "not srl_nokia-features:fpcx and not srl_nokia-features:qos-subinterface-queuing";
      }
      must 'string(../../interface-ref/subinterface) = "" or /srl_nokia-platform:platform/srl_nokia-platform-qos:qos/srl_nokia-platform-qos:traffic-management-mode = "two-priorities"' {
        error-message "Attachment of buffer-allocation-profile, not permitted for sub-interface when traffic-management is set to eight-priorities";
        srl_nokia-ext:if-feature "srl_nokia-features:qos-subinterface-queuing";
      }
      must 'string(../../interface-ref/subinterface) = "" or not(starts-with(../../interface-ref/interface, "lag"))' {
        error-message "Attachment of buffer-allocation-profile, not permitted for LAG sub-interfaces";
        srl_nokia-ext:if-feature "srl_nokia-features:qos-subinterface-queuing and not srl_nokia-features:qos-lag-subinterface-queuing";
      }
    }
    list interface-pool {
      if-feature "srl-feat:qos-interface-pool-policy";
      config false;
      description
        "List of interface-pools associated with the base interface";
      key "index";
      leaf index {
        type uint8;
        description
          "Interface-pool index";
      }
      leaf operational-size {
        description
          "Operational size of the interface-pool";
        type uint32;
        units "bytes";
      }
      leaf used {
        description
          "Actual usage of the interface-pool";
        type uint32;
        units "bytes";
      }
    }
  }

  grouping qos-interface-output-voq {
    list voq-interface {
      config false;
      description
        "List of VOQ ingress traffic objects associated with output traffic on the interface";
      key "name";
      leaf name {
        description
          "The name of the VOQ ingress traffic object in the format 'voq-<x>-<y>-<z>' where <x> is the ingress slot identifier, <y> is the ingress forwarding-complex identifier, and <z> is the ingress core identifier";
        type string;
      }
      list queue {
        description
          "List of egress queues associated with the interface";
        key "queue-name";
        leaf queue-name {
          type leafref {
            path "/srl_nokia-qos:qos/srl_nokia-qos:queues/srl_nokia-qos:queue/srl_nokia-qos:name";
          }
          description
            "The queue name";
        }
        container queue-depth {
          description
            "Enter the queue-depth context

             Container with the latest queue-depth information for a specific VOQ";
          list congestion-event {
            max-elements 1;
            description
              "List of the most recent congestion event(s) for this VOQ";
            key "index";
            leaf index {
              description
                "Index representing the order of recorded congestion events for the VOQ

                 Index 0 is the most recent event, index 1 is the next most recent event, etc.";
              type uint16;
            }
            leaf status {
              description
                "Current status of the congestion event";
              type enumeration {
                enum no-information-available {
                  description
                    "Polling could not be started on this VOQ because of resource limitations";
                }
                enum in-progress {
                  description
                    "Polling has started on this VOQ and congestion has not ended yet";
                }
                enum done {
                  description
                    "Polling has ended on this VOQ and congestion has subsided";
                }
              }
            }
            leaf start-time {
              description
                "The time when the depth of the VOQ exceeded high-threshold-bytes in a rising direction";
              type srl_nokia-comm:date-and-time-delta;
            }
            leaf end-time {
              description
                "The time when VOQ congestion ended, determined by low-threshold conditions";
              type srl_nokia-comm:date-and-time-delta;
            }
            leaf high-watermark {
              description
                "The highest queue-depth sample that was taken between the start-time and end-time";
              type uint32;
              units "bytes";
            }
          }
        }
      }
    }
  }

  grouping qos-interface-output-top {
    container output {
      description
        "Enter the output context

         Top-level container for QoS configuration and state relating to egress traffic on the interface or subinterface";
      leaf interface-pool-policy {
        if-feature "srl-feat:qos-interface-pool-policy";
        description
          "Interface-pool-policy assigned to the interface";
        type leafref {
          path "../../../../buffer-management/interface-pool-policy/name";
        }
        must 'string(../../interface-ref/subinterface) = ""' {
          error-message "Attachment of interface-pool-policy, not permitted for sub-interfaces";
        }
      }
      uses qos-interface-queue-root-top;
      uses qos-interface-scheduler-top;
      uses qos-subinterface-output-top;
      uses qos-subinterface-output-class-map-pending-top {
        if-feature "srl-feat:qos-subinterface-members";
      }
      uses qos-subinterface-output-pending-top {
        if-feature "srl-feat:qos-subinterface-queuing";
      }
      uses qos-interface-buffer-allocation;
      uses qos-interface-output-voq {
        if-feature "srl-feat:qos-triggered-queue-depth-sampling";
      }
    }
  }

  grouping qos-interfaces {
    container interfaces {
      description
        "Enter the interfaces context

         Interfaces and subinterfaces with QoS configuration and state";
      list interface {
        key "interface-id";
        unique "interface-ref/interface interface-ref/subinterface";
        max-elements 16383;
        description
          "List of interfaces and subinterfaces referenced by QoS policies";
        leaf interface-id {
          type string;
          description
            "Identifier for the interface or subinterface";
          must 'not (starts-with(., "_"))' {
            error-message "reserved interface-id cannot be configured";
          }
          must "not (/srl_nokia-if:interface[srl_nokia-if:name=current()]/srl_nokia-if:ethernet/srl_nokia-if:aggregate-id) or
                              ../interface-ref/interface" {
            error-message "qos configuration is not supported on LAG member ports";
          }
        }
        container interface-ref {
          description
            "Enter the interface-ref context

             Reference to an interface or subinterface";
          leaf interface {
            type leafref {
              path "/srl_nokia-if:interface/srl_nokia-if:name";
            }
            description
              "Reference to a base interface, for example a port or LAG";
            must "not (string(../subinterface) != '' and starts-with(current(), 'irb'))" {
              error-message "qos configuration is not supported on IRB sub interface";
              srl_nokia-ext:if-feature "not (srl_nokia-features:qos-irb-subinterface)";
            }
            must "starts-with(current(), 'ethernet') or starts-with(current(), 'lag') or string(../subinterface) != ''" {
              error-message "qos  configuration is not supported on this interface type";
            }
            must 'not (/srl_nokia-if:interface[srl_nokia-if:name=current()]/srl_nokia-if:ethernet/srl_nokia-if:aggregate-id)' {
              error-message "qos configuration is not supported on LAG member ports";
            }
            must 'not (/srl_nokia-if:interface[srl_nokia-if:name=current()]/srl_nokia-if:breakout-mode)' {
              error-message "Interfaces with breakout-mode configured are not supported";
            }
          }
          leaf subinterface {
            type leafref {
              path "/srl_nokia-if:interface[srl_nokia-if:name=current()/../interface]/srl_nokia-if:subinterface/srl_nokia-if:index";
            }
            description
              "Reference to a subinterface

               This requires the base interface to be specified using the interface leaf in this container";
            must '../interface' {
              error-message "interface must be configured when subinterface is set";
            }
            must "/srl_nokia-if:interface[srl_nokia-if:name=current()/../interface]/srl_nokia-if:subinterface[srl_nokia-if:index=current()]/srl_nokia-if:type != 'srl_nokia-if:local-mirror-dest'" {
              error-message "qos configuration not supported on mirror subinterface";
              srl_nokia-ext:if-feature "srl_nokia-features:fpcx";
            }
          }
        }
        uses pfc-interface {
          if-feature "srl-feat:qos-pfc";
        }
        uses dcbx {
          if-feature "srl-feat:qos-dcbx";
        }
        leaf voq-statistics {
          if-feature "srl-feat:qos-voq-stats-enable";
          description
            "Enable or disable voq-stats at interface";
          type boolean;
          must ". = false() or string(../interface-ref/subinterface) = '' or string(../output/buffer-allocation-profile) != ''" {
            error-message "voq-statistics can be enabled on subinterface only when output buffer-allocation-profile is configured";
            srl_nokia-ext:if-feature "srl_nokia-features:qos-subinterface-queuing";
          }
        }
        leaf voq-statistics-allocation-status {
          config false;
          if-feature "srl-feat:qos-voq-stats-enable";
          description
            "Enable or disable voq-stats at interface";
          type enumeration {
            enum complete;
            enum partial;
            enum none;
          }
        }
        uses qos-interface-input-top;
        uses qos-interface-output-top;
      }
    }
  }

  grouping forwarding-complexes {
    list linecard {
      description
        "Container for QoS linecard configuration";
      key "slot";
      leaf slot {
        type uint8 {
          range "1..16";
        }
        description
          "Numeric identifier for the linecard";
      }
      list forwarding-complex {
        description
          "List of forwarding complexes on the card";
        key "name";
        leaf name {
          description
            "Forwarding-complex name";
          type enumeration {
            enum 0;
            enum 1 {
              if-feature "srl-feat:forwarding-complex-1";
            }
          }
        }
        container input {
          if-feature "srl-feat:qos-pfc";
          description
            "Enter the input context

             QoS input parmeters ar forwarding-complex level";
          leaf pfc-buffer-reservation {
            if-feature "srl-feat:qos-pfc-headroom-buffer";
            description
              "Percentage of the buffer reserved for accomodating incoming traffic while upstream node reacts to generated PFC-pause frames";
            type srl_nokia-comm:percentage;
            default "1";
          }
          leaf pfc-reserved-buffer-size {
            if-feature "srl-feat:qos-pfc-headroom-buffer";
            type uint32;
            config false;
            units "bytes";
            description
              "Displays the actual size of pfc-reserved buffer in bytes";
          }
        }
        container output {
          description
            "Enter the output context

             QoS ouput parameters at forwarding-complex level";
          leaf fp-pool-policy {
            if-feature "srl-feat:qos-fp-pool-policy";
            description
              "FP-pool-policy assigned to the forwarding-complex";
            type leafref {
              path "../../../../buffer-management/fp-pool-policy/name";
            }
            default "default";
          }
        }
      }
    }
  }

  grouping qos-queue-management-profile-wred-config {
    leaf min-threshold {
      type uint64;
      units "bytes";
      description
        "The mininum threshold parameter for a RED-managed queue. When the average queue length is less than min-threshold, the packets are admitted to the queue (without any ECN marking change)";
    }
    leaf max-threshold {
      type uint64;
      units "bytes";
      description
        "The maximum threshold parameter for a RED-managed queue. When the average queue length exceeds the max-threshold, the packets are dropped (or marked if ECN is enabled).

         When both, 'drop' and 'ecn-enable' flags are set to false, packets will be drop only if the mbs of the queue is reached";
    }
    leaf min-threshold-percent {
      type srl_nokia-comm:percentage;
      description
        "The percentage of the MBS that corresponds to the WRED mininum threshold parameter";
      must 'string(../min-threshold) = "" and string(../max-threshold) = ""' {
        error-message "percentage and absolute values cannot be configured together";
      }
    }
    leaf max-threshold-percent {
      type srl_nokia-comm:percentage;
      must 'string(../min-threshold) = "" and string(../max-threshold) = ""' {
        error-message "percentage and absolute values cannot be configured together";
      }
      description
        "The percentage of the MBS that corresponds to the WRED maximum threshold parameter";
    }
    leaf slope-enabled {
      description
        "Reads true if traffic is dropped by WRED";
      type boolean;
    }
    leaf max-drop-probability-percent {
      type srl_nokia-comm:percentage;
      description
        "The probability with which packets are dropped or marked at max-threshold";
    }
    leaf weight-factor {
      config false;
      type uint32 {
        range "0..15";
      }
      description
        "Actual Weight factor used in the calculation of the current (average weighted) queue depth";
    }
  }

  grouping qos-buffer-management {
    container buffer-management {
      description
        "Enter the buffer-management context

         Container for the list of configured queue management profiles";
      container committed-burst-size-table {
        srl_nokia-ext:delivery-node-override "true";
        if-feature "srl-feat:qos-committed-burst-size-table";
        description
          "Enter the committed-burst-size-table context

           Defines possible committed-burst sizes";
        leaf alt-0 {
          type uint32;
          units "bytes";
          default "0";
          description
            "ALT-0 committed-burst-size";
        }
        leaf alt-1 {
          type uint32;
          units "bytes";
          default "0";
          description
            "ALT-1 committed-burst-size";
        }
        leaf alt-2 {
          type uint32;
          units "bytes";
          default "0";
          description
            "ALT-2 committed-burst-size";
        }
        leaf alt-3 {
          type uint32;
          units "bytes";
          default "0";
          description
            "ALT-3 committed-burst-size";
        }
      }
      container trunk-pool-policy {
        if-feature "srl-feat:qos-trunk-pool-policy";
        description
          "Enter the trunk-pool-policy context

           Defines system-wide trunk-pool-policy applicable to all CoE interfaces";
        list trunk-pool {
          description
            "List of trunk-pools.
             The trunk-pools are directly mapped to mid-pools in 1:1 fashion";
          key "index";
          leaf index {
            type uint8 {
              range "0..7";
            }
          }
          leaf slope-policy {
            if-feature "srl-feat:qos-slope-policy";
            description
              "Slope policy associated with the given trunk-pool";
            type leafref {
              path "../../../slope-policy/name";
            }
            default "default";
          }
        }
      }
      list queue-management-profile {
        if-feature "srl-feat:qos-queue-management-profile";
        key "name";
        description
          "The name of a queue management profile";
        leaf name {
          type srl_nokia-comm:name;
          description
            "Unique string name used for the queue management profile";
          must ". != 'default'" {
            error-message "name 'default' is reserved";
          }
        }
        leaf weight-factor {
          type uint32 {
            range "0..15";
          }
          default "0";
          description
            "Weight factor to use in the calculation of the current (average weighted) queue depth";
        }
        container wred {
          description
            "Enter the wred context

             Configuration and operational state parameters relating to Weighted Random Early Detection (WRED)";
          list wred-slope {
            description
              "List of WRED slopes";
            key "traffic-type drop-probability enable-ecn";
            leaf traffic-type {
              description
                "The traffic type to which the WRED slope applies";
              type wred-traffic-type;
              must ". = 'all' or
                    not (../../wred-slope[drop-probability=current()/../drop-probability][traffic-type='all'][enable-ecn=current()/../enable-ecn])" {
                error-message "traffic-type 'all' cannot be configured with 'tcp' or 'non-tcp'";
              }
            }
            leaf drop-probability {
              description
                "The drop probability to which the WRED slope applies";
              type wred-drop-probability;
              must ". = 'all' or
                    not (../../wred-slope[traffic-type=current()/../traffic-type][drop-probability='all'][enable-ecn=current()/../enable-ecn])" {
                error-message "drop-probability 'all' cannot be configured with 'low' or 'medium' or 'high'";
              }
            }
            leaf enable-ecn {
              type boolean;
              description
                "When this leaf is true and the number of packets in the queue is between the minimum threshold and the maximum threshold, if the ECN field on the packet indicates that the endpoints are ECN capable and the WRED algorithm determines that the packet should have been dropped based on the drop probability, the CE bits for the packet are changed to 1, and the packet is transmitted.
                 When set to false, the such packets will be discarded based on wred-slope";
              must "current() = false() or string(../traffic-type) = 'all' " {
                error-message "traffic-type must be 'all' to enable ecn ";
              }
              must "current() = false() or string(../drop-probability) = 'all' " {
                error-message "drop-probability must be 'all' to enable ecn ";
                srl_nokia-ext:if-feature "srl_nokia-features:ixr-dnx";
              }
            }
            uses qos-queue-management-profile-wred-config;
          }
        }
      }
      list buffer-allocation-profile {
        key "name";
        description
          "The name of a buffer-allocation-profile";
        leaf name {
          type srl_nokia-comm:name;
          description
            "Unique string name used for the buffer-allocation-profile";
          must ". != 'default'" {
            error-message "name 'default' is reserved";
          }
        }
        container queues {
          choice queue-pfc-queue {
            description
              "Buffer allocation parameters for individual queues";
            list queue {
              description
                "List of queues";
              key "queue-name";
              leaf queue-name {
                type leafref {
                  path "/srl_nokia-qos:qos/srl_nokia-qos:queues/srl_nokia-qos:queue/srl_nokia-qos:name";
                }
                description
                  "The queue name";
              }
              leaf maximum-burst-size {
                type uint32;
                units "bytes";
                default "0";
                description
                  "Maximum amount of shared buffer memory available to the queue.

                   On IXR-6/10 this parameter applies to a set of VOQs. If the configured value is 0 or no value is configured the limit is 256 MB (268435456 bytes), however the use of 'alpha' may limit the effective value to less than 256 MB. A configured non-zero value sets a static limit without 'alpha'.

                   On 7220-D2/D3/D5/H2/H3 this parameter applies to an egress queue and the default value of zero instructs the forwarding chip to apply its own limit based on 'alpha'. A non-zero value disables 'alpha'. The alpha value  is 5 (0.25 multiplier of shared buffer space) for unicast queues and 4 (0.125 multiplier of shared buffer space) for multicast queues.

                   On 7730 this parameter applies to egress-queue. The default value of '0' would set the mbs to no queue buffer available.

                   Must be non-zero/non-default in order to add the active-queue-management presence container";
              }
              leaf maximum-burst-size-delay {
                if-feature "srl-feat:qos-queue-burst-delay";
                type uint32 {
                  range "1..4294967295";
                }
                units "microseconds";
                must '0 = ../maximum-burst-size' {
                  error-message "MBS must be zero/default in order to provision MBS delay";
                }
                must 'string(../committed-burst-size-delay) != ""' {
                  error-message "CBS delay must be provisioned together with MBS delay";
                  srl_nokia-ext:if-feature "srl_nokia-features:qos-queue-committed-burst-size";
                }
                must '/srl_nokia-platform:platform/srl_nokia-platform-qos:qos/srl_nokia-platform-qos:traffic-management-mode != "two-priorities"' {
                  error-message "maximum-burst-size-delay is not supported when traffic-management-mode is two-priorities";
                  srl_nokia-ext:if-feature "srl_nokia-features:qos-subinterface-queuing";
                }
                description
                  "Maximum amount of shared buffer memory available to the queue, expressed as a function of time-delay.
                   The number of bytes is calculated by multiplying maximum-burst-size-delay by interface speed the queue is attached to.

                   Must be non-zero/non-default in order to take effect, and when so, the bytes based maximum-burst-size leaf is meaningless.";
              }
              leaf mbs-adaptation-rule {
                if-feature "srl-feat:qos-queue-mbs-adaptation-rule";
                description
                  "Defines how the user-configured values will be adjusted to available hardware values";
                type srl_nokia-comm:adaptation-rule;
                default "closest";
              }
              leaf committed-burst-size {
                if-feature "srl-feat:qos-queue-committed-burst-size";
                type uint32;
                units "bytes";
                description
                  "Committed queue length expressed in bytes";
              }
              leaf committed-burst-size-delay {
                if-feature "srl-feat:qos-queue-committed-burst-size and srl-feat:qos-queue-burst-delay";
                type uint32 {
                  range "0..4294967295";
                }
                units "microseconds";
                must 'not(../committed-burst-size)' {
                  error-message "CBS must be unprovisioned in order to provision CBS delay";
                }
                must 'string(../maximum-burst-size-delay) != ""' {
                  error-message "MBS delay must be provisioned together with CBS delay";
                }
                must '(../maximum-burst-size-delay) and (. <= ../maximum-burst-size-delay)' {
                  error-message "CBS delay must be less than or equal to MBS delay";
                }
                description
                  "Committed amount of shared buffer memory available to the queue, expressed as a function of time-delay.
                   The number of bytes is calculated by multiplying committed-burst-size-delay by interface speed the queue is attached to.

                   Must be present in order to take effect, and when so, the bytes based committed-burst-size leaf is disallowed.";
              }
              leaf cbs-adaptation-rule {
                if-feature "srl-feat:qos-queue-cbs-adaptation-rule";
                description
                  "Defines how the user-configured values will be adjusted to values defined by committed-burst-size-table";
                type srl_nokia-comm:adaptation-rule;
                default "closest";
              }
              leaf high-threshold-bytes {
                if-feature "srl-feat:qos-queue-high-threshold";
                type uint32;
                must '. <= ../maximum-burst-size' {
                  error-message "High threshold bytes must be less than MBS";
                }
                must '. = 0 or /srl_nokia-platform:platform/srl_nokia-platform-qos:qos/srl_nokia-platform-qos:traffic-management-mode != "two-priorities"' {
                  error-message "high-threshold-bytes is not supported when traffic-management-mode is two-priorities";
                  srl_nokia-ext:if-feature "srl_nokia-features:qos-subinterface-queuing";
                }
                default "0";
                description
                  "The queue depth that, when crossed in a rising direction, signals a potential start of congestion

                   On IXR-6/10 this parameter applies to all VOQs associated with the egress queue. On 7220-D2/D3/H2/H3 this parameter applies to the unicast queue only; the configuration of this leaf is ignored when the queue-template is attached to a queue with queue-type other than unicast.

                   The actions that follow the start of congestion depend on whether queue-depth-sampling is true or false. If queue-depth-sampling is false, the system time is recorded and no further actions are taken. If queue-depth sampling is true, the system starts a rapid queue-depth polling process that profiles the entire duration of congestion.

                   On 7220-D2/D3 the threshold is rounded up the nearest multiple of 2048 bytes. On IXR-6e/10e the threshold is rounded up to the nearest multiple of 4096 bytes. On 7220-H2/H3 the threshold is rounded up to the nearest multiple of 254 bytes.

                   The default value of 0 disables the functionality.";
              }
              leaf low-threshold-bytes {
                if-feature "srl-feat:qos-triggered-queue-depth-sampling";
                type uint32 {
                  range "4096..4294967295";
                }
                must '. < ../high-threshold-bytes' {
                  error-message "Low threshold must be less than high threshold";
                }
                must '/srl_nokia-platform:platform/srl_nokia-platform-qos:qos/srl_nokia-platform-qos:traffic-management-mode != "two-priorities"' {
                  error-message "low-threshold-bytes is not supported when traffic-management-mode is two-priorities";
                  srl_nokia-ext:if-feature "srl_nokia-features:qos-subinterface-queuing";
                }
                description
                  "The queue depth that, when crossed in a falling direction, signals a potential end of congestion

                   When queue-depth-sampling is enabled and a VOQ associated with the egress queue is in a congested state the periodic pollling of that VOQ's depth ends when there have been low-threshold-count samples recording a depth below the low-threshold-bytes.";
              }
              leaf low-threshold-count {
                if-feature "srl-feat:qos-triggered-queue-depth-sampling";
                type uint8 {
                  range "1..255";
                }
                default "3";
                must '. = 3 or /srl_nokia-platform:platform/srl_nokia-platform-qos:qos/srl_nokia-platform-qos:traffic-management-mode != "two-priorities"' {
                  error-message "low-threshold-count is not supported when traffic-management-mode is two-priorities";
                  srl_nokia-ext:if-feature "srl_nokia-features:qos-subinterface-queuing";
                }
                description
                  "The number of consecutive queue-depth samples below low-threshold-bytes that are required to declare the end of congestion

                   When queue-depth-sampling is enabled and a VOQ associated with the egress queue is in a congested state the periodic pollling of that VOQ's depth ends when there have been low-threshold-count samples recording a depth below the low-threshold-bytes.";
              }
              leaf queue-depth-sampling {
                if-feature "srl-feat:qos-triggered-queue-depth-sampling";
                must '. = false() or (../high-threshold-bytes > 0 and ../low-threshold-bytes > 0)' {
                  error-message "True setting requires high-threshold-bytes and low-threshold-bytes to be greater than zero";
                }
                must '. = false() or /srl_nokia-platform:platform/srl_nokia-platform-qos:qos/srl_nokia-platform-qos:traffic-management-mode != "two-priorities"' {
                  error-message "queue-depth-sampling is not supported when traffic-management-mode is two-priorities";
                  srl_nokia-ext:if-feature "srl_nokia-features:qos-subinterface-queuing";
                }
                description
                  "True setting enables triggered queue-depth sampling

                   When this setting is enabled and the queue depth of any VOQ associated with the egress queue exceeds the high-threshold, the system records the congestion start-time and begins collecting regular samples of the VOQ's depth. The periodic sampling continues until the low-threshold conditions are met.";
                type boolean;
                default "false";
              }
              leaf interface-pool {
                if-feature "srl-feat:qos-interface-pool-policy";
                description
                  "Interface-pool the queue is assigned to at subinterface level";
                type leafref {
                  path "../../../../../buffer-management/interface-pool-policy/interface-pool/index";
                }
              }
            }
            list pfc-queue {
              if-feature "srl-feat:qos-pfc";
              description
                "List of pfc-queues";
              key "pfc-queue-name";
              leaf pfc-queue-name {
                type leafref {
                  path "/srl_nokia-qos:qos/srl_nokia-qos:queues/srl_nokia-qos:pfc-queue/srl_nokia-qos:pfc-queue-name";
                }
                description
                  "The pfc-queue name";
              }
              leaf maximum-burst-size {
                type uint32;
                units "bytes";
                default "51200";
                description
                  "Maximum amount of shared buffer memory available for the given pfc-queue";
              }
              leaf maximum-pfc-reserved-share-percentage {
                if-feature "srl-feat:qos-pfc-headroom-buffer";
                type srl_nokia-comm:percentage;
                default "10";
                description
                  "Maximum level the pfc-queue can take from pfc-reserved buffer configured per given forwarding-complex";
              }
              leaf maximum-pfc-reserved-share-bytes {
                if-feature "srl-feat:qos-pfc-headroom-buffer";
                type uint32 {
                  range "0..104857600";
                }
                units "bytes";
                description
                  "Maximum level the pfc-queue can take from pfc-reserved buffer configured per given forwarding-complex expressed as bytes. If this value is configured, maximum-pfc-reserved-share-percentage value is ignored";
              }
              leaf pfc-on-threshold {
                if-feature "srl-feat:qos-pfc-threshold";
                type srl_nokia-comm:percentage {
                  range "1..100";
                }
                default "100";
                description
                  "Defines the pfc-queue depth at which pfc-pause-frames genaration will start. It is expressed as percentage of maximum-burst-size";
              }
              leaf pfc-off-threshold {
                if-feature "srl-feat:qos-pfc-threshold";
                type srl_nokia-comm:percentage {
                  range "1..100";
                }
                default "80";
                description
                  "Defines the pfc-queue depth at which pfc-pause-frames will stop be generated. It is expressed as percentage of maximum-burst-size";
                must '. < ../pfc-on-threshold' {
                  error-message "pfc-off-threshold should be lower than pfc-on-threshold";
                }
              }
            }
          }
          description
            "Enter the queues context";
        }
      }
      list slope-policy {
        if-feature "srl-feat:qos-slope-policy";
        max-elements 64;
        description
          "List of slope-policies";
        key "name";
        leaf name {
          type srl_nokia-comm:name;
          description
            "Unique string name used for the slope-policy";
        }
        list wred-slope {
          key "wred-profile";
          leaf wred-profile {
            description
              "The key for individual wred-slopes ";
            type wred-profile;
          }
          leaf slope-enabled {
            type boolean;
            default "false";
            description
              "Enables/disables the corresponding wred-slope";
          }
          leaf min-threshold-percent {
            type srl_nokia-comm:percentage;
            default "85";
            description
              "The buffer threshold defining when the drop-probability starts rising from zero for the corresponding wred-slope";
          }
          leaf max-threshold-percent {
            type srl_nokia-comm:percentage;
            default "100";
            description
              "The buffer threshold defining when the drop-probability reaches its max-probabilty value for the corresponding wred-slope";
          }
          leaf max-probability {
            type srl_nokia-comm:percentage;
            default "80";
            description
              "The drop probability at max-threshold level for the corresponding wred-slope";
          }
        }
      }
      list fp-pool-policy {
        if-feature "srl-feat:qos-fp-pool-policy";
        max-elements 3;
        description
          "List of fp-pool-policies";
        key "name";
        leaf name {
          type srl_nokia-comm:name;
          description
            "Unique string name used for the fp-pool-policy. There is a default fp-pool-policy named 'default', as a reserved name not usable for user-defined fp-pool-policies";
        }
        leaf system-reserve-percentage {
          type srl_nokia-comm:percentage;
          default "10";
          description
            "The ammount of the global buffer-pool reserved for system generated traffic expressed as percentage of total available buffer space. The sum of all root-pools and system-reserved has to be 100%";
        }
        container root-tier {
          description
            "Enter the root-tier context

             Parameters related to root-tier buffers";
          leaf default-slope-policy {
            if-feature "srl-feat:qos-slope-policy";
            type leafref {
              path "../../../slope-policy/name";
            }
            default "default";
            description
              "Slope-policy associated with all root-tier buffer pools";
          }
          list root-pool {
            description
              "List of root-tier pools";
            key "index";
            leaf index {
              type uint8 {
                range "0..4";
              }
              description
                "Root-pool index";
            }
            leaf allocation-weight {
              type uint8 {
                range "0..100";
              }
              description
                "The amount of the egress buffer space allocated to this root-pool. The weight expresses the relative amount of buffer space taking into account the weight of other root-pools.

                 The buffer divided between individual root-pools is after reserved portion has been substracted from the total buffer size";
            }
            container mid-pool-members {
              description
                "Enter the mid-pool-members context

                 List of mid-pool members participating in this given root-pool";
              list mid-pool-member {
                description
                  "Mid-pool member";
                key "index";
                leaf index {
                  type uint8 {
                    range "0..7";
                  }
                  description
                    "Mid-pool index";
                }
              }
            }
          }
        }
        container mid-tier {
          description
            "Enter the mid-tier context

             Mid-pool parameters definition";
          list mid-pool {
            description
              "Mid-pool definition";
            key "index";
            leaf index {
              type uint8 {
                range "0..7";
              }
              description
                "Mid-pool index";
            }
            leaf allocation-percentage-size {
              type srl_nokia-comm:percentage;
              description
                "The size of the mid-pool as a percentage of root-pool";
            }
            leaf slope-policy {
              if-feature "srl-feat:qos-slope-policy";
              type leafref {
                path "../../../../slope-policy/name";
              }
              default "default";
              description
                "The slope-policy attached to the given mid-pool";
            }
          }
        }
      }
      list interface-pool-policy {
        max-elements 64;
        if-feature "srl-feat:qos-interface-pool-policy";
        description
          "List of interface-pool policies";
        key "name";
        leaf name {
          type srl_nokia-comm:name;
          description
            "Unique string name used for the interface-pool-policy";
        }
        list interface-pool {
          description
            "List of interface-pools.
             The interface-pools are directly mapped to mid-pools in 1:1 fashion";
          key "index";
          leaf index {
            type uint8 {
              range "0..7";
            }
          }
          leaf slope-policy {
            if-feature "srl-feat:qos-slope-policy";
            description
              "Slope policy associated with the given interface-pool";
            type leafref {
              path "../../../slope-policy/name";
            }
            default "default";
          }
          container allocation-size {
            description
              "Enter the allocation-size context

               Interface-pool size definition";
            leaf explicit-percentage {
              type srl_nokia-comm:percentage;
              description
                "Interface-pool size as percentage of mid-pool. The value equal '0' means that bw-proportinal distribution is used";
              default "0";
            }
            container bw-proportional {
              description
                "Enter the bw-proportional context

                 Defines how the mid-pool size is shared between individual interface-pools taking into account interface-speed";
              leaf over-subscription-factor {
                description
                  "Factor defining how much of the over-subscription for the given interface-pool is allowed, when its size is calculated as a proportion of the corresponding interface-speed.

                   This parameter is ignored whenever 'explicit-percentage' is set to non-zero value";
                type decimal64 {
                  fraction-digits 2;
                  range "0..10";
                }
                default "1.25";
              }
            }
          }
        }
      }
    }
  }

  grouping queue-names-config {
    container queues {
      description
        "Enter the queues context

         Enclosing container for the list of user-defined queue names";
      list queue {
        key "name";
        description
          "List of user-defined queues";
        leaf name {
          type srl_nokia-comm:name;
          description
            "User-defined name of the queue

             The following queue names are the system-reserved default queue names on 7250 IXR systems:
             unicast-0
             unicast-1
             unicast-2
             unicast-3
             unicast-4
             unicast-5
             unicast-6
             unicast-7

             The following queue names are the system-reserved default queue names on FPcx chipset based systems:
             queue-0
             queue-1
             queue-2
             queue-3
             queue-4
             queue-5
             queue-6
             queue-7
             queue-8
             queue-9
             queue-10
             queue-11";
        }
        leaf queue-index {
          mandatory true;
          type uint16 {
            range "0..11";
          }
          description
            "The queue index (offset) of the queue within the set of queues allocated to a given interface or subinterface";
          must '. <= 7' {
            error-message "queue-index out of range";
            srl_nokia-ext:if-feature "not srl_nokia-features:qos-multi-traffic-queue";
          }
        }
      }
      list pfc-queue {
        if-feature "srl-feat:qos-pfc";
        description
          "List of pfc-queues";
        key "pfc-queue-name";
        unique "queue-index";
        leaf pfc-queue-name {
          type srl_nokia-comm:name;
          description
            "User-defined name of the pfc-queue";
        }
        leaf queue-index {
          mandatory true;
          type uint16 {
            range "0..7";
          }
          must 'not (re-match(../pfc-queue-name,"pfc[0-7]")) or substring-after(../pfc-queue-name, "pfc") = string(current())' {
            error-message "default pfc queue's cannot be modified";
          }
          description
            "The queue index (offset) of the pfc-queue";
        }
      }
      container queue-depth-sampling {
        if-feature "srl-feat:qos-queue-depth-sampling";
        description
          "Enter the queue-depth-sampling context

           System level configuration for queue-depth sampling";
        leaf admin-state {
          type srl_nokia-comm:admin-state;
          default "disable";
          description
            "Set to enable to activate queue-depth sampling on all ports";
        }
        leaf polling-interval {
          description
            "The interval of time between each sample of queue depth";
          type uint16 {
            range "30..1000";
          }
          default "1000";
          units "milliseconds";
        }
      }
    }
  }

  grouping forwarding-classes-config {
    container forwarding-classes {
      description
        "Enter the forwarding-classes context

         Enclosing container for list of user-defined forwarding class names";
      list forwarding-class {
        key "name";
        unique "forwarding-class-index";
        unique "output/unicast-queue";
        leaf name {
          type srl_nokia-comm:name;
          description
            "User-defined name of the forwarding class

             The following forwarding-class names are the system-reserved default FC names on 7250 IXR systems:
             fc0
             fc1
             fc2
             fc3
             fc4
             fc5
             fc6
             fc7

             In addition to fc0-fc7, the following forwarding-class names are also system-reserved default FC names on FPcx based platforms
             fc8
             fc9
             fc10
             fc11
             fc12
             fc13
             fc14
             fc15";
        }
        leaf forwarding-class-index {
          if-feature "srl-feat:qos-forwarding-class-index";
          mandatory true;
          type uint8 {
            range "0..15";
          }
          description
            "Associates the forwarding class name with an index representing the forwarding-class-index. Forwarding classes with a higher forwarding-class-index are generally (subject to scheduler configuration) serviced more preferentially than forwarding classes with a lower forwarding-class-index.

             For the system-reserved default forwarding classes:
             fc0 -> forwarding-class-index = 0
             fc1 -> forwarding-class-index = 1
             fc2 -> forwarding-class-index = 2
             fc3 -> forwarding-class-index = 3
             fc4 -> forwarding-class-index = 4
             fc5 -> forwarding-class-index = 5
             fc6 -> forwarding-class-index = 6
             fc7 -> forwarding-class-index = 7
             fc8 -> forwarding-class-index = 8
             fc9 -> forwarding-class-index = 9
             fc10 -> forwarding-class-index = 10
             fc11 -> forwarding-class-index = 11
             fc12 -> forwarding-class-index = 12
             fc13 -> forwarding-class-index = 13
             fc14 -> forwarding-class-index = 14
             fc15 -> forwarding-class-index = 15";
        }
        container output {
          leaf slope-policy {
            if-feature "srl-feat:qos-slope-policy";
            description
              "Assigns slope policy to interface-level forwarding-class";
            type leafref {
              path "../../../../buffer-management/slope-policy/name";
            }
          }
          leaf queue {
            if-feature "srl-feat:qos-multi-traffic-queue";
            mandatory true;
            type leafref {
              path "../../../../queues/queue/name";
            }
            description
              "Output queue for this forwarding class";
          }
          leaf unicast-queue {
            if-feature "srl-feat:qos-unicast-queue";
            must '. != ../multicast-queue' {
              error-message "cannot use same queue for mutlicast and unicast";
              srl_nokia-ext:if-feature "srl_nokia-features:qos-multicast-queue";
            }
            must 're-match(../../name,"fc[0-7]") or not (/srl_nokia-qos:qos/srl_nokia-qos:queues/srl_nokia-qos:queue[srl_nokia-qos:name=concat("unicast-",/srl_nokia-qos:qos/srl_nokia-qos:queues/srl_nokia-qos:queue[srl_nokia-qos:name=current()]/srl_nokia-qos:queue-index)])' {
              error-message "cannot be configured together with default unicast queue";
            }
            mandatory true;
            type leafref {
              path "../../../../queues/queue/name";
            }
            description
              "Output queue for unicast packets within this forwarding class

               For the system-reserved default forwarding classes:
               fc0 -> unicast-queue = unicast-queue0
               fc1 -> unicast-queue = unicast-queue1
               fc2 -> unicast-queue = unicast-queue2
               fc3 -> unicast-queue = unicast-queue3
               fc4 -> unicast-queue = unicast-queue4
               fc5 -> unicast-queue = unicast-queue5
               fc6 -> unicast-queue = unicast-queue6
               fc7 -> unicast-queue = unicast-queue7";
          }
          leaf multicast-queue {
            if-feature "srl-feat:qos-multicast-queue";
            type leafref {
              path "../../../../queues/queue/name";
            }
            description
              "Output queue for multicast packets within this forwarding class";
            must 're-match(../../name,"fc[0-7]") or not (/srl_nokia-qos:qos/srl_nokia-qos:queues/srl_nokia-qos:queue[srl_nokia-qos:name=concat("multicast-",/srl_nokia-qos:qos/srl_nokia-qos:queues/srl_nokia-qos:queue[srl_nokia-qos:name=current()]/srl_nokia-qos:queue-index)])' {
              error-message "cannot be configured together with default multicast queue";
            }
          }
          description
            "Enter the output context";
        }
      }
    }
  }

  grouping packet-trimming-top {
    container packet-trimming {
      srl_nokia-ext:delivery-node-override "true";
      description
        "Enter the packet-trimming context

         Configuration related to packet-trimming";
      leaf enable-packet-trimming {
        description
          "Enables packet-trimming on the system";
        type boolean;
      }
      leaf-list trimmable-queues {
        if-feature "srl-feat:qos-packet-trimming-queue";
        description
          "List of queues enabled for packet-trimming";
        type leafref {
          path "/srl_nokia-qos:qos/srl_nokia-qos:queues/srl_nokia-qos:queue/srl_nokia-qos:name";
        }
      }
      list trimmable-dscp {
        description
          "List of dscp values which are eligible for packet-trimming";
        key "dscp-value";
        max-elements 3;
        leaf dscp-value {
          description
            "Trimmable DSCP value";
          type srl_nokia-comm:dscp;
        }
        leaf trimmed-dscp {
          mandatory true;
          description
            "The dscp-value the trimmed packets will be marked with";
          type srl_nokia-comm:dscp;
        }
        leaf trimmed-packets-queue {
          mandatory true;
          type leafref {
            path "/srl_nokia-qos:qos/srl_nokia-qos:queues/srl_nokia-qos:queue/srl_nokia-qos:name";
          }
        }
      }
    }
  }

  grouping pfc-profile-config {
    list pfc-mapping-profile {
      key "name";
      max-elements 7;
      leaf name {
        type srl_nokia-comm:name;
        description
          "User defined pfc-mapping-profile name. The name 'default' is reserved for system use";
        must ". != 'default'" {
          error-message "name 'default' is reserved";
        }
      }
      list pfc-priority {
        key "index";
        leaf index {
          description
            "PFC-priority index";
          type uint8 {
            range "0..7";
          }
        }
        leaf pfc-enable {
          type boolean;
          default "false";
          description
            "Enables/disables pfc for a given pfc-priority";
        }
      }
      container received-traffic {
        if-feature "srl-feat:qos-pfc-received-traffic-mapping";
        description
          "Enter the received-traffic context

           Parameters related to receiving traffic for pfc-generation";
        container unicast-mapping {
          description
            "Enter the unicast-mapping context

             Parameters defing mapping of incoming unicast traffic into a pfc-queues";
          list pfc-queue {
            key "pfc-queue-name";
            unique "pfc-pause-frame-priority";
            unique "dot1p";
            unique "forwarding-class";
            leaf pfc-queue-name {
              type leafref {
                path "/srl_nokia-qos:qos/srl_nokia-qos:queues/srl_nokia-qos:pfc-queue/srl_nokia-qos:pfc-queue-name";
              }
              description
                "PFC-queue the packets should be mapped to";
            }
            leaf dot1p {
              type dot1p-value;
              description
                "dot1p of the packets which will be assigned to a given pfc-queue";
            }
            leaf forwarding-class {
              description
                "forwarding-class of packets, that are assigned to a given pfc-queue for untagged routed-interfaces";
              type leafref {
                path "/srl_nokia-qos:qos/srl_nokia-qos:forwarding-classes/srl_nokia-qos:forwarding-class/srl_nokia-qos:name";
              }
              must 'string(../dot1p) = ""' {
                error-message "dot1p and forwarding-class cannot be configured together";
              }
            }
            leaf pfc-pause-frame-priority {
              type uint8 {
                range "0..7";
              }
              description
                "PFC priorities indicated in generated pfc-pause-frame if congestion occurs in a given pfc-queue";
              must 'string(../dot1p) != "" or string(../forwarding-class) != "" ' {
                error-message "either dot1p or forwarding-class must be configured";
              }
            }
          }
        }
      }
      container received-pfc-pause-frames {
        description
          "Enter the received-pfc-pause-frames context

           Parameters describing the behaviour when pfc-pause-frames are received on outgoing interface";
        container deadlock {
          description
            "Enter the deadlock context

             Parameters related to avoid a deadlock related to pfc on outgoing interface";
          leaf enable {
            type boolean;
            default "false";
            description
              "Enables/disables deadlock mechanism";
          }
          leaf detection-timer {
            type uint16 {
              range "10..1500";
            }
            units "millisecond";
            default "750";
            description
              "Number of milliseconds during which outgoing interface is receiving pfc-pause-frames before triggering recovery-timer";
          }
          leaf recovery-timer {
            type uint16 {
              range "100..1500";
            }
            units "milliseconds";
            default "750";
            description
              "Number of milliseconds during which the pfc-pause-frames will be ignored";
          }
        }
        list queue {
          key "queue-name";
          unique "pfc-pause-frame-priority";
          description
            "List of egress-queue which should react to PFC-pause-frames";
          leaf queue-name {
            description
              "Egress-queue name";
            type leafref {
              path "../../../../queues/queue/name";
            }
          }
          leaf pfc-pause-frame-priority {
            type uint8 {
              range "0..7";
            }
            description
              "The pfc-priority received in pfc-pause-frame";
          }
        }
      }
    }
  }

  grouping pfc-interface-stats {
    container statistics {
      description
        "Enter the statistics context

         Statistics related to PFC functionality";
      config false;
      leaf last-clear {
        type srl_nokia-comm:date-and-time-delta;
        description
          "Timestamp of the last time the statistics associated with this queue were cleared";
      }
      leaf total-pfc-pause-frames-received {
        type uint64;
        description
          "Total number of pfc-pause-frames received on the interface";
      }
      leaf total-pfc-pause-frames-generated {
        type uint64;
        description
          "Total number of pfc-pause-frames generated on the interface";
      }
      leaf total-packet-pfc-discards {
        type uint64;
        description
          "Total number of packets discarded becuase pfc-buffer-allocation was depleted. Under normal condition this counter should not be incremented";
      }
      list pfc-priority {
        key "index";
        leaf index {
          description
            "PFC-priority index";
          type uint8 {
            range "0..7";
          }
        }
        leaf pfc-pause-frames-received {
          type uint64;
          description
            "Number of pfc-pause-frames received on the interface and given pfc-priority";
        }
        leaf pfc-pause-frames-generated {
          type uint64;
          description
            "Number of pfc-pause-frames generated on the interface for a given pfc-priority";
        }
        leaf pfc-transitions {
          type uint64;
          description
            "Number of transitions PFC-ON --> PFC-OFF on the interface for a given pfc-priority";
        }
        leaf deadlock-recovery-occurrences {
          type uint64;
          description
            "Number of deadlock recovery events";
        }
      }
    }
  }

  grouping pfc-interface-state {
    leaf source-pfc-mac {
      config false;
      type srl_nokia-comm:mac-address;
      description
        "MAC address used as source-mac address used in generated pfc-pause-frames on the interface";
    }
    leaf deadlock-detection-timer {
      config false;
      type uint16;
      description
        "The actual value of deadlock-detection-timer";
    }
    list pfc-queue {
      config false;
      description
        "List of pfc-queues";
      key "pfc-queue-name";
      leaf pfc-queue-name {
        type leafref {
          path "/srl_nokia-qos:qos/srl_nokia-qos:queues/srl_nokia-qos:pfc-queue/srl_nokia-qos:pfc-queue-name";
        }
        description
          "The pfc-queue name";
      }
      leaf pfc-enable {
        type boolean;
        description
          "Displays the actual state of the pfc-queue";
      }
      leaf forwarding-class {
        if-feature "not srl-feat:qos-pfc-received-traffic-mapping";
        type leafref {
          path "/srl_nokia-qos:qos/srl_nokia-qos:forwarding-classes/srl_nokia-qos:forwarding-class/srl_nokia-qos:name";
        }
        description
          "The forwarding class mapped in the given pfc-queue";
      }
      leaf pfc-on-threshold-bytes {
        if-feature "srl-feat:qos-pfc-threshold";
        type uint32;
        description
          "Displays the actual on-threshold of the pfc-queue";
      }
      leaf pfc-off-threshold-bytes {
        if-feature "srl-feat:qos-pfc-threshold";
        type uint32;
        description
          "Displays the actual off-threshold of the pfc-queue";
      }
      leaf pfc-maximum-burst-size {
        type uint32;
        description
          "Displays the actual maximum-burst-size of the pfc-queue";
      }
      leaf pfc-maximum-pfc-reserved-share {
        if-feature "srl-feat:qos-pfc-headroom-buffer";
        type uint32;
        units "bytes";
        description
          "Displays the actual maximum share the pfc-queue can take from pfc-reserved buffer configured per given forwarding-complex";
      }
      leaf pfc-buffer-used {
        type uint32;
        description
          "The pfc-buffer usage by pfc-queue";
      }
      leaf peak-pfc-buffer-used {
        if-feature "srl-feat:qos-pfc-peak-buffer";
        type uint32;
        description
          "The peak value for pfc-buffer usage by pfc-queue";
      }
      leaf pfc-reserved-buffer-used {
        if-feature "srl-feat:qos-pfc-headroom-buffer";
        type uint32;
        description
          "The pfc-reserved-buffer usage by pfc-queue";
      }
    }
  }

  grouping dcbx {
    container dcbx {
      description
        "Enter the dcbx context

         Container defining DCBX related parameters and state information";
      leaf admin-state {
        type srl_nokia-comm:admin-state;
        default "enable";
        description
          "Enabling/disabling DCBX protocol on the interface";
      }
      leaf oper-state {
        config false;
        type srl_nokia-comm:oper-state;
        description
          "Operational state for DCBX on the interface";
      }
      leaf oper-state-reason {
        config false;
        type enumeration {
          enum lldp-oper-state-down {
            value 1;
          }
          enum multiple-lldp-peers {
            value 2;
          }
          enum remote-dcbx-down {
            value 3;
          }
          enum dcbx-admin-disabled {
            value 4;
          }
        }
        description
          "Indicates the reason for DCBX oper-state down";
      }
      list pfc-priority {
        config false;
        key "index";
        leaf index {
          description
            "PFC-priority index";
          type uint8 {
            range "0..7";
          }
        }
        leaf oper-state {
          type srl_nokia-comm:oper-state;
          description
            "Indicates the PFC state on receiving side of the interface";
        }
        leaf remote-state {
          type enumeration {
            enum remote-down;
            enum remote-up;
          }
        }
      }
      container ets-tlv {
        config false;
        if-feature "srl-feat:qos-dcbx-ets";
        description
          "Enter the ets-tlv context

           Information about received and sent ETS TLVs";
        leaf remote-credit-based-shaper {
          type uint8;
          description
            "Value of credit-based-shaper TLV received from DCBX peer";
        }
        leaf local-credit-based-shaper {
          type uint8;
          description
            "Value of credit-based-shaper TLV sent to DCBX peer";
        }
        leaf remote-maximum-traffic-classes {
          type uint8;
          description
            "Value of maximum-traffic-classes TLV received from DCBX peer";
        }
        leaf local-maximum-traffic-classes {
          type uint8;
          description
            "Value of maximum-traffic-classes TLV sent to DCBX peer";
        }
        list priority {
          description
            "List of priorities";
          key "index";
          leaf index {
            type uint8 {
              range "0..7";
            }
          }
          leaf remote-priority-assignment-configuration {
            description
              "Configured Priority Assignment value for a given priority received from DCBX peer";
            type uint8;
          }
          leaf remote-priority-assignment-recommendation {
            description
              "Recommended Priority Assignment value for a given priority received from DCBX peer";
            type uint8;
          }
          leaf local-priority-assignment {
            description
              "Priority Assignment value for a given priority sent to DCBX peer";
            type uint8;
          }
        }
        list traffic-class {
          description
            "List of traffic-classes";
          key "traffic-class-index";
          leaf traffic-class-index {
            type uint8 {
              range "0..7";
            }
          }
          leaf remote-traffic-class-bandwidth-assignment-configuration {
            description
              "Configured Bandwidth assignment for a given traffic-class received from DCBX peer";
            type uint8;
          }
          leaf remote-traffic-class-bandwidth-assignment-recommendation {
            description
              "Recommended Bandwidth assignment for a given traffic-class received from DCBX peer";
            type uint8;
          }
          leaf local-traffic-class-bandwidth-assignment {
            description
              "Bandwidth assignment for a given traffic-class sent to DCBX peer";
            type uint8;
          }
          leaf remote-tsa-value-configuration {
            description
              "Configured TSA for a given traffic-class received from DCBX peer";
            type uint8;
          }
          leaf remote-tsa-value-recommendation {
            description
              "Recommended TSA for a given traffic-class received from DCBX peer";
            type uint8;
          }
          leaf local-tsa-value {
            description
              "TSA for a given traffic-class sent to DCBX peer";
            type uint8;
          }
        }
      }
    }
  }

  grouping pfc-interface {
    container pfc {
      description
        "Enter the pfc context

         Parameters and information related to PFC on the interface";
      leaf pfc-mapping-profile {
        type leafref {
          path "../../../../pfc-mapping-profile/name";
        }
        description
          "Assigns a pfc-mapping-profile to the interface. There is always default pfc-mapping-profile assigned named 'default'";
        must 'string(../../interface-ref/subinterface) = ""' {
          error-message "Attachment of pfc, not permitted for sub-interfaces";
        }
      }
      leaf pfc-enable {
        type boolean;
        default "false";
        description
          "Enables/disables reaction to received pfc-frames for a given interface";
        must '. = false() or string(../../interface-ref/subinterface) = ""' {
          error-message "pfc cannot be enabled on sub-interfaces";
        }
        must ". = false() or string(../../interface-ref/interface) = '' or /srl_nokia-if:interface[srl_nokia-if:name=current()/../../interface-ref/interface]/srl_nokia-if:ethernet/srl_nokia-if:flow-control/srl_nokia-if:receive = false()" {
          error-message "pfc and ethernet flow-control are mutually exclusive";
        }
      }
      uses pfc-interface-stats;
      uses pfc-interface-state;
    }
  }

  grouping input-class-map-config {
    list input-class-map {
      key "name";
      max-elements 32;
      leaf name {
        type srl_nokia-comm:name;
        description
          "User defined input-class-map name";
      }
      list forwarding-class {
        key "name";
        leaf name {
          type leafref {
            path "/srl_nokia-qos:qos/srl_nokia-qos:forwarding-classes/srl_nokia-qos:forwarding-class/srl_nokia-qos:name";
          }
          description
            "The forwarding class";
        }
        container policers {
          if-feature "srl-feat:qos-policer-policies";
          description
            "Enter the policers context

             Container containing the assignment of the policers to respective forwarding types";
          leaf unicast-policer {
            type leafref {
              path "../../../../policer-policies/policer-policy/policer/policer-id";
            }
            description
              "Policer for the unicast traffic";
          }
          leaf multicast-policer {
            type leafref {
              path "../../../../policer-policies/policer-policy/policer/policer-id";
            }
            description
              "Policer for the multicast traffic";
          }
          leaf broadcast-policer {
            type leafref {
              path "../../../../policer-policies/policer-policy/policer/policer-id";
            }
            description
              "Policer for the broadcast traffic";
          }
          leaf unknown-unicast-policer {
            type leafref {
              path "../../../../policer-policies/policer-policy/policer/policer-id";
            }
            description
              "Policer for the unknown-unicast traffic";
          }
        }
      }
    }
  }

  grouping output-class-map-config {
    list output-class-map {
      key "name";
      max-elements 64;
      leaf name {
        type srl_nokia-comm:name;
        description
          "User defined output-class-map name";
      }
      leaf queue-block-size {
        if-feature "srl-feat:qos-queue-block-size";
        type uint8 {
          range "0|4|8|12";
        }
        default "12";
      }
      list forwarding-class {
        key "name";
        leaf name {
          type leafref {
            path "/srl_nokia-qos:qos/srl_nokia-qos:forwarding-classes/srl_nokia-qos:forwarding-class/srl_nokia-qos:name";
          }
          description
            "The forwarding class";
        }
        leaf slope-policy {
          if-feature "srl-feat:qos-slope-policy";
          description
            "Slope-policy assigned to the forwarding-class";
          type leafref {
            path "../../../buffer-management/slope-policy/name";
          }
        }
        container queue {
          description
            "Enter the queue context

             Container used to define whether local subinterface should be created or re-direction to remote queue at interface level should be used";
          leaf name {
            type leafref {
              path "/srl_nokia-qos:qos/srl_nokia-qos:queues/srl_nokia-qos:queue/srl_nokia-qos:name";
            }
            mandatory true;
            description
              "The queue name";
          }
          leaf re-direct-to {
            type enumeration {
              enum remote;
            }
            description
              "The re-direction to interface level queue";
          }
        }
      }
    }
  }

  grouping ecn-top {
    container explicit-congestion-notification {
      if-feature "srl-feat:qos-ecn";
      srl_nokia-ext:first-released "20.12.1";
      presence "When present ECN marking is enabled globally (on all interfaces)";
      leaf ecn-dscp-policy {
        if-feature "srl-feat:qos-ecn-dscp-policy";
        mandatory true;
        description
          "Reference to the DSCP rewrite policy to use when DSCP rewrite is required as a side effect of ECN remarking.

           This is required configuration in order to globally enable ECN on J2 platforms";
        type leafref {
          path "../../rewrite-rules/dscp-policy/name";
        }
      }
    }
  }

  grouping fpcx-global-tables {
    container resource-management {
      if-feature "srl-feat:qos-resource-management";
      container pre-classification {
        if-feature "srl-feat:qos-pre-classifier";
        description
          "Enter the pre-classification context

           Defines list of protected codepoints within the system

           Dot1p codepoints have highest priority. MPLS and DSCP condepoints are relevant only on untagged interfaces";
        list dot1p {
          description
            "List of protected dot1p values";
          key "value";
          leaf value {
            type dot1p-value;
            description
              "A single dot1p value";
          }
          leaf action {
            type enumeration {
              enum protect {
                description
                  "Indicates that packets marked with the corresponding codepoint should treated preferentially";
              }
            }
          }
        }
        list dscp {
          key "value";
          leaf value {
            type srl_nokia-comm:dscp;
            description
              "A single dscp value";
          }
          leaf action {
            type enumeration {
              enum protect {
                description
                  "Indicates that packets marked with the corresponding codepoint should treated preferentially";
              }
            }
          }
        }
        list mpls-traffic-class {
          key "value";
          leaf value {
            type traffic-class;
            description
              "A single traffic-class value";
          }
          leaf action {
            type enumeration {
              enum protect {
                description
                  "Indicates that packets marked with the corresponding codepoint should treated preferentially";
              }
            }
          }
        }
      }
      container forwarding-class-resource-priority {
        if-feature "srl-feat:qos-forwarding-class-resource-priority";
        description
          "Enter the forwarding-class-resource-priority context

           Defines priority per forwarding-class and per profile to be used for access to shared chipset resources";
        list forwarding-class {
          description
            "User defined forwarding class";
          key "name";
          leaf name {
            type leafref {
              path "/srl_nokia-qos:qos/srl_nokia-qos:forwarding-classes/srl_nokia-qos:forwarding-class/srl_nokia-qos:name";
            }
            description
              "The forwarding class";
          }
          list profile {
            description
              "User defined forwarding class";
            key "profile-name";
            leaf profile-name {
              type srl_nokia-comm:classify-profile;
            }
            leaf unicast-resource-priority {
              description
                "Defines priority unicast packets will be assigned to shared chipset resources for a specific forwarding-class and profile combination";
              type uint8 {
                range "0..3";
              }
            }
            leaf multicast-resource-priority {
              description
                "Defines priority multicast and broadcast packets will be assigned to shared chipset resources for a specific forwarding-class and profile combination";
              type uint8 {
                range "0..3";
              }
            }
          }
        }
      }
      container drop-zones {
        if-feature "srl-feat:qos-drop-zones";
        description
          "Enter the drop-zones context

           Defines drop-zones per shared-resource on per resource-priority and per packet-type basis";
        list unicast-priority {
          key "resource-priority";
          leaf resource-priority {
            description
              "Resource-priority for unicast packets";
            type uint8 {
              range "0..3";
            }
          }
          leaf buffer-segment-drop-zone {
            description
              "Defines drop-zone for buffer-segments at which packets with a given resource-priority will be disarded";
            type uint8 {
              range "0..3";
            }
          }
          leaf packet-id-drop-zone {
            description
              "Defines drop-zone for packet-id at which packets with a given resource-priority will be discarded";
            type uint8 {
              range "0..3";
            }
          }
          leaf header-buffer-drop-zone {
            description
              "Defines drop-zone for header-buffer at which packets with a given resource-priority will be discarded";
            type uint8 {
              range "0..15";
            }
          }
        }
        list multicast-priority {
          key "resource-priority";
          leaf resource-priority {
            description
              "Resource-priority for multicast and broadcast packets";
            type uint8 {
              range "0..3";
            }
          }
          leaf buffer-segment-drop-zone {
            description
              "Defines drop-zone for buffer-segments at which packets with a given resource-priority will be disarded";
            type uint8 {
              range "0..3";
            }
          }
          leaf packet-id-drop-zone {
            description
              "Defines drop-zone for packet-id at which packets with a given resource-priority will be discarded";
            type uint8 {
              range "0..3";
            }
          }
          leaf header-buffer-drop-zone {
            description
              "Defines drop-zone for header-buffer at which packets with a given resource-priority will be discarded";
            type uint8 {
              range "0..15";
            }
          }
        }
      }
      container resource-utilization-thresholds {
        if-feature "srl-feat:qos-resource-utilization-thresholds";
        description
          "Enter the resource-utilization-thresholds context

           Defines thresholds monitoring used resorces which divide individual shared chipset resources into 4 utilization-zones";
        list threshold {
          key "index";
          leaf index {
            description
              "Threshold index";
            type uint8 {
              range "1..3";
            }
          }
          container buffer-segment {
            description
              "Enter the buffer-segment context

               Utilization thresholds for buffer segments";
            leaf rising-threshold-value {
              description
                "The rising-threshold-value definining the transition from higher-congestion zone to lower-congestion zone";
              type decimal64 {
                fraction-digits 2;
                range "0..100";
              }
            }
            leaf falling-threshold-value {
              description
                "The falling-threshold-value defining the transition from lower-congestion zone to higher-congestion zone";
              type decimal64 {
                fraction-digits 2;
                range "0..100";
              }
            }
          }
          container packet-id {
            description
              "Enter the packet-id context

               Utilization thresholds for packet re-ordering contexts";
            leaf rising-threshold-value {
              description
                "The rising-threshold-value definining the transition from higher-congestion zone to lower-congestion zone";
              type decimal64 {
                fraction-digits 2;
                range "0..100";
              }
            }
            leaf falling-threshold-value {
              description
                "The falling-threshold-value defining the transition from lower-congestion zone to higher-congestion zone";
              type decimal64 {
                fraction-digits 2;
                range "0..100";
              }
            }
          }
          container header-buffer {
            description
              "Enter the header-buffer context

               Utilization thresholds for packet header buffers";
            leaf rising-threshold-value {
              description
                "The rising-threshold-value definining the transition from higher-congestion zone to lower-congestion zone";
              type decimal64 {
                fraction-digits 2;
                range "0..100";
              }
            }
            leaf falling-threshold-value {
              description
                "The falling-threshold-value defining the transition from lower-congestion zone to higher-congestion zone";
              type decimal64 {
                fraction-digits 2;
                range "0..100";
              }
            }
          }
        }
      }
      description
        "Enter the resource-management context";
    }
    container system-generated-traffic {
      if-feature "srl-feat:qos-system-generated-traffic-map";
      description
        "Enter the system-generated-traffic context

         Defines mapping of dscp values into forwarding-class and profile for system generated traffic";
      config false;
      list dscp {
        key "value";
        leaf value {
          type srl_nokia-comm:dscp;
        }
        leaf forwarding-class {
          type leafref {
            path "/srl_nokia-qos:qos/srl_nokia-qos:forwarding-classes/srl_nokia-qos:forwarding-class/srl_nokia-qos:name";
          }
          description
            "The forwarding class";
        }
        leaf profile {
          if-feature "srl-feat:qos-classify-profile";
          type srl_nokia-comm:classify-profile;
          description
            "The profile to which the DSCP value is mapped";
        }
      }
    }
  }

  grouping scheduler-policies-top {
    container scheduler-policies {
      description
        "Enter the scheduler-policies context

         Container for the list of configured scheduler policies";
      list scheduler-policy {
        if-feature "srl-feat:qos-scheduler-policies";
        key "name";
        description
          "List of scheduler policies. A scheduler policy is a set of schedulers that are to be applied together. Each scheduler within a scheduler policy takes an input, and outputs it according to a scheduling discipline that is specified within it";
        leaf name {
          type srl_nokia-comm:name;
          description
            "Name for the scheduler policy";
          must ". != 'default'" {
            error-message "name 'default' is reserved";
          }
        }
        list scheduler {
          key "sequence";
          description
            "List of defined QoS traffic schedulers";
          leaf sequence {
            type uint32 {
              range "0..1";
            }
            description
              "Sequence number for the scheduler within the scheduler policy. Schedulers are processed from lowest sequence to highest";
            must "(. = 0 and ../priority = 'strict') or (. = 1 and ../priority != 'strict')" {
              error-message "scheduler with sequence 0 must be strict priority and scheduler with sequence 1 must be weighted RR";
            }
          }
          leaf priority {
            type enumeration {
              enum strict {
                description
                  "This scheduler term is considered as a strict priority term - such that packets that arrive in the queue are immediately serviced";
              }
            }
            description
              "Priority of the scheduler within the scheduler policy";
          }
          list input {
            key "id";
            unique "queue-name";
            description
              "List of input sources for the scheduler";
            leaf id {
              type string;
              description
                "User-defined identifier for the scheduler input";
            }
            leaf input-type {
              type enumeration {
                enum queue;
              }
              default "queue";
            }
            leaf queue-name {
              type leafref {
                path "/srl_nokia-qos:qos/srl_nokia-qos:queues/srl_nokia-qos:queue/srl_nokia-qos:name";
              }
              description
                "The queue name";
            }
            leaf priority-level {
              if-feature "srl-feat:qos-subinterface-queuing";
              type uint8 {
                range "1..5";
              }
              description
                "Priority-level for the input in strict-priority scheduler (scheduler 0)";
              must '/srl_nokia-platform:platform/srl_nokia-platform-qos:qos/srl_nokia-platform-qos:traffic-management-mode = "two-priorities" and ../../sequence = 0' {
                error-message "Can only be configured in scheduler sequence 0 when in two-priorities mode";
              }
            }
            leaf peak-rate-percent {
              srl_nokia-ext:first-released "20.6.1";
              type uint8 {
                range "1..100";
              }
              default "100";
              description
                "The maximum percentage of port bandwidth that is available to the traffic in this queue during the PIR scheduling loop. The default is 100";
              must '/srl_nokia-platform:platform/srl_nokia-platform-qos:qos/srl_nokia-platform-qos:traffic-management-mode = "eight-priorities" or (../../sequence = 1) or (. = 100)' {
                error-message "peak-rate-percent can be configured only in weighted schedulers in two-priorities";
                srl_nokia-ext:if-feature "srl_nokia-features:qos-subinterface-queuing";
              }
            }
            leaf weight {
              type uint8 {
                range "1..255";
              }
              must '. <= 127' {
                error-message "Should be in the range 1..127";
                srl_nokia-ext:if-feature "not (srl_nokia-features:ixr-dnx)";
              }
              must '/srl_nokia-platform:platform/srl_nokia-platform-qos:qos/srl_nokia-platform-qos:traffic-management-mode = "eight-priorities" or (../../sequence = 1)' {
                error-message "weight can be configured only in weighted schedulers in two-priorities";
                srl_nokia-ext:if-feature "srl_nokia-features:qos-subinterface-queuing";
              }
              description
                "For weighted round-robin schedulers, this leaf indicates the weight of the corresponding input";
            }
            leaf committed-rate-kbps {
              if-feature "srl-feat:qos-subinterface-queuing";
              description
                "Defines CIR value for subinterface queue";
              type uint64;
              must '/srl_nokia-platform:platform/srl_nokia-platform-qos:qos/srl_nokia-platform-qos:traffic-management-mode = "two-priorities"' {
                error-message "committed-rate can be configured when traffic-management is set to two-priorities";
              }
            }
            leaf committed-rate-percent {
              if-feature "srl-feat:qos-subinterface-queuing";
              description
                "Defines CIR value for subinterface queue";
              type uint8 {
                range "0..100";
              }
              must '/srl_nokia-platform:platform/srl_nokia-platform-qos:qos/srl_nokia-platform-qos:traffic-management-mode = "two-priorities"' {
                error-message "committed-rate can be configured when traffic-management is set to two-priorities";
              }
              must '. >= 0 and not (../committed-rate-kbps >= 0)' {
                error-message "committed-rate-percent and committed-rate-kbps are mutually exclusive";
              }
              must '../peak-rate-percent  >= .' {
                error-message "committed-rate-percent must be less than or equal to peak-rate-percent";
              }
            }
            leaf peak-rate-kbps {
              if-feature "srl-feat:qos-subinterface-queuing";
              description
                "Defines PIR value for subinterface queue";
              type uint64;
              must '/srl_nokia-platform:platform/srl_nokia-platform-qos:qos/srl_nokia-platform-qos:traffic-management-mode = "two-priorities"' {
                error-message "peak-rate-kbps can be configured when traffic-management is set to two-priorities";
              }
              must '. >= 0 and ../../sequence = 1' {
                error-message "can only be configured for weighted schedulers";
              }
              must '. >= 0 and not (../peak-rate-percent != 100)' {
                error-message "peak-rate-percent and peak-rate-kbps are mutually exclusive";
              }
              must '. >= (../committed-rate-kbps)' {
                error-message "committed-rate-kbps must be less than or equal to peak-rate-kbps";
              }
            }
          }
          container output {
            if-feature "srl-feat:qos-subinterface-queuing";
            description
              "Enter the output context

               Output for this scheduler";
            leaf output-type {
              type enumeration {
                enum interface;
              }
              must '/srl_nokia-platform:platform/srl_nokia-platform-qos:qos/srl_nokia-platform-qos:traffic-management-mode = "two-priorities" and (../../sequence = 1)' {
                error-message "output can only be configured for scheduler sequence 1 when traffic-management-mode is two-priorities";
              }
            }
            leaf peak-rate-percent {
              description
                "Defines PIR aggregate output rate for scheduler";
              type uint8 {
                range "1..100";
              }
              must '/srl_nokia-platform:platform/srl_nokia-platform-qos:qos/srl_nokia-platform-qos:traffic-management-mode = "two-priorities" and (../../sequence = 1)' {
                error-message "output can only be configured for scheduler sequence 1 when traffic-management-mode is two-priorities";
              }
              must '../output-type = "interface"' {
                error-message "peak-rate-percent can only be configured when output-type is set to interface";
              }
            }
          }
        }
      }
      container scheduling-priority-mapping-table {
        if-feature "srl-feat:qos-scheduling-priority-mapping";
        description
          "Enter the scheduling-priority-mapping-table context

           This table maps individual scheduling-classes into scheduling-priority.

           This table is global for the whole system";
        list scheduling-class {
          description
            "List of scheduling-classes";
          key "index";
          leaf index {
            description
              "Scheduling-class index";
            type uint8 {
              range "0|2|4|6";
            }
          }
          leaf scheduling-priority {
            description
              "Scheduling-priority assigned to the scheduling-class";
            type uint8 {
              range "0..2";
            }
          }
        }
      }
      list queue-scheduling-policy {
        if-feature "srl-feat:qos-queue-scheduling-policy";
        key "name";
        max-elements 64;
        description
          "Scheduling-policy defining scheduling at queue level";
        leaf name {
          type srl_nokia-comm:name;
          description
            "Name for the queue-scheduling-policy";
        }
        list queue {
          description
            "The queue parameters that is the input to the scheduler";
          key "queue-name";
          leaf queue-name {
            type leafref {
              path "/srl_nokia-qos:qos/srl_nokia-qos:queues/srl_nokia-qos:queue/srl_nokia-qos:name";
            }
            description
              "The queue name";
          }
          container scheduling {
            description
              "Enter the scheduling context

               Definition of scheduling related for the queue";
            leaf scheduling-class {
              description
                "Scheduling-class of the queue";
              type uint8 {
                range "0|2|4|6";
              }
              default "0";
            }
            leaf weight {
              description
                "The scheduling weight of the given queue";
              type uint8 {
                range "1..127";
              }
              default "1";
            }
            container packet-length-adjustment {
              description
                "Enter the packet-length-adjustment context

                 The definition on how packet-length should be adjusted for the scheduling-algorithm calculation";
              leaf add {
                description
                  "Number of bytes to be added to the packet-length for the scheduling-algorithm calculation";
                type uint32 {
                  range "0..32";
                }
                units "bytes";
                default "0";
              }
            }
          }
        }
        list scheduler {
          description
            "Scheduling options for output traffic";
          key "sequence-id";
          leaf sequence-id {
            description
              "Identifier of the scheduler";
            type uint8 {
              range "0..16";
            }
          }
          leaf tier {
            description
              "Scheduling-hierarchy level";
            type uint8 {
              range "0..1";
            }
            default "0";
            must "(. = 0) or (. = 1 and ../inputs/inputs = 'auto-input')" {
              error-message "tier 1 scheduler must have auto-inputs configured";
            }
            must "(. = 1) or (. = 0 and ../inputs/inputs != 'auto-input')" {
              error-message "tier 0 scheduler can not have auto-inputs configured";
            }
          }
          leaf output-weight {
            if-feature "srl-feat:qos-scheduler-output-weight";
            description
              "Output weight of the scheduler";
            type uint8 {
              range "1..127";
            }
            default "1";
            must '. = 1 or ../tier = 0' {
              error-message "output-weight only supported on tier 0 schedulers";
            }
          }
          leaf burst-allowance {
            description
              "Burst allowance for the scheduler in bytes";
            type uint64;
            units "bytes";
            default "9000";
          }
          leaf threshold-separation {
            description
              "Separation between thresholds in scheduling bucket in bytes";
            type uint32;
            default "28672";
          }
          container rate {
            description
              "Enter the rate context

               Defines the scheduler rate";
            choice kbps-or-percentage {
              case peak-rate-kbps {
                leaf peak-rate-kbps {
                  description
                    "Scheduler peak-rate in kilobits-per-second";
                  type uint64;
                }
              }
              case peak-rate-percentage {
                leaf peak-rate-percentage {
                  description
                    "Scheduler peak-rate as the percentage of the output rate";
                  type uint8 {
                    range "1..100";
                  }
                  default "100";
                }
              }
            }
            leaf pir-adaptation-rule {
              description
                "Defines how the user-configured values will be adjusted to available hardware values";
              type srl_nokia-comm:adaptation-rule;
              default "closest";
            }
          }
          container inputs {
            description
              "Enter the inputs context

               List of scheduler inputs";
            choice auto-or-explicit-input {
              case queue-list {
                leaf-list queue {
                  description
                    "List of queues which are input to the scheduler";
                  type leafref {
                    path "../../../queue/queue-name";
                  }
                }
              }
              case auto-input {
                leaf inputs {
                  description
                    "This options defines that all queues defined in this queue-scheduling-policy are input to this tier-0 scheduler or all tier-0 schedulers are input to tier-1 scheduler";
                  type enumeration {
                    enum auto-input;
                  }
                }
              }
            }
          }
        }
      }
      list sched-class-scheduling-policy {
        if-feature "srl-feat:qos-sched-class-scheduling-policy";
        description
          "Scheduling-policy defining scheduling at scheduling-class level";
        key "name";
        max-elements 64;
        leaf name {
          type srl_nokia-comm:name;
          description
            "Name for the sched-class-scheduling-policy";
        }
        list scheduler {
          description
            "Scheduling options for output traffic";
          key "sequence-id";
          leaf sequence-id {
            description
              "Identifier of the scheduler";
            type uint8 {
              range "0..8";
            }
          }
          leaf tier {
            description
              "Scheduling-hierarchy level";
            type uint8 {
              range "0..1";
            }
            default "0";
          }
          leaf burst-allowance {
            description
              "Burst allowance for the scheduler in bytes";
            type uint64;
            units "bytes";
            default "9000";
          }
          leaf threshold-separation {
            description
              "Separation between thresholds in scheduling bucket in bytes";
            type uint32;
            default "28672";
          }
          container rate {
            description
              "Enter the rate context

               Defines the scheduler rate";
            choice kbps-or-percentage {
              case peak-rate-kbps {
                leaf peak-rate-kbps {
                  description
                    "Scheduler peak-rate in kilobits-per-second";
                  type uint64;
                }
              }
              case peak-rate-percentage {
                leaf peak-rate-percentage {
                  description
                    "Scheduler peak-rate as the percentage of the output rate";
                  type uint8 {
                    range "1..100";
                  }
                  default "100";
                }
              }
            }
            leaf pir-adaptation-rule {
              description
                "Defines how the user-configured values will be adjusted to available hardware values";
              type srl_nokia-comm:adaptation-rule;
              default "closest";
            }
          }
          container inputs {
            description
              "Enter the inputs context

               List of scheduler inputs";
            choice auto-or-explicit-list {
              case scheduling-class {
                leaf-list scheduling-class {
                  description
                    "List of scheduling-classes which are input to this tier-0 scheduler";
                  type uint8 {
                    range "0|2|4|6";
                  }
                }
              }
              case auto-input {
                leaf inputs {
                  description
                    "This options defines that all scheduling-classes are input to this tier-0 scheduler or all tier-0 schedulers are input to tier-1 scheduler";
                  type enumeration {
                    enum auto-input;
                  }
                }
              }
            }
          }
        }
      }
    }
  }

  grouping preserve-dscp-top {
    description
      "Configuration for DSCP preservation from ingress to egress";
    leaf preserve-dscp {
      description
        "When forwarding an untunneled IP packet or decapsulating an IP-in-IP packet, preserve the received DSCP and use it in the transmitted packet.

         This should not be enabled unless all IP packets have been classified by a multi-field classifier policy";
      type boolean;
      must 'not(. = true() and boolean(../explicit-congestion-notification))' {
        error-message "Explicit congestion notification should not be enabled globally with preserve-dscp";
      }
    }
  }

  grouping qos-classifier-top {
    description
      "Top-level grouping for classifier data";
    container classifiers {
      srl_nokia-ext:first-released "19.11.1";
      uses vxlan-classifier {
        if-feature "srl-feat:qos-vxlan-classifier-policy";
      }
      uses ip-classifier;
      uses mpls-tc-classifier;
      uses ethernet-classifier;
      uses egress-reclassification {
        if-feature "srl-feat:qos-dscp-reclassifier-policy";
      }
      description
        "Enter the classifiers context";
    }
  }

  grouping egress-reclassification {
    list dscp-reclassify-policy {
      description
        "Egress DSCP reclassification policy";
      key "name";
      leaf name {
        type srl_nokia-comm:name;
        description
          "Name of egress dscp-reclassifier policy";
      }
      list dscp {
        key "value";
        leaf value {
          type srl_nokia-comm:dscp;
        }
        leaf forwarding-class {
          type leafref {
            path "/srl_nokia-qos:qos/srl_nokia-qos:forwarding-classes/srl_nokia-qos:forwarding-class/srl_nokia-qos:name";
          }
          description
            "The forwarding class";
        }
        leaf profile {
          if-feature "srl-feat:qos-classify-profile";
          type srl_nokia-comm:classify-profile;
          description
            "The profile to which the DSCP value is mapped";
        }
      }
    }
  }

  grouping vxlan-classifier {
    leaf vxlan-default {
      if-feature "srl-feat:qos-vxlan-classifier-policy";
      type leafref {
        path "/srl_nokia-qos:qos/srl_nokia-qos:classifiers/srl_nokia-qos:dscp-policy/name";
      }
      description
        "Reference to the name of a DSCP mapping policy that applies to terminating VXLAN packets";
    }
  }

  grouping ip-classifier {
    list dscp-policy {
      key "name";
      leaf name {
        type srl_nokia-comm:name;
        description
          "User-configured name for a DSCP mapping policy

           The name 'default' is reserved for the system default DSCP mapping policy";
        must ". != 'default'" {
          error-message "Policy name 'default' not permitted";
          srl_nokia-ext:if-feature "not srl_nokia-features:fpcx";
        }
      }
      list dscp {
        key "value";
        leaf value {
          type srl_nokia-comm:dscp;
        }
        leaf forwarding-class {
          type leafref {
            path "/srl_nokia-qos:qos/srl_nokia-qos:forwarding-classes/srl_nokia-qos:forwarding-class/srl_nokia-qos:name";
          }
          description
            "The forwarding class";
        }
        leaf drop-probability {
          srl_nokia-ext:first-released "20.12.1";
          if-feature "srl-feat:qos-drop-probability";
          type srl_nokia-comm:drop-probability;
          description
            "The drop probability to which the DSCP value is mapped";
        }
        leaf profile {
          if-feature "srl-feat:qos-classify-profile";
          type srl_nokia-comm:classify-profile;
          description
            "The profile to which the DSCP value is mapped";
        }
        leaf de-out-profile {
          if-feature "srl-feat:qos-de-out-profile";
          type boolean;
          default "true";
          description
            "The discard-eligibility to which the DSCP value is mapped";
        }
        leaf ip-rewrite-policy {
          if-feature "srl-feat:qos-ip-rewrite-policy";
          description
            "The ip-rewrite-policy to be used for this dscp-value";
          type leafref {
            path "../../../../rewrite-rules/ip-rewrite-policy/name";
          }
        }
      }
    }
  }

  grouping mpls-tc-classifier {
    list mpls-traffic-class-policy {
      if-feature "srl-feat:qos-mpls-classifier-policy";
      key "name";
      leaf name {
        type srl_nokia-comm:name;
        description
          "User-configured name for an MPLS traffic-class mapping policy

           The name 'default' is reserved for the system default MPLS TC mapping policy";
        must ". != 'default'" {
          error-message "Policy name 'default' not permitted";
          srl_nokia-ext:if-feature "not srl_nokia-features:fpcx";
        }
      }
      list traffic-class {
        key "value";
        leaf value {
          type traffic-class;
          description
            "A single traffic-class value";
        }
        leaf forwarding-class {
          type leafref {
            path "/srl_nokia-qos:qos/srl_nokia-qos:forwarding-classes/srl_nokia-qos:forwarding-class/srl_nokia-qos:name";
          }
          description
            "The forwarding class";
        }
        leaf drop-probability {
          srl_nokia-ext:first-released "21.6.3";
          if-feature "srl-feat:qos-drop-probability";
          type srl_nokia-comm:drop-probability;
          description
            "The drop probability to which the traffic-class value is mapped";
        }
        leaf profile {
          if-feature "srl-feat:qos-classify-profile";
          type srl_nokia-comm:classify-profile;
          description
            "The profile to which the traffic-class value is mapped";
        }
        leaf de-out-profile {
          if-feature "srl-feat:qos-de-out-profile";
          type boolean;
          default "true";
          description
            "The discard-eligibility to which the traffic-class value is mapped";
        }
        leaf ip-rewrite-policy {
          if-feature "srl-feat:qos-ip-rewrite-policy";
          description
            "The ip-rewrite-policy to be used for this traffic-class value";
          type leafref {
            path "../../../../rewrite-rules/ip-rewrite-policy/name";
          }
        }
      }
    }
  }

  grouping ethernet-classifier {
    list dot1p-policy {
      if-feature "srl-feat:qos-dot1p-classifier-policy";
      key "name";
      leaf name {
        type srl_nokia-comm:name;
        description
          "User-configured name for a 802.1p prioriy code point mapping policy

           The name 'default' is reserved for the system default dot1p mapping policy";
        must ". != 'default'" {
          error-message "Policy name 'default' not permitted";
          srl_nokia-ext:if-feature "not srl_nokia-features:fpcx";
        }
      }
      list dot1p {
        key "value";
        leaf value {
          type dot1p-value;
        }
        leaf forwarding-class {
          type leafref {
            path "/srl_nokia-qos:qos/srl_nokia-qos:forwarding-classes/srl_nokia-qos:forwarding-class/srl_nokia-qos:name";
          }
          description
            "The forwarding class";
        }
        leaf drop-probability {
          if-feature "srl-feat:qos-drop-probability";
          type srl_nokia-comm:drop-probability;
          description
            "The drop probability to which the dot1p value is mapped";
        }
        leaf profile {
          if-feature "srl-feat:qos-classify-profile";
          type srl_nokia-comm:classify-profile;
          description
            "The profile to which the dot1p value is mapped";
        }
        leaf de-out-profile {
          if-feature "srl-feat:qos-de-out-profile";
          type boolean;
          default "true";
          description
            "The discard-eligibility to which dot1p value is mapped ";
        }
        leaf ip-rewrite-policy {
          if-feature "srl-feat:qos-ip-rewrite-policy";
          description
            "The ip-rewrite-policy to be used for this dot1p value";
          type leafref {
            path "../../../../rewrite-rules/ip-rewrite-policy/name";
          }
        }
      }
    }
  }

  grouping qos-rewrite-top {
    description
      "Top-level grouping for traffic marking (rewrite) policies";
    container rewrite-rules {
      srl_nokia-ext:first-released "19.11.1";
      uses vxlan-outer-header-rewrite {
        if-feature "srl-feat:qos-vxlan-outer-header-rewrite";
      }
      uses dscp-rewrite;
      uses mpls-tc-rewrite;
      uses dot1p-rewrite;
      uses ip-rewrite {
        if-feature "srl-feat:qos-ip-rewrite-policy";
      }
      description
        "Enter the rewrite-rules context";
    }
  }

  grouping vxlan-outer-header-rewrite {
    leaf vxlan-outer-header-dscp-policy {
      type leafref {
        path "/srl_nokia-qos:qos/srl_nokia-qos:rewrite-rules/srl_nokia-qos:dscp-policy/name";
      }
      description
        "Reference to the name of a DSCP rewrite policy that applies to the outer IP header of originating VXLAN packets";
    }
  }

  grouping dscp-rewrite {
    list dscp-policy {
      key "name";
      leaf name {
        type srl_nokia-comm:name;
        description
          "User-configured name for a DSCP rewrite policy";
        must ". != 'default'" {
          error-message "Policy name 'default' not permitted";
        }
      }
      list map {
        key "forwarding-class";
        leaf forwarding-class {
          type leafref {
            path "/srl_nokia-qos:qos/srl_nokia-qos:forwarding-classes/srl_nokia-qos:forwarding-class/srl_nokia-qos:name";
          }
          description
            "The forwarding class";
        }
        list drop-probability {
          srl_nokia-ext:first-released "20.12.1";
          if-feature "srl-feat:qos-drop-probability";
          key "drop-probability";
          leaf drop-probability {
            type srl_nokia-comm:drop-probability;
            description
              "A drop probability level within the FC for which a different remarking is desired";
          }
          leaf dscp {
            mandatory true;
            type srl_nokia-comm:dscp;
            description
              "The DSCP marking to be used for this specific drop-probability";
          }
        }
        list profile {
          if-feature "srl-feat:qos-rewrite-profile";
          key "profile";
          leaf profile {
            type srl_nokia-comm:rewrite-profile;
            description
              "A packet profile within the FC for which a different remarking is desired";
          }
          leaf dscp {
            mandatory true;
            type srl_nokia-comm:dscp;
            description
              "The DSCP marking to be used for this specific profile";
          }
        }
        leaf dscp {
          mandatory true;
          type srl_nokia-comm:dscp;
          description
            "The DSCP marking to be used for all packets associated with the FC, except those with a drop-probability-specific or profile-specific override";
        }
      }
    }
  }

  grouping ip-rewrite {
    list ip-rewrite-policy {
      key "name";
      leaf name {
        type srl_nokia-comm:name;
        description
          "User defined ip-rewrite-policy name";
      }
      container in-plus {
        choice dscp-or-precedence {
          case dscp {
            leaf dscp {
              type srl_nokia-comm:dscp;
              description
                "The DSCP marking to be used for this specific profile";
            }
          }
          case precedence {
            leaf precedence {
              description
                "The ip-precedence marking to be used for this specific profile";
              type uint8 {
                range "0..7";
              }
            }
          }
        }
        description
          "Enter the in-plus context";
      }
      container in {
        choice dscp-or-precedence {
          case dscp {
            leaf dscp {
              type srl_nokia-comm:dscp;
              description
                "The DSCP marking to be used for this specific profile";
            }
          }
          case precedence {
            leaf precedence {
              description
                "The ip-precedence marking to be used for this specific profile";
              type uint8 {
                range "0..7";
              }
            }
          }
        }
        description
          "Enter the in context";
      }
      container out {
        choice dscp-or-precedence {
          case dscp {
            leaf dscp {
              type srl_nokia-comm:dscp;
              description
                "The DSCP marking to be used for this specific profile";
            }
          }
          case precedence {
            leaf precedence {
              description
                "The ip-precedence marking to be used for this specific profile";
              type uint8 {
                range "0..7";
              }
            }
          }
        }
        description
          "Enter the out context";
      }
      container exceed {
        choice dscp-or-precedence {
          case dscp {
            leaf dscp {
              type srl_nokia-comm:dscp;
              description
                "The DSCP marking to be used for this specific profile";
            }
          }
          case precedence {
            leaf precedence {
              description
                "The ip-precedence marking to be used for this specific profile";
              type uint8 {
                range "0..7";
              }
            }
          }
        }
        description
          "Enter the exceed context";
      }
    }
  }

  grouping mpls-tc-rewrite {
    list mpls-traffic-class-policy {
      if-feature "srl-feat:qos-mpls-rewrite-policy";
      key "name";
      leaf name {
        type srl_nokia-comm:name;
        description
          "User-configured name for an MPLS traffic-class rewrite policy";
        must ". != 'default'" {
          error-message "Policy name 'default' not permitted";
        }
      }
      list map {
        key "forwarding-class";
        leaf forwarding-class {
          type leafref {
            path "/srl_nokia-qos:qos/srl_nokia-qos:forwarding-classes/srl_nokia-qos:forwarding-class/srl_nokia-qos:name";
          }
          description
            "The forwarding class";
        }
        list drop-probability {
          srl_nokia-ext:first-released "21.6.1";
          if-feature "srl-feat:qos-drop-probability";
          key "drop-probability";
          leaf drop-probability {
            type srl_nokia-comm:drop-probability;
            description
              "A drop probability level within the FC for which a different remarking is desired";
          }
          leaf traffic-class {
            mandatory true;
            type traffic-class;
            description
              "The MPLS traffic class marking to be used for this specific drop-probability";
          }
        }
        list profile {
          if-feature "srl-feat:qos-rewrite-profile";
          key "profile";
          leaf profile {
            type srl_nokia-comm:rewrite-profile;
            description
              "A packet profile within the FC for which a different remarking is desired";
          }
          leaf traffic-class {
            mandatory true;
            type traffic-class;
            description
              "The MPLS traffic class marking to be used for this specific profile";
          }
        }
        leaf traffic-class {
          mandatory true;
          type traffic-class;
          description
            "The MPLS traffic class marking to be used for all packets associated with the FC, except those with a drop-probability-specific or profile-specific override";
        }
      }
    }
  }

  grouping dot1p-rewrite {
    list dot1p-policy {
      if-feature "srl-feat:qos-dot1p-rewrite-policy";
      key "name";
      leaf name {
        type srl_nokia-comm:name;
        description
          "User-configured name for an 802.1p priorty code point rewrite policy";
        must ". != 'default'" {
          error-message "Policy name 'default' not permitted";
          srl_nokia-ext:if-feature "srl_nokia-features:fpcx";
        }
      }
      list map {
        key "forwarding-class";
        leaf forwarding-class {
          type leafref {
            path "/srl_nokia-qos:qos/srl_nokia-qos:forwarding-classes/srl_nokia-qos:forwarding-class/srl_nokia-qos:name";
          }
          description
            "The forwarding class";
        }
        list drop-probability {
          srl_nokia-ext:first-released "20.12.1";
          if-feature "srl-feat:qos-drop-probability";
          key "drop-probability";
          leaf drop-probability {
            type srl_nokia-comm:drop-probability;
            description
              "A drop probability level within the FC for which a different remarking is desired";
          }
          leaf dot1p {
            mandatory true;
            type dot1p-value;
            description
              "The dot1p marking to be used for this specific drop-probability";
          }
        }
        list profile {
          if-feature "srl-feat:qos-rewrite-profile";
          key "profile";
          leaf profile {
            type srl_nokia-comm:rewrite-profile;
            description
              "A packet profile within the FC for which a different remarking is desired";
          }
          leaf inner-dot1p {
            type dot1p-value;
            description
              "The inner-dot1p marking to be used for this specific forwarding-class and profile";
          }
          leaf outer-dot1p {
            type dot1p-value;
            description
              "The outer-dot1p marking to be used for this specific forwarding-class and profile";
          }
          leaf inner-de {
            if-feature "srl-feat:qos-rewrite-inner-de";
            description
              "Re-marking inner-vlan discard-eligibility bit for this speciific forwarding-class and profile";
            type boolean;
            default "false";
          }
          leaf outer-de {
            if-feature "srl-feat:qos-rewrite-outer-de";
            description
              "Re-marking outer-vlan discard-eligibility bit for this specific forwarding-class and profile";
            type boolean;
            default "false";
          }
        }
        leaf dot1p {
          if-feature "srl-feat:qos-rewrite-dot1p";
          mandatory true;
          type dot1p-value;
          description
            "The dot1p marking to be used for all packets associated with the FC, except those with a drop-probability-specific or profile-specific override";
        }
        leaf inner-dot1p {
          if-feature "srl-feat:qos-rewrite-inner-dot1p";
          type dot1p-value;
          description
            "The inner-dot1p marking to be used for all packets associated with the FC, except those with a profile-specific override";
        }
        leaf outer-dot1p {
          if-feature "srl-feat:qos-rewrite-outer-dot1p";
          type dot1p-value;
          description
            "The outer-dot1p marking to be used for all packets associated with the FC, except those with a profile-specific override";
        }
        leaf inner-de {
          if-feature "srl-feat:qos-rewrite-inner-de";
          description
            "Re-marking inner-vlan discard-eligibility bit for the respecitve forwarding-class";
          type boolean;
          default "false";
        }
        leaf outer-de {
          if-feature "srl-feat:qos-rewrite-outer-de";
          description
            "Re-marking outer-vlan discard-eligibility bit for the respecitve forwarding-class";
          type boolean;
          default "false";
        }
      }
    }
  }

  grouping queue-stats-group {
    leaf transmitted-packets {
      type srl_nokia-comm:zero-based-counter64;
      description
        "Number of packets transmitted by the queue, including transit traffic and locally originated traffic";
    }
    leaf transmitted-octets {
      type srl_nokia-comm:zero-based-counter64;
      description
        "Number of octets transmitted by the queue, including transit traffic and locally originated traffic";
    }
    leaf dropped-packets {
      type srl_nokia-comm:zero-based-counter64;
      description
        "Number of packets transmitted by the queue dropped by the queue";
    }
    leaf dropped-octets {
      type srl_nokia-comm:zero-based-counter64;
      description
        "Number of octets transmitted by the queue dropped by the queue";
    }
  }

  grouping fpcx-queue-stats {
    container in-profile {
      description
        "Enter the in-profile context

         Stats for packets marked with In profile transmitted by the queue";
      uses queue-stats-group;
    }
    container in-plus-profile {
      description
        "Enter the in-plus-profile context

         Stats for packets marked with In-Plus profile transmitted by the queue";
      uses queue-stats-group;
    }
    container out-profile {
      description
        "Enter the out-profile context

         Stats for packets marked with Out profile transmitted by the queue";
      uses queue-stats-group;
    }
    container exceed-profile {
      description
        "Enter the exceed-profile context

         Stats for packets marked with Exceed profile transmitted by the queue";
      uses queue-stats-group;
    }
  }

  grouping single-queue-stats {
    leaf transmitted-packets {
      if-feature "not srl-feat:qos-queue-profile-stats";
      type srl_nokia-comm:zero-based-counter64;
      description
        "Number of packets transmitted by the queue, including transit traffic and locally originated traffic";
    }
    leaf transmitted-octets {
      if-feature "not srl-feat:qos-queue-profile-stats";
      type srl_nokia-comm:zero-based-counter64;
      description
        "Number of octets transmitted by the queue.

         Note that on IXR-6/10 this count is based on the ingress packet size including received MPLS labels plus the Ethernet encapsulation that was present at ingress; popped and pushed MPLS labels are not accounted for and neither is the difference, if any, between ingress and egress Ethernet encapsulation size.

         Note that on IXR-6e/10e this count is based on the ingress packet size minus terminated/popped MPLS labels minus the Ethernet encapsulation; pushed MPLS labels are not accounted for and neither is the egress Ethernet encapsulation";
    }
    leaf dropped-packets {
      if-feature "not srl-feat:qos-queue-profile-stats";
      type srl_nokia-comm:zero-based-counter64;
      description
        "Number of packets dropped by the queue.

         On 7250-IXR (Jericho2-based) systems unicast packet drops related to egress port congestion should show up in the VOQ stats. This statistics is an aggregate of VOQ and EGQ drops";
    }
    leaf dropped-octets {
      if-feature "not srl-feat:qos-queue-profile-stats";
      type srl_nokia-comm:zero-based-counter64;
      description
        "Number of octets dropped by the queue.

         On 7250-IXR (Jericho2-based) systems unicast packet drops related to egress port congestion should show up in the VOQ stats.This statistics is an aggregate of VOQ and EGQ drops";
    }
    leaf egq-dropped-packets {
      if-feature "srl-feat:qos-virtual-output-queue";
      type srl_nokia-comm:zero-based-counter64;
      description
        "Number of packets dropped by the queue at egress";
    }
    leaf egq-dropped-octets {
      if-feature "srl-feat:qos-virtual-output-queue";
      type srl_nokia-comm:zero-based-counter64;
      description
        "Number of octets dropped by the queue at egress";
    }
    leaf ecn-marked-packets {
      if-feature "srl-feat:qos-queue-ecn-stats";
      type srl_nokia-comm:zero-based-counter64;
      description
        "Number of packets in which the ECN codepoint was changed from ECT to CE";
    }
    leaf ecn-marked-octets {
      if-feature "srl-feat:qos-queue-ecn-stats";
      type srl_nokia-comm:zero-based-counter64;
      description
        "Number of octets in packets in which the ECN codepoint was changed from ECT to CE";
    }
    leaf trimmed-packets {
      if-feature "srl-feat:qos-packet-trimming-queue";
      type srl_nokia-comm:zero-based-counter64;
      description
        "Number of packets which were trimmed";
    }
    container queue-depth {
      config false;
      leaf last-high-threshold-time {
        description
          "The last time the queue depth exceeded the high-threshold in a rising direction";
        type srl_nokia-comm:date-and-time-delta;
      }
      leaf high-threshold-bytes {
        type uint32;
        units "bytes";
        description
          "The operational hardware value of the high threshold in bytes";
      }
      description
        "Enter the queue-depth context";
    }
    list virtual-output-queue {
      if-feature "srl-feat:qos-virtual-output-queue";
      description
        "List of virtual output queues that can send traffic to this egress queue. The list always has one entry for each IMM slot in the chassis, even if one or more slots are empty";
      key "slot";
      leaf slot {
        type uint8 {
          range "1..16";
        }
        description
          "The slot identifier for the virtual output queue";
      }
      container queue-depth {
        config false;
        leaf last-high-threshold-time {
          description
            "The last time the depth of either VOQ associated with this slot exceeded the high-threshold in a rising direction";
          type srl_nokia-comm:date-and-time-delta;
        }
        leaf high-threshold-bytes {
          type uint32;
          units "bytes";
          description
            "The operational hardware value of the high threshold in bytes";
        }
        description
          "Enter the queue-depth context";
      }
      container low-drop-probability {
        description
          "Enter the low-drop-probability context

           The unicast statistics from the VOQ to the egress queue that were classified as low drop-probability. This reads 0 when the IMM associated with the VOQ is not inserted and it resets to 0 whenever the IMM associated with the VOQ is removed";
        uses queue-stats-group;
      }
      container medium-drop-probability {
        description
          "Enter the medium-drop-probability context

           The unicast statistics from the VOQ to the egress queue that were classified as medium drop-probability. This reads 0 when the IMM associated with the VOQ is not inserted and it resets to 0 whenever the IMM associated with the VOQ is removed";
        uses queue-stats-group;
      }
      container high-drop-probability {
        description
          "Enter the high-drop-probability context

           The unicast statistics unicast packets transmitted from the VOQ to the egress queue that were classified as high drop-probability. This reads 0 when the IMM associated with the VOQ is not inserted and it resets to 0 whenever the IMM associated with the VOQ is removed";
        uses queue-stats-group;
      }
    }
  }

  uses qos-top;

  augment "/srl_nokia-system:system/srl_nokia-system:control-plane-traffic/srl_nokia-system:output" {
    container qos {
      description
        "Enter the qos context

         Parameters describing QoS handling of system generated traffic";
      leaf management-protocols-dscp {
        if-feature "srl-feat:qos-management-protocols-dscp";
        description
          "Defines dscp value the system generated traffic by management-protocols should be marked with";
        type srl_nokia-comm:dscp;
        default "32";
      }
    }
  }
}
