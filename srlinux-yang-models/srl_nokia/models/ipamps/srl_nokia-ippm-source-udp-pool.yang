module srl_nokia-ippm-source-udp-pool {
  yang-version 1.1;
  namespace "urn:srl_nokia/ippm-sourceudp--pool";
  prefix srl_nokia-ippm-source-udp-pool;

  import srl_nokia-common {
    prefix srl_nokia-comm;
  }
  import srl_nokia-features {
    prefix srl_nokia-feat;
  }
  import srl_nokia-oam {
    prefix srl_nokia-oam;
  }

  organization
    "Nokia";
  contact
    "Nokia SR Linux Support
     Web: <http://www.nokia.com>";
  description
    "This module contains configuration and state data for the IP PM reserved source UDP pool.  This pool is available to multiple IP PM
     features.  The ports must be allocated to a function prior to that port being configurable under a specific function.";

  revision 2023-10-31 {
    description
      "SRLinux 23.10.1";
  }

  grouping source-udp-allocation-configuration {
    container source-udp-port-pools {
      description
        "The source-udp-port-pools allocation";
      list port {
        key "port-number";
        description
          "The UDP port list instance";
        leaf port-number {
          type srl_nokia-comm:port-number {
            range "64374..64383";
          }
          description
            "IPPM source UDP port pools port number";
        }
        leaf application-assignment {
          type enumeration {
            enum oam-pm-ip {
              value 1;
              if-feature "srl_nokia-feat:oam-pm-ip";
            }
            enum link-measurement {
              value 2;
              if-feature "srl_nokia-feat:link-measurement";
            }
          }
          description
            "Optionally assign an available reserved UDP port to a specific IPPM application";
        }
      }
    }
  }

  augment "/srl_nokia-oam:oam" {
    if-feature "srl_nokia-feat:link-measurement or srl_nokia-feat:oam-pm-ip";
    container ippm {
      uses source-udp-allocation-configuration;
    }
  }
}
