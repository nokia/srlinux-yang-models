module srl_nokia-link-measurement {
  yang-version 1.1;
  namespace "urn:srl_nokia/link-measurement";
  prefix srl_nokia-link-measurement;

  import srl_nokia-common {
    prefix srl_nokia-comm;
  }
  import srl_nokia-extensions {
    prefix srl_nokia-ext;
  }
  import srl_nokia-features {
    prefix srl_nokia-feat;
  }
  import srl_nokia-interfaces {
    prefix srl_nokia-if;
  }
  import srl_nokia-ippm-source-udp-pool {
    prefix srl_nokia-source-udp;
  }
  import srl_nokia-network-instance {
    prefix srl_nokia-net-inst;
  }
  import srl_nokia-oam {
    prefix srl_nokia-oam;
  }
  import srl_nokia-qos {
    prefix srl_nokia-qos;
  }
  import srl_nokia-traffic-engineering {
    prefix srl_nokia-traffic-eng;
  }

  organization
    "Nokia";
  contact
    "Nokia SR Linux Support
     Web: <http://www.nokia.com>";
  description
    "This module contains configuration and state data definitions for the dynamic link measurement
     template and the subinterface configuration and state";

  revision 2023-10-31 {
    description
      "SRLinux 23.10.1";
  }

  grouping link-measurement-template-configuration {
    list measurement-template {
      key "template-name";
      description
        "The measurement-template list instance";
      leaf template-name {
        type srl_nokia-comm:name;
        description
          "Measurement template name

           The template may be modified without having to change the admin state to 'disable'.  Any
           tests referencing the template that is changed on the fly will be terminated and restarted.";
      }
      leaf admin-state {
        type srl_nokia-comm:admin-state;
        default "disable";
        description
          "Administrative state of the measurement template

           This value can be changed while a subinterface is referencing the template.  However, the value
           'disable' will prevent any link measurement test for a subinterface referencing the template
           from becoming operational.";
      }
      leaf description {
        type srl_nokia-comm:description;
        description
          "Text description for the template";
      }
      leaf unidirectional-measurement {
        type enumeration {
          enum derived {
            value 1;
          }
          enum actual {
            value 2;
          }
        }
        default "derived";
        description
          "Method used to compute the unidirectional delay value

           The value 'derived' computes unidirectional measurements using roundtrip divide by 2.  This method
           could be considered in environments without Time of Day (ToD) clock synchronization.  The value 'actual' uses the
           traditional (T2-T1) computation for unidirectional delay.  ";
      }
      leaf delay {
        type enumeration {
          enum minimum {
            value 1;
          }
          enum maximum {
            value 2;
          }
          enum average {
            value 3;
          }
        }
        default "minimum";
        description
          "Delay measurement statistic type";
      }
      leaf interval {
        type uint32 {
          range "1..10";
        }
        units "seconds";
        default "1";
        description
          "Interval between test packet transmissions";
      }
      leaf last-reported-delay-hold {
        type uint32 {
          range "0..86400";
        }
        units "seconds";
        default "86400";
        description
          "Time to wait to flush the last reported delay

           This command configures the timer that specifies the wait time before the last reported
           delay measurement is flushed after a link measurement test enters the operationally
           down state.

           The aging timer delays the flushing of the last reported delay metric to the routing
           engine. This timer starts a countdown to zero when an administrative function causes
           the operational state of the test on that specific interface to transition from 'up' to 'down'.

           If the timer expires before the operational state transitions to 'up', the previously reported
           value is flushed. The Delay Measurement Last Reported indicates 'Cleared'. The timestamp indicates
           the time of the clear event. The Triggered By indicates 'Expired'.

           If the administrative state recovers to operationally 'up' before the expiration of the timer,
           the previous reported value is not flushed.

           The aging timer does not apply to failure conditions that do not affect the administrative
           state of the interface, for example interface failure or routing changes.

           A value '0' means the last reported delay is flushed immediately without delay.";
      }
      leaf reporting {
        type boolean;
        default "true";
        description
          "Report behavior for values reaching the configured threshold

           A value 'true' means the routing engine will be informed of the threshold event and the delay measurement.  A
           value 'false' means a new value is not passed to the routing engine even if a threshold event has occurred.";
      }
      container stamp {
        description
          "The STAMP protocol configuration";
        leaf destination-udp-port {
          type srl_nokia-comm:port-number;
          default "862";
          must '. > 0' {
            error-message "Destination UDP port must not be 0";
          }
          description
            "Destination UDP port used by link measurement test";
        }
        leaf source-udp-port {
          type union {
            type srl_nokia-comm:port-number {
              range "64374..64383";
            }
            type enumeration {
              enum auto {
                value 1;
              }
            }
          }
          default "auto";
          must "/srl_nokia-oam:oam/srl_nokia-source-udp:ippm/srl_nokia-source-udp:source-udp-port-pools/srl_nokia-source-udp:port[srl_nokia-source-udp:port-number = current ()]/srl_nokia-source-udp:application-assignment = 'link-measurement'" {
            error-message "The source UDP port must be assign to the link-measurement application before it can be configured under this leaf";
          }
          description
            "Fixed source UDP port for link measurement tests

             This range of Source UDP ports is a common pool that must be administratively assigned to the applications
             that share this pool.  Performance monitoring IP tests and link-measurement test can assign these UDP ports to their
             application.  Once a UDP port in this range is assigned to one application it cannot be used by the other application.

             Allocation of these UDP ports can be found at srl_nokia-udp-source-pool.yang model (path oam ippm source-udp-pools).";
        }
        leaf timestamp-format {
          type enumeration {
            enum ntp {
              value 1;
            }
            enum ptp {
              value 2;
            }
          }
          default "ntp";
          description
            "Format of the timestamp used in STAMP PDU

             This is used to encode the time of day information in the PDU.
             The value 'ntp' uses the 32seconds.32fractional seconds UTC timestamp format.
             Tha value 'ptp' uses the 32seconds.32nanoseconds UTC timestamp format.";
        }
        leaf pad-tlv-size {
          type uint32 {
            range "4..9714";
          }
          units "bytes";
          description
            "Optional PAD TLV size";
        }
        container return-path {
          description
            "The STAMP return-path TLV choice";
          choice tlv {
            case link {
              leaf link {
                type boolean;
                default "false";
                description
                  "Optional Return Path sub-TLV specifying link";
              }
            }
          }
        }
        leaf allow-ipv6-udp-checksum-zero {
          type boolean;
          default "false";
          description
            "Process IPv6 packets with UDP check sum zero for STAMP packets";
        }
        leaf dscp {
          type srl_nokia-comm:dscp;
          default "CS6";
          description
            "DSCP used in IP header of the STAMP PDU";
        }
        leaf allow-egress-remark-dscp {
          type boolean;
          default "false";
          description
            "Allow overwrite of DSCP value by the egress QoS policy";
        }
        uses srl_nokia-qos:qos-forwarding-class-leaf-forwarding-class {
          if-feature "not srl_nokia-feat:platform-7220-d1";
        }
        leaf profile {
          if-feature "not srl_nokia-feat:platform-7220-d1";
          type srl_nokia-comm:rewrite-profile;
          default "in";
          description
            "QoS profile for packet treatment in the local node";
        }
        leaf ttl {
          type uint32 {
            range "1..255";
          }
          default "1";
          description
            "Time to live value used in the IP header of the STAMP test packet";
        }
        container ipv6-destination-discovery {
          description
            "The ipv6-destination-discovery configuration options

             This uses a ping with a destination address of the well-known multicast address ff02::2 (all routers) to solicit
             a response from the peer.  The source address of the peer's response will be used as the IPv6 destination address
             for the test.  This discovery method must only be used when there is a single IPv6 router reachable out this interface.";
          leaf admin-state {
            type srl_nokia-comm:admin-state;
            default "disable";
            description
              "Administrative state of IPv6 auto destination discovery";
          }
          leaf discovery-timer {
            type uint32 {
              range "1..1800";
            }
            units "seconds";
            default "60";
            description
              "Maximum time to remain in the discovery phase

               The discovery phase will end when the IPv6 peer is discovered or this timer expires.";
          }
          leaf discovery-interval {
            type uint32 {
              range "1..10";
            }
            units "seconds";
            default "10";
            description
              "Transmission frequency for discovery packets while in discovery mode";
          }
          leaf update-interval {
            type uint32 {
              range "0..3600";
            }
            units "seconds";
            default "600";
            description
              "Transmission frequency to maintain the peer address

               Once a peer is discovered further discovery packets will be sent at this interval.  A value '0'
               disables the continued validation and updating of changed peer information.  If the discovery-timer
               counts down to zero and a peer has not been discovered and the value of this leaf is '0'.  The peer
               will not be discovered and the test will need an admin-state change to restart the discovery process.";
          }
        }
        container aggregate-sample-window {
          description
            "The aggregate-sample-window configuration options

             The aggregate sample window is a collection of sample windows.  It executes threshold comparisons
             based on the results passed from each sample window.";
          leaf multiplier {
            type uint32 {
              range "1..12";
            }
            default "12";
            description
              "Number of sample windows in the aggregate sample window";
          }
          leaf window-integrity {
            type uint32 {
              range "1..100";
            }
            units "percent";
            description
              "Sample percentage required for window integrity report

               The configured percentage translates to a required sample window count that must
               be included in the aggregate sample window.

               The number of samples is computed as follows:
               (window-integrity (%)) x (((aggregate-sample-window length (s)) / (sample-window length (s)))

               If the number of samples in the aggregate sample window is equal to or greater than the computed
               number of required samples, the sample window has integrity and the aggregate sample window result
               is compared to the configured sample window thresholds.

               If the count is less than the computed number of required samples, the aggregate sample window
               does not have integrity and the value is not considered as representative. In this case the
               aggregate sample window results are not compared to the configured sample window thresholds.

               If this option leaf is not configured, integrity checking is disabled and all results are compared
               to the configured thresholds.";
          }
          container threshold {
            description
              "Threshold configuration options for aggregate sample window";
            leaf relative {
              type uint32 {
                range "1..100";
              }
              units "percent";
              description
                "Relative delta for measurement reporting, percentage of change";
            }
            leaf absolute {
              type uint32 {
                range "1..100000";
              }
              units "microseconds";
              description
                "Absolute delta for delay measurement reporting";
            }
          }
        }
        container sample-window {
          description
            "The sample-window configuration options

             The  sample window is a collection of individual test packet results.  It executes threshold comparisons
             using the results in the sample window.";
          leaf multiplier {
            type uint32 {
              range "1..900";
            }
            default "10";
            description
              "Multiplier of interval used for sample window length";
          }
          leaf window-integrity {
            type uint32 {
              range "1..100";
            }
            units "percent";
            description
              "Sample percentage required for window integrity report

               This command configures the percentage value that is used to determine whether the sample window
               has enough samples to be considered representative for that window (integrity), by comparing the
               number of samples received from the sample window to the percentage configured.

               The configured percentage considers the interval of probes and the length of the sample window to
               determine the number of packets required in the sample:
               (window-integrity (%)) x ((sample-window length (s)) / pps per test (interval))

               If the count is less than the computed number of required samples, the sample window does not have
               integrity and the sample window results are not compared to configured sample window thresholds.

               If the count is equal to or greater than the computed number of required samples, the sample window
               has integrity and the aggregate sample window result is compared to the configured sample window thresholds.

               If this option leaf is not configured, integrity checking is disabled and all results are compared
               to the configured thresholds.";
          }
          container threshold {
            description
              "Threshold configuration options for sample window";
            leaf relative {
              type uint32 {
                range "1..500";
              }
              units "percent";
              description
                "Relative delta for measurement reporting, percentage of change";
            }
            leaf absolute {
              type uint32 {
                range "1..100000";
              }
              units "microseconds";
              description
                "Absolute delta for delay measurement reporting";
            }
          }
        }
      }
    }
  }

  grouping interface-configuration {
    container dynamic {
      container link-measurement {
        description
          "The link-measurement dynamic measurement configuration for the interface";
        presence "Configuration of delay interface attributes";
        must "(current()/../../../../../srl_nokia-net-inst:type = 'srl_nokia-net-inst:default')" {
          error-message "Link measurement is only supported within the default network instance";
        }
        must "starts-with(../../../interface-name,'eth') or starts-with(../../../interface-name,'lag')" {
          error-message "Link measurement is supported for Ethernet interfaces only";
        }
        must 'not(/srl_nokia-if:interface[srl_nokia-if:name=current()]/srl_nokia-if:breakout-mode)' {
          error-message "Breakout interfaces are not supported";
        }
        leaf measurement-template {
          type leafref {
            path "/srl_nokia-oam:oam/srl_nokia-link-measurement:link-measurement/srl_nokia-link-measurement:measurement-template/srl_nokia-link-measurement:template-name";
          }
          description
            "The link measurement template assigned to the interface";
        }
        container stamp {
          description
            "The STAMP IP protocol configuration";
          container ipv4 {
            description
              "The ipv4 address and administrative configuration";
            leaf admin-state {
              type srl_nokia-comm:admin-state;
              must "../../ipv6/admin-state = 'disable'" {
                error-message "IPv4 STAMP link measurement testing cannot be enabled when IPv6 STAMP link measurement testing is enabled";
              }
              default "disable";
              description
                "Administrative state of IPv4 STAMP packets";
            }
            leaf destination-ip {
              type srl_nokia-comm:ipv4-address-excluding-all-zero;
              description
                "STAMP measurement packet destination IPv4 address

                 When the destination address is not specified the system resolves the peer address when
                 the prefix-length of the primary local interface has a length of 30 or 31.  When the destination
                 address is not specified and the prefix length is shorter than 30 the peer address cannot be
                 determined and the invalid destination address will result.";
            }
            leaf source-ip {
              type srl_nokia-comm:ipv4-address-excluding-all-zero;
              description
                "STAMP measurement packets source IPv4 address

                 The primary local interface address will be used when this leaf is not configured.";
            }
          }
          container ipv6 {
            description
              "The ipv6 address and administrative configuration";
            leaf admin-state {
              type srl_nokia-comm:admin-state;
              default "disable";
              must "../../ipv4/admin-state = 'disable'" {
                error-message "IPv6 STAMP link measurement testing cannot be enabled when IPv4 STAMP link measurement testing is enabled";
              }
              description
                "Administrative state of IPv6 STAMP packets";
            }
            leaf destination-ip {
              type srl_nokia-comm:ipv6-address-excluding-all-zero;
              description
                "STAMP measurement packet destination IPv6 address

                 When the destination address is not specified the system relies on ipv6-destination-discovery
                 to resolves the address. If ipv6-destination-discovery is disabled or the discovery fails an
                 invalid destination address will result.";
            }
            leaf source-ip {
              type srl_nokia-comm:ipv6-address-excluding-all-zero;
              description
                "STAMP measurement packets source IPv6 address

                 The link-local interface address will be used when this leaf is not configured.";
            }
          }
        }
      }
    }
  }

  grouping link-measurement-interface-state {
    list interface {
      config false;
      key "name";
      leaf name {
        type leafref {
          path "/srl_nokia-if:interface/srl_nokia-if:name";
        }
        description
          "Reference to an interface";
      }
      list subinterface {
        key "index";
        leaf index {
          type leafref {
            path "/srl_nokia-if:interface/srl_nokia-if:subinterface/srl_nokia-if:index";
          }
          description
            "Reference to a subinterface";
        }
        leaf oper-state {
          type srl_nokia-comm:oper-state;
          description
            "Indicates the operational state of link measurement on this interface";
        }
        list operational-failure {
          key "condition";
          leaf condition {
            type enumeration {
              enum no-protocol {
                value 1;
              }
              enum template-admin-down {
                value 2;
              }
              enum udp-port-unavailable {
                value 3;
              }
              enum internal-error {
                value 4;
              }
            }
            description
              "Indicates the reason(s) why this interface's link measurement is operationally disabled";
          }
        }
        leaf detectable-transmit-error {
          type enumeration {
            enum none {
              value 1;
            }
            enum interface-down {
              value 2;
            }
            enum unexpected-error {
              value 3;
            }
            enum no-route {
              value 4;
            }
            enum source-ip-not-local {
              value 5;
            }
            enum invalid-dest-ip {
              value 6;
            }
            enum invalid-interface-type {
              value 7;
            }
            enum source-destination-same {
              value 8;
            }
          }
          description
            "Indicates a detectable error preventing STAMP test packet transmission";
        }
        leaf operational-source-address {
          type srl_nokia-comm:ip-address;
          description
            "Indicates the source IP address from which STAMP packets are being sent";
        }
        leaf source-ip-auto-assigned {
          type boolean;
          description
            "Indicates whether the oper-source-address was system assigned (true) or configured (false)";
        }
        leaf operational-destination-address {
          type srl_nokia-comm:ip-address;
          description
            "Indicates the destination IP address to which STAMP packets are being sent";
        }
        leaf destination-ip-auto-assigned {
          type boolean;
          description
            "Indicates whether the oper-destination-address was assigned (true) or configured (false)";
        }
        leaf in-use-source-udp-port {
          type uint32;
          description
            "Indicates the source UDP port in use for the session";
        }
        leaf in-use-destination-udp-port {
          type uint32;
          description
            "Indicates the destination UDP port in use for the session";
        }
        leaf stamp-session-sender-id {
          type uint32;
          description
            "Indicates the autogenerated Session Sender ID (SSID) assigned to the session";
        }
        leaf reporting {
          type boolean;
          description
            "Indicates whether the interface is currently reporting to the routing engine";
        }
        leaf last-reported-delay {
          type union {
            type int32 {
              range "0..2147483647";
            }
            type enumeration {
              enum none {
                value -1;
              }
            }
          }
          units "microseconds";
          description
            "Indicates the last delay measurement reported to the routing engine";
        }
        leaf report-timestamp {
          type srl_nokia-comm:date-and-time;
          description
            "When ./last-reported-delay > 0, report-timestamp holds the time at which
             ./last-reported-delay was reported to the routing engine.

             When ./last-reported-delay = 0, report-timestamp holds the time at which
             ./last-reported-delay was cleared (because its aging timer expired).

             When ./last-reported-delay = 'none', report-timestamp holds '1970-Jan-01 00:00:00.0'
             UTC as a placeholder representing a delay has not yet been reported to the routing
             engine.";
        }
        leaf report-triggered-by {
          type enumeration {
            enum none {
              value 1;
            }
            enum sample-threshold-absolute {
              value 2;
            }
            enum sample-threshold-relative {
              value 3;
            }
            enum aggregate-threshold-absolute {
              value 4;
            }
            enum aggregate-threshold-relative {
              value 5;
            }
            enum expired {
              value 6;
            }
            enum reporting-disabled {
              value 7;
            }
          }
          description
            "Indicates the reason for the report to the routing engine";
        }
        leaf aggregate-newest-index {
          type srl_nokia-comm:counter32;
          description
            "Indicates the index of the newest aggregate sample window for this subinterface";
        }
        leaf sample-newest-index {
          type srl_nokia-comm:counter32;
          description
            "Indicates the index of the newest sample window for this subinterface";
        }
        container statistics {
          description
            "The aggregate sample window and sample window statistics";
          container aggregate-sample-window {
            description
              "The aggregate sample window statistics";
            list index {
              key "index";
              description
                "The index list instance";
              leaf index {
                type srl_nokia-comm:counter32;
                description
                  "Specifies an index used to differentiate aggregate sample windows on the same interface over time";
              }
              leaf end-timestamp-utc {
                type srl_nokia-comm:date-and-time;
                description
                  "Indicates the time (UTC) at which this aggregate sample window closed";
              }
              leaf window-state {
                type enumeration {
                  enum completed {
                    value 1;
                  }
                  enum in-progress {
                    value 2;
                  }
                  enum sw-reported {
                    value 3;
                  }
                  enum asw-reported {
                    value 4;
                  }
                  enum terminated {
                    value 5;
                  }
                }
                description
                  "Indicates the state of this aggregate sample window

                   completed    - window ran to completion
                   in-progress  - window currently active and collecting results
                   sw-reported  - sample window threshold event caused a report aggregated sample window restarted
                   asw-reported - aggregate sample window threshold caused a report
                   terminated   - window terminated prior to completion";
              }
              leaf sample-window-count {
                type srl_nokia-comm:zero-based-counter32;
                description
                  "Indicates the number of sample windows that have completed and met their integrity
                   value within this aggregate sample window";
              }
              leaf minimum {
                type uint32;
                units "microseconds";
                description
                  "Indicates the minimum delay measurement reported to the aggregate sample window by the
                   sample windows that have been open during its lifetime";
              }
              leaf maximum {
                type uint32;
                units "microseconds";
                description
                  "Indicates the maximum delay measurement reported to the aggregate sample window by the
                   sample windows that have been open during its lifetime";
              }
              leaf average {
                type uint32;
                units "microseconds";
                description
                  "Indicates the average delay measurement reported to the aggregate sample window by the
                   sample windows that have been open during its lifetime";
              }
              leaf result {
                type uint32;
                units "microseconds";
                description
                  "The delay that was being evaluated for report when this aggregate sample window was open";
              }
              leaf integrity {
                type boolean;
                description
                  "Indicates whether a sufficient percentage of this aggregate sample window's child
                   sample windows met their configured integrity value";
              }
            }
          }
          container sample-window {
            description
              "The sample window statistics";
            list index {
              key "index";
              description
                "The index list instance";
              leaf index {
                type srl_nokia-comm:counter32;
                description
                  "Specifies an index used to differentiate sample windows on the same interface over time";
              }
              leaf end-timestamp-utc {
                type srl_nokia-comm:date-and-time;
                description
                  "Indicates the time (UTC) at which this sample window closed";
              }
              leaf window-state {
                type enumeration {
                  enum completed {
                    value 1;
                  }
                  enum in-progress {
                    value 2;
                  }
                  enum sw-reported {
                    value 3;
                  }
                  enum terminated {
                    value 4;
                  }
                }
                description
                  "Indicates the state of this sample window

                   completed    - window ran to completion
                   in-progress  - window currently active and collecting results
                   sw-reported  - sample window threshold event caused a report
                   terminated   - window terminated prior to completion";
              }
              leaf transmitted-packets {
                type srl_nokia-comm:zero-based-counter32;
                description
                  "Indicates the number of STAMP packets that have been sent for this sample window";
              }
              leaf received-packets {
                type srl_nokia-comm:zero-based-counter32;
                description
                  "Indicates the number of STAMP packets that have been received for this sample window";
              }
              leaf minimum {
                type uint32;
                units "microseconds";
                description
                  "Indicates the minimum of the series of delay measurements that occurred during this sample window";
              }
              leaf maximum {
                type uint32;
                units "microseconds";
                description
                  "Indicates the maximum of the series of delay measurements that occurred during this sample window";
              }
              leaf average {
                type uint32;
                units "microseconds";
                description
                  "Indicates the average of the series of delay measurements that occurred during this sample window";
              }
              leaf result {
                type uint32;
                units "microseconds";
                description
                  "The delay that was being evaluated for report when this sample window was open";
              }
              leaf integrity {
                type boolean;
                description
                  "Indicates whether the percentage of successful request-response pairs of test packets met the configured integrity value";
              }
              leaf error-count {
                type srl_nokia-comm:zero-based-counter32;
                description
                  "Indicates the number of erroneous delay measurements that occurred in this sample window";
              }
              leaf stamp-unrecognized-flag-count {
                type srl_nokia-comm:zero-based-counter32;
                description
                  "Indicates the count of packets in this sample window with the U (Unrecognized) bit set

                   This is a bit in the flags field of the STAMP TLV.";
              }
              leaf stamp-malformed-flag-count {
                type srl_nokia-comm:zero-based-counter32;
                description
                  "Indicates the count of packets in this sample window with the M (Malformed) bit set

                   This is a bit in the flags field of the STAMP TLV.";
              }
              leaf zero-or-negative-delay-count {
                type srl_nokia-comm:zero-based-counter32;
                description
                  "Indicates the count of packets that have a zero or negative computed delay for this sample window";
              }
              leaf duplicate-packet-count {
                type srl_nokia-comm:zero-based-counter32;
                description
                  "Indicates the count of duplicate packets that have arrived during this sample window";
              }
            }
          }
        }
      }
    }
  }

  augment "/srl_nokia-oam:oam" {
    if-feature "srl_nokia-feat:link-measurement";
    container link-measurement {
      uses link-measurement-template-configuration;
      uses link-measurement-interface-state;
    }
  }

  augment "/srl_nokia-net-inst:network-instance/srl_nokia-traffic-eng:traffic-engineering/srl_nokia-traffic-eng:interface/srl_nokia-traffic-eng:delay" {
    if-feature "srl_nokia-feat:oam";
    if-feature "srl_nokia-feat:link-measurement";
    uses interface-configuration;
  }
}
