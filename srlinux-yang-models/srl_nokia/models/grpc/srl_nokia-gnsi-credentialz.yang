module srl_nokia-gnsi-credentialz {
  yang-version 1.1;
  namespace "urn:nokia.com:srlinux:linux:gnsi-credentialz";
  prefix srl-gnsi-credentialz;

  import srl_nokia-common {
    prefix srl-comm;
  }
  import srl_nokia-system {
    prefix srl-system;
  }
  import srl_nokia-ssh {
    prefix srl-ssh;
  }
  import srl_nokia-features {
    prefix srl-feat;
  }

  organization
    "Nokia";
  contact
    "Nokia SR Linux Support
     Web: <http://www.nokia.com>";
  description
    "This module defines configuration and operational state data related to the Credentialz service within gNSI.";

  revision 2026-07-31 {
    description
      "SRLinux 26.7.1";
  }
  revision 2024-03-31 {
    description
      "SRLinux 24.3.1";
  }

  grouping artifact-common {
    description
      "Grouping of common information used between artifacts";
    leaf version {
      description
        "The version string as provided by the gNSI client at the time of uploading the artifact

         The maps to the version field within a Entity message in the Credentialz protobuf.";
      type string;
    }
    leaf created-on {
      description
        "The created on timestamp as provided by the gNSI client at the time of uploading the artifact

         The maps to the created_on field within a Entity message in the Credentialz protobuf.";
      type srl-comm:date-and-time-delta;
    }
  }

  grouping credentialz-top {
    description
      "Grouping of Credentialz state paths";
    container credentialz {
      config false;
      description
        "Enter the credentialz context

         Information relating to the active host keys and certificates as provided via Credentialz

         State is provided by the gNSI Credentialz service, and can be changed using the gNSI.Credentialz.RotateHostParameters RPC";
      container trusted-user-ca-keys {
        description
          "Enter the trusted-user-ca-keys context

           State relating to the Certificate Authorities provided via Credentialz.";
        uses artifact-common;
      }
      container host-certificate {
        description
          "Enter the host-certificate context

           State relating to the Host Certificates provided via Credentialz";
        uses artifact-common;
      }
      container host-key {
        description
          "Enter the host-key context

           State relating to the Host Keys provided via Credentialz";
        uses artifact-common;
      }
    }
  }

  grouping credentialz-aaa-top {
    description
      "Grouping of Credentialz AAA state paths";
    container credentialz {
      config false;
      description
        "Enter the credentialz context

         Information relating to the active user credentials as provided via Credentialz

         State is provided by the gNSI Credentialz service, and can be changed using the gNSI.Credentialz.RotateAccountCredentials RPC";
      container password {
        description
          "Enter the password context

           State relating to the Password provided via Credentialz.";
        uses artifact-common;
      }
      container authorized-keys {
        description
          "Enter the authorized-keys context

           State relating to the Authorized Keys provided via Credentialz";
        uses artifact-common;
      }
      container authorized-principals {
        description
          "Enter the authorized-principals context

           State relating to the Authorized Principals provided via Credentialz";
        uses artifact-common;
      }
    }
  }

  grouping counters-top {
    description
      "A collection of counters that were collected while evaluating access to the SSH server.";
    container counters {
      config false;
      description
        "Enter the counters context

         A collection of counters that were collected by the SSH server during the SSH authentication process.";
      leaf access-rejects {
        type uint64;
        description
          "The total number of times the SSH server denied access to the server.";
      }
      leaf last-access-reject {
        type srl-comm:date-and-time-delta;
        description
          "A timestamp of the last time the SSH server denied access to the server.";
      }
      leaf access-accepts {
        type uint64;
        description
          "The total number of times the SSH allowed access to the server.";
      }
      leaf last-access-accept {
        type srl-comm:date-and-time-delta;
        description
          "A timestamp of the last time the SSH allowed access to the server.";
      }
    }
  }

  augment "/srl-system:system/srl-ssh:ssh-server" {
    if-feature "srl-feat:gnsi-credentialz";
    uses credentialz-top;
  }

  augment "/srl-system:system/srl-ssh:ssh-server" {
    if-feature "srl-feat:gnsi-credentialz";
    uses counters-top;
  }
}
