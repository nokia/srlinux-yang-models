module srl_nokia-tools-gnoi {
  yang-version 1.1;
  namespace "urn:nokia.com:srlinux:grpc:tools-gnoi";
  prefix srl_nokia-tools-gnoi;

  import srl_nokia-tools-gnoi-healthz {
    prefix srl-tools-gnoi-healthz;
  }

  organization
    "Nokia";
  contact
    "Nokia SR Linux Support
     Web: <http://www.nokia.com>";
  description
    "Model for managing gNOI";

  revision 2026-07-31 {
    description
      "SRLinux 26.7.1";
  }
  revision 2026-03-31 {
    description
      "SRLinux 26.3.1";
  }
  revision 2025-10-31 {
    description
      "SRLinux 25.10.1";
  }
  revision 2024-03-31 {
    description
      "SRLinux 24.3.1";
  }

  grouping tools-gnoi-top {
    container gnoi {
      presence "Configure tools gNOI";
      description
        "Top-level container for operational commands related to gNOI";
      uses srl-tools-gnoi-healthz:tools-gnoi-healthz-top;
    }
  }
}
