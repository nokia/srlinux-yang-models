module srl_nokia-tools-gnsi-pathz {
  yang-version 1.1;
  namespace "urn:nokia.com:srlinux:aaa:tools-gnsi-pathz";
  prefix srl-tools-gnsi-pathz;

  import srl_nokia-tools-system {
    prefix srl-tools-system;
  }

  // import srl_nokia-tools-configuration {
  //   prefix srl-tools-configuration;
  // }

  import srl_nokia-extensions {
    prefix srl-ext;
  }
  import srl_nokia-features {
    prefix srl-feat;
  }

  organization
    "Nokia";
  contact
    "Nokia SR Linux Support
     Web: <http://www.nokia.com>";
  description
    "This module defines operational commands related to Pathz.";

  revision 2024-07-31 {
    description
      "SRLinux 24.7.1";
  }

  grouping pathz-top {
    container pathz-policy {
      presence "Operational commands relating to Pathz gRPC policies";
      srl-ext:first-released "24.7.1";
      description
        "Top-level container for operational commands relating to Pathz gRPC policies";
      leaf remove {
        type empty;
        description
          "Remove Pathz authorization policy from the system";
      }
      leaf clear {
        type empty;
        description
          "Clear Pathz authorization policy counters";
      }
    }
  }

  // augment "/srl-tools-system:system/srl-tools-configuration:configuration" {
  //   if-feature "srl-feat:gnsi-pathz";
  //   uses pathz-top;
  // }
}
