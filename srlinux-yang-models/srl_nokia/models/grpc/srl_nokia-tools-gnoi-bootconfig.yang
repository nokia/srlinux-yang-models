module srl_nokia-tools-gnoi-bootconfig {
  yang-version 1.1;
  namespace "urn:nokia.com:srlinux:grpc:tools-gnoi-bootconfig";
  prefix srl_nokia-tools-gnoi-bootconfig;

  organization
    "Nokia";
  contact
    "Nokia SR Linux Support
     Web: <http://www.nokia.com>";
  description
    "Model for managing gNOI BootConfig";

  revision 2026-07-31 {
    description
      "SRLinux 26.7.1";
  }
  revision 2026-03-31 {
    description
      "SRLinux 26.3.1";
  }
  revision 2025-10-31 {
    description
      "SRLinux 25.10.1";
  }

  grouping tools-gnoi-bootconfig-top {
    container bootconfig {
      description
        "Enter the bootconfig context

         gNOI BootConfig tools commands";
      leaf remove {
        description
          "Remove all BootConfig data from the system";
        type empty;
      }
      container set {
        description
          "Enter the set context

           Set BootConfig data";
        container boot-config {
          presence "The boot config data to set";
          description
            "The boot config data to set";
          leaf vendor-config {
            type string;
            description
              "The vendor specific boot configuration data";
          }
          leaf oc-config {
            type string;
            description
              "The openconfig specific boot configuration data";
          }
          leaf dynamic-vendor-config {
            type string;
            description
              "The dynamic vendor specific boot configuration data";
          }
          leaf dynamic-oc-config {
            type string;
            description
              "The dynamic openconfig specific boot configuration data";
          }
        }
      }
      container get {
        description
          "Enter the get context

           Get BootConfig data";
        container boot-config {
          presence "The boot config data to get";
          description
            "The boot config data to get";
          leaf vendor-config {
            type empty;
            description
              "The vendor specific boot configuration data";
          }
          leaf oc-config {
            type empty;
            description
              "The openconfig specific boot configuration data";
          }
          leaf dynamic-vendor-config {
            type empty;
            description
              "The dynamic vendor specific boot configuration data";
          }
          leaf dynamic-oc-config {
            type empty;
            description
              "The dynamic openconfig specific boot configuration data";
          }
        }
      }
    }
  }
}
