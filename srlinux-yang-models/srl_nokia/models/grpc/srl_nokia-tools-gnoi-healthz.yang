module srl_nokia-tools-gnoi-healthz {
  yang-version 1.1;
  namespace "urn:nokia.com:srlinux:grpc:tools-gnoi-healthz";
  prefix srl_nokia-tools-gnoi-healthz;

  import srl_nokia-common {
    prefix srl-comm;
  }
  import srl_nokia-features {
    prefix srl-feat;
  }

  organization
    "Nokia";
  contact
    "Nokia SR Linux Support
     Web: <http://www.nokia.com>";
  description
    "Model for managing gNOI Healthz";

  revision 2026-07-31 {
    description
      "SRLinux 26.7.1";
  }
  revision 2025-03-31 {
    description
      "SRLinux 25.3.1";
  }
  revision 2024-03-31 {
    description
      "SRLinux 24.3.1";
  }

  grouping common-tools-clear {
    description
      "Grouping for common component commands";
    leaf clear {
      description
        "Clear healthz events for this component";
      type empty;
    }
  }

  grouping tools-gnoi-healthz-top {
    container healthz {
      description
        "Enter the healthz context

         gNOI Healthz tools commands";
      leaf clear {
        description
          "Clear all healthz events";
        type empty;
      }
      choice component {
        case chassis {
          container chassis {
            description
              "Enter the chassis context

               Chassis component";
            uses common-tools-clear;
          }
        }
        case control {
          container control {
            description
              "Enter the control context

               Control module component";
            leaf slot {
              mandatory true;
              type string {
                pattern 'A|B';
              }
              description
                "Slot identifier for the control module";
            }
            uses common-tools-clear;
          }
        }
        case fabric {
          container fabric {
            description
              "Enter the fabric context

               Fabric module component";
            leaf slot {
              mandatory true;
              type uint8;
              description
                "Numeric identifier for the fabric module";
            }
            uses common-tools-clear;
          }
        }
        case fan-tray {
          container fan-tray {
            description
              "Enter the fan-tray context

               Fan component";
            leaf id {
              mandatory true;
              type uint8;
              description
                "Numeric identifier for the fan module";
            }
            uses common-tools-clear;
          }
        }
        case linecard {
          container linecard {
            description
              "Enter the linecard context

               Line card component

               Clearing a slot component will not clear it's corresponding forwarding-complex components.
               Similarly, clearing a forwarding-complex component will not clear the slot component.";
            leaf slot {
              mandatory true;
              type uint8;
              description
                "Numeric identifier for the line card";
            }
            leaf forwarding-complex {
              if-feature "srl-feat:gnoi-healthz-forwarding-complex";
              description
                "individual ASIC (forwarding-complex) component";
              type enumeration {
                enum 0;
                enum 1 {
                  if-feature "srl-feat:forwarding-complex-1";
                }
              }
            }
            uses common-tools-clear;
          }
        }
        case power-supply {
          container power-supply {
            description
              "Enter the power-supply context

               Power supply component";
            leaf id {
              mandatory true;
              type uint8;
              description
                "Numeric identifier for the power supply module";
            }
            uses common-tools-clear;
          }
        }
        case transceiver {
          container transceiver {
            description
              "Enter the transceiver context

               Transceiver component";
            leaf interface {
              mandatory true;
              type srl-comm:name;
              description
                "Interface name for the transceiver module";
            }
            uses common-tools-clear;
          }
        }
      }
    }
  }
}
