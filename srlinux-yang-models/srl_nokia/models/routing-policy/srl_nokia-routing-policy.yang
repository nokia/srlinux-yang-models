module srl_nokia-routing-policy {
  yang-version 1.1;
  namespace "urn:nokia.com:srlinux:plcy:routing-policy";
  prefix srl_rpol;

  import srl_nokia-common {
    prefix srl_nokia-comm;
  }
  import srl_nokia-extensions {
    prefix srl_nokia-ext;
  }
  import srl_nokia-policy-types {
    prefix srl_nokia-pol-types;
  }
  import srl_nokia-ospf-types {
    prefix srl_nokia-ospf-types;
  }
  import srl_nokia-isis-types {
    prefix srl_nokia-isis-types;
  }
  import srl_nokia-features {
    prefix srl_nokia-feat;
  }
  import srl_nokia-network-instance {
    prefix srl_nokia-netinst;
  }
  import srl_nokia-flexible-algorithms-types {
    prefix srl_nokia-flex-algo-types;
  }
  import srl_nokia-system {
    prefix srl_nokia-system;
  }
  import srl_nokia-protection-policies {
    prefix srl_nokia-prot-pol;
  }
  import srl_nokia-srv6 {
    prefix srl_nokia-srv6;
  }

  organization
    "Nokia";
  contact
    "Nokia SR Linux Support
     Web: <http://www.nokia.com>";
  description
    "YANG model for route policies. It supports widely used constructs for managing how routes are imported, exported, and modified across different routing protocols.";

  revision 2026-07-31 {
    description
      "SRLinux 26.7.1";
  }
  revision 2026-03-31 {
    description
      "SRLinux 26.3.1";
  }
  revision 2025-10-31 {
    description
      "SRLinux 25.10.1";
  }
  revision 2025-07-31 {
    description
      "SRLinux 25.7.1";
  }
  revision 2025-03-31 {
    description
      "SRLinux 25.3.1";
  }
  revision 2024-10-31 {
    description
      "SRLinux 24.10.1";
  }
  revision 2024-07-31 {
    description
      "SRLinux 24.7.1";
  }
  revision 2024-03-31 {
    description
      "SRLinux 24.3.1";
  }
  revision 2023-10-31 {
    description
      "SRLinux 23.10.1";
  }
  revision 2023-07-31 {
    description
      "SRLinux 23.7.1";
  }
  revision 2023-03-31 {
    description
      "SRLinux 23.3.1";
  }
  revision 2022-11-30 {
    description
      "SRLinux 22.11.1";
  }
  revision 2022-06-30 {
    description
      "SRLinux 22.6.1";
  }
  revision 2022-03-31 {
    description
      "SRLinux 22.3.1";
  }
  revision 2021-11-30 {
    description
      "SRLinux 21.11.1";
  }
  revision 2021-06-30 {
    description
      "SRLinux 21.6.1";
  }
  revision 2021-03-31 {
    description
      "SRLinux 21.3.1";
  }
  revision 2020-06-30 {
    description
      "SRLinux 20.6.1";
  }
  revision 2019-11-30 {
    description
      "SRLinux 19.11.1";
  }

  grouping prefix-top {
    list prefix {
      key "ip-prefix mask-length-range";
      description
        "List of prefixes in the prefix set";
      leaf ip-prefix {
        type srl_nokia-comm:ip-prefix;
        description
          "The IPv4 or IPv6 prefix in CIDR notation";
      }
      leaf mask-length-range {
        type string {
          pattern '([0-9]+\.\.[0-9]+)|exact';
          length "1..16";
        }
        description
          "The range of prefix lengths to match

           Example: 10.3.192.0/21 through 10.3.192.0/24 would be expressed as prefix: 10.3.192.0/21, mask-length-range: 21..24.

           Example: 10.3.192.0/21 would be expressed as prefix: 10.3.192.0/21,
           mask-length-range: exact";
      }
    }
  }

  grouping as-path-set-top {
    list as-path-set {
      key "name";
      description
        "AS Path regular expressions for use in policy entries";
      leaf name {
        type srl_nokia-comm:name;
        description
          "A name used to identify the AS path regular expression";
      }
      leaf regex-mode {
        description
          "Mode used to parse the regular expression in every as-path-set-member of the as-path-set

           In ASN mode the AS path is converted to a string and the string is matched one complete AS number at a time. In character mode the AS path is converted to a string and the string is matched one character at a time.";
        type enumeration {
          enum asn {
            description
              "ASN mode regular expression parsing";
          }
          enum character {
            if-feature "srl_nokia-feat:routing-policy-enhanced-as-path-set";
            description
              "Character mode regular expression parsing";
          }
        }
        default "asn";
      }
      leaf-list as-path-set-member {
        srl_nokia-ext:no-globbing;
        max-elements 32;
        if-feature "srl_nokia-feat:routing-policy-enhanced-as-path-set";
        type srl_nokia-pol-types:as-path-regexp {
          length "1..255";
        }
        description
          "A list of regular expressions";
      }
    }
  }

  grouping prefix-set-top {
    list prefix-set {
      key "name";
      description
        "List of defined prefix sets";
      leaf name {
        type srl_nokia-comm:name;
        description
          "A name used to identify the prefix set";
      }
      uses prefix-top;
    }
  }

  grouping community-member-top {
    description
      "Members of a community set";
    leaf-list member {
      srl_nokia-ext:no-globbing;
      type union {
        type srl_nokia-pol-types:bgp-std-community-well-known-type;
        type srl_nokia-pol-types:bgp-std-community-type;
        type srl_nokia-pol-types:bgp-large-community-type;
        type srl_nokia-pol-types:bgp-ext-community-type;
        type srl_nokia-pol-types:bgp-ext-community-regexp-type;
        type srl_nokia-pol-types:bgp-large-community-regexp-type;
        type srl_nokia-pol-types:bgp-std-community-regexp-type;
      }
      description
        "A standard BGP community value, regular expression or well-known name or else a large BGP community value or regular expression";
    }
    leaf match-set-options {
      if-feature "srl_nokia-feat:routing-policy-community-match-set-options";
      type enumeration {
        enum any {
          description
            "Match is true if any of the listed community member values is present in the route";
        }
        enum all {
          description
            "Match is true if all of the listed community member values are present in the route";
        }
        enum invert {
          description
            "Match is true if none of the listed community member values are present in the route";
        }
      }
      default "all";
      description
        "Options that determine the matching criteria that applies to the list of community members";
    }
  }

  grouping std-community-member-top {
    description
      "Members of a standard community set";
    leaf-list member {
      srl_nokia-ext:no-globbing;
      type union {
        type srl_nokia-pol-types:bgp-std-community-well-known-type;
        type srl_nokia-pol-types:bgp-std-community-regexp-type2;
      }
      description
        "A standard BGP community value or regular expression";
    }
  }

  grouping ext-community-member-top {
    description
      "Members of an extended community set";
    leaf-list member {
      srl_nokia-ext:no-globbing;
      type srl_nokia-pol-types:bgp-ext-community-regexp-type2;
      description
        "An extended BGP community value or regular expression";
    }
  }

  grouping community-set-top {
    list community-set {
      key "name";
      description
        "List of BGP community sets containing standard, extended and large BGP communities";
      leaf name {
        type srl_nokia-comm:name;
        description
          "A name used to identify the community set";
      }
      uses community-member-top;
    }
  }

  grouping standard-community-set-top {
    list standard-community-set {
      key "name";
      description
        "List of BGP standard community sets containing only standard BGP communities";
      leaf name {
        type srl_nokia-comm:name;
        description
          "A name used to identify the community set";
      }
      uses std-community-member-top;
    }
  }

  grouping extended-community-set-top {
    list extended-community-set {
      key "name";
      description
        "List of BGP extended community sets containing only extended BGP communities";
      leaf name {
        type srl_nokia-comm:name;
        description
          "A name used to identify the community set";
      }
      uses ext-community-member-top;
    }
  }

  grouping tag-set-top {
    description
      "Configuration and state for tag-sets";
    list tag-set {
      if-feature "srl_nokia-feat:internal-tags";
      key "name";
      max-elements 1024;
      description
        "List of administrative tag sets";
      leaf name {
        type srl_nokia-comm:name;
        description
          "A name used to identify the tag set";
      }
      leaf-list tag-value {
        min-elements 1;
        max-elements 2;
        type srl_nokia-pol-types:tag-type;
        must "not(string(.)='00' or string(.)='00:00' or string(.)='00:00:00' or string(.)='00:00:00:00')";
        description
          "Value of the tag set member";
      }
      leaf tag-set-index {
        config false;
        type uint32;
        description
          "System-wide persistent unique identifier assigned to the tag-set";
      }
    }
  }

  grouping tags-action {
    description
      "Group containing actions related to tags";
    container internal-tags {
      if-feature "srl_nokia-feat:internal-tags";
      description
        "Enter the internal-tags context

         Configuration of internal tags";
      leaf-list set-tag-set {
        max-elements 1;
        type leafref {
          path "/srl_rpol:routing-policy/srl_rpol:tag-set/srl_rpol:name";
        }
        description
          "Reference to a tag-set defined under routing-policy";
      }
    }
  }

  grouping route-preference-action {
    container route-preference {
      if-feature "srl_nokia-feat:routing-policy-preference-action";
      description
        "Enter the route-preference context

         Options for modifying route preference";
      leaf set {
        type uint8;
        description
          "Overwrite the route preference with the specified value

           The IP route table preference is sometimes called the administrative distance of the route. In general, when comparing any two routes, the route with the lower preference is the one that is activated and used for forwarding.

           This action has an effect only in BGP import policies and VRF import policies";
      }
    }
  }

  grouping resilient-hash-action {
    container resilient-hash {
      description
        "Enter the resilient-hash context

         Options for controlling ECMP resilient hashing behavior";
      leaf apply {
        description
          "When set true, resilient hashing is enabled if the accepted route becomes the best BGP path

           When set false, resilient hashing is disabled if the accepted route becomes the best BGP path.

           This action only applies in BGP import policies.";
        type boolean;
        must '. = false() or boolean(../hash-buckets-per-path) = true()' {
          error-message "hash-buckets per path configuration is required";
        }
        must '. = false() or boolean(../max-paths) = true()' {
          error-message "max-paths configuration is required";
        }
      }
      leaf hash-buckets-per-path {
        type uint8 {
          range "1..32";
        }
        description
          "The number of times each next-hop is repeated in the fill pattern if there are max-paths ECMP next-hops

           A larger number consumes more resources but provides more granularity when flows need to be moved. There is a platform-specific limit to the product of this hash-buckets-per-path value and the max-paths value.";
        must 'not(boolean(../apply) = false())' {
          error-message "apply must be true to specify this parameter";
        }
      }
      leaf max-paths {
        type uint8 {
          range "1..64";
        }
        description
          "The maximum number of ECMP next-hops per route associated with the resilient-hash prefix

           If a matching route has more than this number of ECMP next-hops only the first N are used, where N is the value of this parameter. There is a platform-specific limit to the product of this max-paths value and the hash-buckets-per-path value.";
        must 'not(boolean(../apply) = false())' {
          error-message "apply must be true to specify this parameter";
        }
      }
    }
  }

  grouping bgp-as-path-actions {
    container as-path {
      description
        "Enter the as-path context

         Modify AS Path attribute of routes";
      leaf remove {
        description
          "Clear the AS path to make it empty.";
        type boolean;
      }
      leaf-list replace {
        type srl_nokia-pol-types:as-number;
        ordered-by user;
        must 'not(../remove)';
        description
          "Clear the existing AS path and replace it a new AS_SEQUENCE containing the listed AS numbers.

           This takes precedence over a prepend action; the prepend action is not performed if a remove or replace action is specified.";
      }
      container prepend {
        description
          "Enter the prepend context

           Prepend a BGP AS number to the AS Path attribute of routes";
        leaf as-number {
          type union {
            type srl_nokia-pol-types:as-number;
            type enumeration {
              enum auto {
                value 1;
              }
            }
          }
          description
            "The AS number to prepend to the AS Path attributes

             If 'auto' is specified then the peer's AS number is used in the context of an import policy and the local AS number is used in the context of an export policy.";
        }
        leaf repeat-n {
          type uint8 {
            range "1..50";
          }
          description
            "The number of repetitions of the prepended AS number";
        }
      }
    }
  }

  grouping bgp-community-actions {
    container communities {
      description
        "Enter the communities context

         Modify BGP communities attached to routes";
      leaf add {
        type leafref {
          path "/srl_rpol:routing-policy/srl_rpol:community-set/name";
        }
        description
          "Reference to a community-set name

           All of the non-regex community members in the referenced community-set are added to the COMMUNTIES and LARGE_COMMUNITIES attributes.";
      }
      leaf remove {
        type leafref {
          path "/srl_rpol:routing-policy/srl_rpol:community-set/name";
        }
        description
          "Reference to a community-set name

           The communities in the route are compared to all of the community members in the referenced community-set, and all matching communities are removed from the COMMUNITIES and LARGE_COMMUNITIES  attributes.";
      }
      leaf replace {
        type leafref {
          path "/srl_rpol:routing-policy/srl_rpol:community-set/name";
        }
        description
          "Reference to a community-set name

           All of the existing communities are deleted and then all of the non-regex community members in the referenced community-set are encoded in new COMMUNTIES and LARGE_COMMUNITIES attributes.";
        must 'not(../remove or ../add)';
      }
    }
    container standard-community {
      if-feature "srl_nokia-feat:routing-policy-standard-community-actions";
      leaf operation {
        type srl_nokia-pol-types:bgp-set-community-operation-type;
        description
          "The type of operation for modifying the community attribute with the specified values";
      }
      leaf-list referenced-sets {
        if-feature "srl_nokia-feat:routing-policy-standard-community-sets";
        max-elements 28;
        type leafref {
          path "/srl_rpol:routing-policy/srl_rpol:standard-community-set/name";
        }
      }
      leaf method {
        type enumeration {
          enum reference {
            description
              "The standard communities are specified by referencing a defined standard-community set";
          }
        }
        default "reference";
        description
          "Indicates the method used to specify the standard communities for the action";
      }
      description
        "Enter the standard-community context";
    }
    container extended-community {
      if-feature "srl_nokia-feat:routing-policy-extended-community-actions";
      leaf operation {
        type srl_nokia-pol-types:bgp-set-community-operation-type;
        description
          "The type of operation for modifying the community attribute with the specified values";
      }
      leaf-list referenced-sets {
        if-feature "srl_nokia-feat:routing-policy-extended-community-sets";
        max-elements 28;
        type leafref {
          path "/srl_rpol:routing-policy/srl_rpol:extended-community-set/name";
        }
      }
      leaf method {
        type enumeration {
          enum reference {
            description
              "The extended communities are specified by referencing a defined extended-community set";
          }
        }
        default "reference";
        description
          "Indicates the method used to specify the extended communities for the action";
      }
      description
        "Enter the extended-community context";
    }
  }

  grouping bgp-fib-actions {
    leaf disable-ip-route-install {
      if-feature "srl_nokia-feat:routing-policy-bgp-disable-fib";
      type boolean;
      description
        "Accept the route, allowing its re-advertisement, but do not install the route to the IP FIB";
    }
  }

  grouping bgp-local-pref-actions {
    container local-preference {
      description
        "Enter the local-preference context

         Options for modifying the BGP local preference attribute value";
      leaf value {
        if-feature "srl_nokia-feat:routing-policy-bgp-local-pref-set";
        type uint32;
        must '../operation' {
          error-message "value cannot be specified without an operation";
        }
        description
          "Change the value of the Local-Pref attribute in matching BGP routes";
      }
      leaf operation {
        type enumeration {
          enum set {
            if-feature "srl_nokia-feat:routing-policy-bgp-local-pref-set";
            description
              "Set the Local-Pref to the specified value, overwriting the current value";
          }
        }
        must "string(../value) != ''" {
          error-message "operation cannot be specified without a value";
        }
        description
          "The operation to use when applying the configured value to the current Local-Pref";
      }
    }
  }

  grouping bgp-med-actions {
    container med {
      if-feature "srl_nokia-feat:routing-policy-bgp-med";
      leaf value {
        type union {
          type enumeration {
            enum route-table-cost;
          }
          type uint32;
        }
        must '../operation' {
          error-message "value cannot be specified without an operation";
        }
        description
          "Change the value of the Multi-Exit Discriminator attribute in matching BGP routes

           The route-table-cost option derives its value from the route metric.";
      }
      leaf operation {
        type enumeration {
          enum set {
            description
              "Set the MED to the specified value";
          }
          enum add {
            description
              "Increment the previous MED by the specified value";
          }
          enum subtract {
            description
              "Decrement the previous MED by the specified value";
          }
        }
        must "string(../value) != ''" {
          error-message "operation cannot be specified without a value";
        }
        description
          "The operation to use when applying the configured value to the existing MED";
      }
      description
        "Enter the med context";
    }
  }

  grouping bgp-next-hop-actions {
    container next-hop {
      description
        "Enter the next-hop context

         Container for BGP next-hop modifications";
      leaf set {
        if-feature "srl_nokia-feat:routing-policy-bgp-next-hop-set-action";
        description
          "Set the protocol next-hop addres of matched BGP routes";
        type srl_nokia-pol-types:bgp-next-hop-type;
        must "(. = 'self' or (contains(., '.') and not(starts-with(., '0.') or starts-with(., '127.') or (number(substring-before(., '.')) >= 224))) or (contains(., ':') and not(re-match(., '[0:]+') or re-match(., '[0:]+:0*1') or re-match(., '[fF][fF].*') or re-match(., '[fF][eE]8.*') or re-match(., '[fF][eE]9.*') or re-match(., '[fF][eE][aA].*') or re-match(., '[fF][eE][bB].*'))))" {
          error-message "Not a valid unicast address";
        }
      }
    }
    container next-hop-resolution {
      if-feature "srl_nokia-feat:internal-tags and srl_nokia-feat:routing-policy-bgp-next-hop-resolution-action";
      description
        "Enter the next-hop-resolution context

         Actions related to next-hop resolution of matched BGP routes";
      leaf set-tag-set {
        type leafref {
          path "/srl_rpol:routing-policy/srl_rpol:tag-set/srl_rpol:name";
        }
        description
          "Reference to a tag-set to be used for controlling next-hop resolution";
      }
      leaf set-flex-algo {
        if-feature "srl_nokia-feat:routing-policy-bgp-flex-algo-next-hop-resolution-action";
        description
          "Action to set the algorithm fornext-hop resolution of matched BGP routes";
        type srl_nokia-flex-algo-types:flex-algo-id;
      }
    }
  }

  grouping bgp-origin-actions {
    container origin {
      leaf set {
        type enumeration {
          enum igp;
          enum egp;
          enum incomplete;
        }
        description
          "The new value of the ORIGIN attribute to write into the matching BGP routes";
      }
      description
        "Enter the origin context";
    }
  }

  grouping bgp-label-allocation-actions {
    container label-allocation {
      if-feature "srl_nokia-feat:bgp-labeled-unicast";
      description
        "Enter the label-allocation context

         Actions that determine the method used to assign labels to BGP LU routes matched and accepted by route-table-import policies";
      choice label-allocation-method {
        case prefix-sid {
          container prefix-sid {
            if-feature "srl_nokia-feat:bgp-labeled-unicast-prefix-sid";
            description
              "Enter the prefix-sid context

               RIB-OUT label is based on prefix SID configuration";
            leaf reuse-igp {
              description
                "When true use the programmed SR-IGP label index for the matching prefix, resulting in a stitch to the IGP segment routing tunnel";
              type boolean;
            }
          }
        }
      }
    }
  }

  grouping bgp-statistics-actions {
    container statistics {
      if-feature "srl_nokia-feat:bgp-labeled-unicast-tunnel-statistics or srl_nokia-feat:te-policy-colored-statistics";
      description
        "Enter the statistics context

         Policy actions related to statistics collection";
      container labeled-unicast {
        if-feature "srl_nokia-feat:bgp-labeled-unicast-tunnel-statistics";
        description
          "Enter the labeled-unicast context

           Policy actions related to statistics collection of BGP-LU routes and tunnels";
        leaf ingress {
          description
            "Set true to enable statistics collection for ILM forwarding entries associated with BGP-LU routes";
          type boolean;
        }
        leaf egress {
          description
            "Set true to enable statistics collection for NHLFE forwarding entries associated with BGP-LU routes";
          type boolean;
        }
      }
      container srte-policy {
        if-feature "srl_nokia-feat:te-policy-colored-statistics";
        description
          "Enter the srte-policy context

           Policy actions related to statistics collection of BGP-signaled SR policies";
        leaf ingress {
          description
            "Set true to enable statistics collection for ILM forwarding entries associated with BGP SR policies";
          type boolean;
        }
        leaf egress {
          description
            "Set true to enable statistics collection for NHLFE forwarding entries associated with BGP SR policies";
          type boolean;
        }
      }
    }
  }

  grouping bgp-protection-actions {
    container protection {
      description
        "Enter the protection context

         Policy actions related to protection and maintenance of BGP tunnels";
      container srte-policy {
        description
          "Enter the srte-policy context

           Policy actions related to protection and maintenance of BGP SRTE policy tunnels";
        container return-path {
          if-feature "srl_nokia-feat:bgp-srte-policy-sbfd-return-label";
          description
            "Enter the return-path context

             In case of Colored TE-Policy, BGP signalled, return label or SID used by sBFD reflector for return path selection";
          leaf mpls-label {
            description
              "MPLS label that is used by reflector while responding to the sBFD request. Assigned value should uniquely identify the sender. Binding-SID or a Node-SID are commonly used options";
            type srl_nokia-comm:mpls-label-non-reserved;
            must '../../protection-policy' {
              error-message "mpls-label cannot be specified without a protection-policy";
            }
          }
        }
        leaf protection-policy {
          if-feature "srl_nokia-feat:protection-policies and srl_nokia-feat:routing-policy-bgp-srte-policy";
          description
            "The protection policy to use with the TE policy if the matched BGP route becomes the active candidate path";
          type leafref {
            path "/srl_nokia-system:system/srl_nokia-prot-pol:protection-policies/srl_nokia-prot-pol:policy/srl_nokia-prot-pol:protection-policy-name";
          }
        }
      }
    }
  }

  grouping bgp-srv6-actions {
    container srv6 {
      if-feature "srl_nokia-feat:srv6";
      description
        "Enter the srv6 context";
      leaf locator {
        type leafref {
          path "/srl_nokia-system:system/srl_nokia-srv6:srv6/srl_nokia-srv6:locator/srl_nokia-srv6:locator-name";
        }
        description
          "Locator for SRv6 TLV to use";
      }
    }
  }

  grouping isis-actions {
    leaf level {
      type srl_nokia-isis-types:isis-level-number;
      description
        "Set the level that a prefix is to be imported into";
    }
    container metric {
      description
        "Enter the metric context

         Policy actions related to ISIS metrics";
      leaf set-style {
        type enumeration {
          enum wide {
            description
              "Wide metric style, supporting metrics greater than 63";
          }
        }
        description
          "Set the style of the metric";
      }
      leaf set-value {
        type srl_nokia-isis-types:isis-wide-metric;
        description
          "Set the metric of the IS-IS prefix";
      }
    }
  }

  grouping ospf-actions {
    container metric {
      description
        "Enter the metric context

         Policy actions related to OSPF metrics";
      leaf set-external-type {
        type enumeration {
          enum type-1;
          enum type-2;
        }
        description
          "Set the external metric type of the redistributed route";
      }
      leaf set-value {
        type srl_nokia-ospf-types:ospf-metric;
        description
          "Set the metric value of the redistributed route";
      }
    }
  }

  grouping statement-action-top {
    description
      "Policy actions supported at the statement level";
    container bgp {
      uses bgp-as-path-actions;
      uses bgp-community-actions;
      uses bgp-fib-actions;
      uses bgp-local-pref-actions;
      uses bgp-med-actions;
      uses bgp-next-hop-actions;
      uses bgp-origin-actions;
      uses bgp-label-allocation-actions;
      uses bgp-statistics-actions;
      uses bgp-protection-actions;
      uses bgp-srv6-actions;
      description
        "Enter the bgp context";
    }
    container isis {
      if-feature "srl_nokia-feat:routing-policy-isis-actions";
      uses isis-actions;
      description
        "Enter the isis context";
    }
    container ospf {
      if-feature "srl_nokia-feat:routing-policy-ospf-actions";
      uses ospf-actions;
      description
        "Enter the ospf context";
    }
    uses route-preference-action;
    uses resilient-hash-action {
      if-feature "srl_nokia-feat:routing-policy-resilient-hash-action";
    }
    uses tags-action;
  }

  grouping default-action-top {
    container default-action {
      description
        "Enter the default-action context

         Actions for routes that do not match any policy statement";
      leaf policy-result {
        type srl_nokia-pol-types:default-policy-result;
        description
          "Select the action type for routes that do not match any policy statement

           If no value is configured for the policy-result then the implicit default is a next-policy behavior.";
      }
      container bgp {
        uses bgp-as-path-actions;
        uses bgp-community-actions;
        uses bgp-fib-actions;
        uses bgp-local-pref-actions;
        uses bgp-med-actions;
        uses bgp-next-hop-actions;
        uses bgp-origin-actions;
        uses bgp-label-allocation-actions;
        uses bgp-srv6-actions;
        description
          "Enter the bgp context";
      }
      container isis {
        if-feature "srl_nokia-feat:routing-policy-isis-actions";
        uses isis-actions;
        description
          "Enter the isis context";
      }
      container ospf {
        if-feature "srl_nokia-feat:routing-policy-ospf-actions";
        uses ospf-actions;
        description
          "Enter the ospf context";
      }
      uses route-preference-action;
      uses tags-action;
    }
  }

  grouping match-prefix-set {
    description
      "Configuration for prefix-set match criteria";
    container prefix {
      leaf prefix-set {
        type leafref {
          path "/srl_rpol:routing-policy/srl_rpol:prefix-set/name";
        }
        description
          "Reference to a prefix set name";
      }
      leaf match-set-options {
        if-feature "srl_nokia-feat:routing-policy-prefix-set-match-options-any";
        type enumeration {
          enum any {
            description
              "Match is true if any of the members in the referenced set is present in the route";
          }
          enum invert {
            if-feature "srl_nokia-feat:routing-policy-prefix-set-match-options-invert";
            description
              "Match is true if no element in the referenced set matches the prefix of the route";
          }
        }
        default "any";
      }
      description
        "Enter the prefix context";
    }
  }

  grouping match-bgp-evpn {
    container evpn {
      description
        "Enter the evpn context

         Container for match conditions that are specific to BGP EVPN routes.";
      leaf-list route-type {
        type uint8 {
          range "1..8";
        }
        max-elements 1;
        description
          "An EVPN route meets this condition if the route-type field in the NLRI is one of the values provided in this list.";
      }
    }
  }

  grouping match-bgp-srte-policy {
    container srte-policy {
      if-feature "srl_nokia-feat:routing-policy-bgp-srte-policy";
      leaf distinguisher {
        description
          "Unique identifier of the policy candidate path in the context of <color, endpoint> tuple";
        type uint32;
      }
      leaf color {
        description
          "Color of the SRTE policy, used to steer traffic into the tunnel";
        type uint32;
      }
      leaf endpoint {
        description
          "The endpoint IPv4 or IPv6 address of the SR policy";
        type srl_nokia-comm:ip-address;
        must "((contains(., '.') and not(starts-with(., '0.') or starts-with(., '127.') or (number(substring-before(., '.')) >= 224))) or (contains(., ':') and not(re-match(., '[0:]+') or re-match(., '[0:]+:0*1') or re-match(., '[fF][fF].*') or re-match(., '[fF][eE]8.*') or re-match(., '[fF][eE]9.*') or re-match(., '[fF][eE][aA].*') or re-match(., '[fF][eE][bB].*'))))" {
          error-message "Not a valid unicast address";
        }
      }
      description
        "Enter the srte-policy context";
    }
  }

  grouping match-bgp {
    container bgp {
      description
        "Enter the bgp context

         Configuration for BGP-specific policy match criteria";
      container as-path {
        leaf as-path-set {
          description
            "Reference to an as-path-set name

             A route meets this condition if it matches the as-path-set-member regex strings according to the match-set-options logic";
          type leafref {
            path "/srl_rpol:routing-policy/srl_rpol:as-path-set/name";
          }
        }
        uses srl_nokia-pol-types:match-set-options {
          if-feature "srl_nokia-feat:routing-policy-enhanced-as-path-set";
        }
        description
          "Enter the as-path context";
      }
      container as-path-length {
        description
          "Enter the as-path-length context

           A BGP route matches this condition if the number of (unique) AS numbers in its AS_PATH matches this value or the range implied by the value+operator.";
        leaf value {
          type uint8 {
            range "0..255";
          }
          description
            "The number of (unique) AS numbers in the AS path";
        }
        leaf operator {
          type srl_nokia-pol-types:comparison-operator-type;
          description
            "The comparison operator that applies to the value";
        }
        leaf unique {
          type boolean;
          description
            "Count a repeated sequence of the same AS number as just 1 element";
        }
      }
      leaf community-set {
        description
          "Reference to a community-set name

           A route meets this condition if has any community value matching a community member in the referenced community-set";
        type leafref {
          path "/srl_rpol:routing-policy/srl_rpol:community-set/name";
        }
      }
      container standard-community {
        if-feature "srl_nokia-feat:routing-policy-standard-community-sets";
        leaf standard-community-set {
          description
            "Reference to a standard-community-set name

             A route meets this condition if the configured match-set-options apply to the referenced standard-community-set";
          type leafref {
            path "/srl_rpol:routing-policy/srl_rpol:standard-community-set/name";
          }
        }
        uses srl_nokia-pol-types:match-set-options;
        description
          "Enter the standard-community context";
      }
      container extended-community {
        if-feature "srl_nokia-feat:routing-policy-extended-community-sets";
        leaf extended-community-set {
          description
            "Reference to an extended-community-set name

             A route meets this condition if the configured match-set-options apply to the referenced extended-community-set";
          type leafref {
            path "/srl_rpol:routing-policy/srl_rpol:extended-community-set/name";
          }
        }
        uses srl_nokia-pol-types:match-set-options;
        description
          "Enter the extended-community context";
      }
      uses match-bgp-evpn;
      uses match-bgp-srte-policy;
      uses match-srv6;
    }
  }

  grouping match-general {
    description
      "Configuration for general match criteria applicable to multiple route types";
    leaf-list family {
      type srl_nokia-pol-types:bgp-family-type;
      description
        "The name of an address family

         A route meets this condition if the prefix belongs to one of the indicated address families.";
    }
    leaf protocol {
      type identityref {
        base srl_nokia-comm:routing-policy-protocol-match-type;
      }
      description
        "The route type to match";
      must ". != 'gribi'" {
        error-message "Protocol value \"gribi\" is not supported on this release";
        srl_nokia-ext:if-feature "not srl_nokia-feat:routing-policy-gribi-route-type";
      }
    }
    leaf tunnel {
      if-feature "srl_nokia-feat:bgp-next-hop-resolution-policy";
      type boolean;
      description
        "When true, only match tunnels and when false, only match IP routes

         When unconfigured, match both routes and tunnels";
    }
    leaf tunnel-type {
      if-feature "srl_nokia-feat:bgp-next-hop-resolution-policy";
      type identityref {
        base srl_nokia-comm:routing-policy-tunnel-match-type;
      }
      description
        "The tunnel type to match";
    }
    leaf-list call-policy {
      if-feature "srl_nokia-feat:routing-policy-subroutines";
      max-elements 1;
      type leafref {
        path "/routing-policy/policy/name";
      }
      description
        "Call another policy as a subroutine

         If the final action of the called policy (which may in turn call other policies) with respect to a route is 'accept' then the route is considered to satisfy this match condition. If the final action of the called policy with respect to a route is 'reject' then the route is considered a non-match of this condition and hence the policy statement";
    }
    leaf origin-network-instance {
      if-feature "srl_nokia-feat:network-instance-leaked-route-readvertisement";
      description
        "Reference to network-instance that leaked the route into the network-instance where the policy is being evaluated";
      type leafref {
        path "/srl_nokia-netinst:network-instance/srl_nokia-netinst:name";
      }
      must "(/srl_nokia-netinst:network-instance[srl_nokia-netinst:name=current()]/srl_nokia-netinst:type = \"srl_nokia-netinst:ip-vrf\") or
                  (/srl_nokia-netinst:network-instance[srl_nokia-netinst:name=current()]/srl_nokia-netinst:type = \"srl_nokia-netinst:default\")" {
        error-message "origin-network-instance match is only suported in the default and ip-vrf network-instances";
      }
    }
    leaf network-instance-leaked-route {
      if-feature "srl_nokia-feat:network-instance-leaked-route-readvertisement";
      description
        "When set true, match all leaked routes (with an origin-network-instance different than the local context network-instance)";
      type boolean;
    }
  }

  grouping match-igp {
    container isis {
      srl_nokia-ext:first-released "20.12.1";
      description
        "Enter the isis context

         Configuration for ISIS-specific policy match criteria";
      leaf level {
        description
          "Match an IS-IS route based on its level";
        type uint8 {
          range "1..2";
        }
        must "../../protocol = 'isis' or ../../tunnel-type = 'sr-isis' or ../../tunnel-type = 'srv6-isis'" {
          error-message "Protocol must be isis or tunnel-type must be either sr-isis or srv6-isis";
        }
      }
      leaf route-type {
        description
          "Match an IS-IS route based on its type

           An IS-IS IPv4 prefix is external if it is signalled in TLV 130 or TLV135 with RFC 7794 X flag=1. An IS-IS IPv6 prefix is external if the TLV 236/TLV 237 external bit = 1.";
        type enumeration {
          enum internal {
            description
              "Match only internal routes";
          }
          enum external {
            description
              "Match only external routes";
          }
        }
        must "../../protocol = 'isis'" {
          error-message "Protocol must be isis";
        }
      }
    }
    container ospf {
      srl_nokia-ext:first-released "20.12.1";
      description
        "Enter the ospf context

         Configuration for OSPF-specific policy match criteria";
      leaf area-id {
        type srl_nokia-ospf-types:ospf-area-identifier;
        description
          "The area identifier as a dotted-quad.";
        must "../../protocol = 'ospfv2' or ../../protocol = 'ospfv3'" {
          error-message "Protocol must be OSPF";
        }
      }
      leaf route-type {
        description
          "The OSPF route type.";
        type enumeration {
          enum internal {
            description
              "Match only internal routes";
          }
          enum external {
            description
              "Match only external routes";
          }
        }
        must "../../protocol = 'ospfv2' or ../../protocol = 'ospfv3'" {
          error-message "Protocol must be OSPF";
        }
      }
      leaf instance-id {
        description
          "OSPFv3 instance identifier";
        type uint32 {
          range "0..255";
        }
        must "((../../protocol = 'ospfv3') and ((. >= 0 and . <=31) or (. >= 64 and . <= 95)))" {
          error-message "Protocol must be OSPFv3 and Instance-id range must either be 0..31 or 64..95";
        }
      }
    }
    container multicast {
      if-feature "srl_nokia-feat:mcast-route-policy";
      container group-address {
        description
          "Enter the group-address context

           Multicast group IP address

           To match a <S,G> the source needs to be present in the multicast source-address leafref and the group needs to present in the group-address leafref.
           To match a <*,G> the group has to be programmed in the group-address leafref and no source in the source-address leafref.
           Group address can be configured as a prefix.";
        leaf prefix-set {
          type leafref {
            path "/srl_rpol:routing-policy/srl_rpol:prefix-set/name";
          }
        }
      }
      container source-address {
        description
          "Enter the source-address context

           Multicast Source IP address

           Source address can be configured as a prefix.";
        leaf prefix-set {
          type leafref {
            path "/srl_rpol:routing-policy/srl_rpol:prefix-set/name";
          }
        }
      }
      description
        "Enter the multicast context";
    }
  }

  grouping match-srv6 {
    container srv6 {
      if-feature "srl_nokia-feat:srv6";
      description
        "Enter the srv6 context";
      leaf sid-prefix {
        type srl_nokia-comm:ipv6-prefix-unicast;
        description
          "SRv6 SID or uSID as match criterion for the BGP route";
      }
      leaf tlv {
        type enumeration {
          enum present {
            value 1;
          }
          enum not-present {
            value 2;
          }
        }
        description
          "SRv6 TLV presence as match criterion for BGP route";
      }
    }
  }

  grouping match-tags {
    description
      "Configuration tag based match criteria";
    container internal-tags {
      if-feature "srl_nokia-feat:internal-tags";
      description
        "Enter the internal-tags context

         Configuration and state of internal tags";
      leaf-list tag-set {
        max-elements 1;
        type leafref {
          path "/srl_rpol:routing-policy/srl_rpol:tag-set/srl_rpol:name";
        }
        description
          "Reference to a tag-set defined under routing-policy";
      }
      uses srl_nokia-pol-types:match-set-options {
        if-feature "srl_nokia-feat:routing-policy-tag-set-match-options";
      }
    }
  }

  grouping match-top {
    description
      "Top-level grouping for match criteria";
    container match {
      description
        "Enter the match context

         Match conditions of the policy statement";
      uses match-prefix-set;
      uses match-general;
      uses match-tags;
      uses match-bgp;
      uses match-igp;
    }
  }

  grouping action-top {
    description
      "Top-level grouping for policy actions";
    container action {
      srl_nokia-ext:first-released "19.11.1";
      description
        "Enter the action context

         Actions for routes that match the policy statement";
      leaf policy-result {
        type srl_nokia-pol-types:statement-policy-result;
        description
          "Select the action to apply to matching routes

           If no value is configured for the policy-result then the implicit default is a next-statement behavior.";
      }
      uses statement-action-top;
    }
  }

  grouping condition-top {
    description
      "Top level grouping for policy statemene conditions";
    container condition {
      description
        "Enter the condition context

         Conditions that must be met for the policy statement to be evaluated";
      leaf evaluation-result {
        config false;
        description
          "Reads true when the condition is fulfilled, resulting in evaluation of the statement";
        type boolean;
      }
      container route-table {
        description
          "Enter the route-table context

           Conditions related to the presence of routes in the route-table";
        leaf network-instance {
          description
            "Reference to the network-instance with the route-table to be analyzed";
          type leafref {
            path "/srl_nokia-netinst:network-instance/srl_nokia-netinst:name";
          }
          must '../prefix-set' {
            error-message "network-instance requires prefix-set as well";
          }
          must '(/srl_nokia-netinst:network-instance[srl_nokia-netinst:name=current()]/srl_nokia-netinst:type = "srl_nokia-netinst:ip-vrf") or (/srl_nokia-netinst:network-instance[srl_nokia-netinst:name=current()]/srl_nokia-netinst:type = "srl_nokia-netinst:default")' {
            error-message "origin-network-instance match is only supported in the default and ip-vrf network-instances";
          }
        }
        leaf prefix-set {
          description
            "Reference to a prefix set name";
          type leafref {
            path "/srl_rpol:routing-policy/srl_rpol:prefix-set/name";
          }
          must '../network-instance' {
            error-message "prefix-set requires a network-instance to be specified";
          }
        }
        leaf match-set-options {
          type enumeration {
            enum any {
              description
                "Condition is true if any element in the prefix set matches at least one active route in the route-table";
            }
            enum all {
              description
                "Match is true if every element in the prefix set matches at least one active route in the route-table";
            }
            enum invert {
              description
                "Match is true if there is no element in the prefix set that matches at least one route in the route-table";
            }
          }
          description
            "Options that determine the matching criteria that applies to the list of prefixes

             The implicit default behavior is any";
        }
      }
    }
  }

  grouping statement-top {
    description
      "Top-level grouping for the policy statements list";
    list statement {
      max-elements 16384;
      key "name";
      ordered-by user;
      description
        "Policy statements group conditions and actions within a policy definition.  They are evaluated in configuration order.";
      leaf name {
        type srl_nokia-comm:name;
        description
          "Name given to the policy statement (rule).";
      }
      uses condition-top {
        if-feature "srl_nokia-feat:routing-policy-conditional-statements";
      }
      uses match-top;
      uses action-top;
    }
  }

  grouping policy-top {
    description
      "Top-level grouping for the policy list";
    list policy {
      key "name";
      description
        "List of policy definitions, keyed by unique name

         These policy definitions are expected to be referenced (by name) in policy in import-policy and/or export-policy statements.";
      leaf name {
        type srl_nokia-comm:name;
        description
          "A name used to identify the policy";
      }
      uses default-action-top;
      uses statement-top;
    }
  }

  grouping routing-policy-top {
    description
      "Top level container for route policies";
    container routing-policy {
      description
        "Enter the routing-policy context

         Top-level container for all routing policy configuration";
      uses as-path-set-top;
      uses community-set-top;
      uses standard-community-set-top {
        if-feature "srl_nokia-feat:routing-policy-standard-community-sets";
      }
      uses extended-community-set-top {
        if-feature "srl_nokia-feat:routing-policy-extended-community-sets";
      }
      uses prefix-set-top;
      uses tag-set-top;
      uses policy-top;
    }
  }

  uses routing-policy-top;
}
