module srl_nokia-platform-cgroup {
  yang-version 1.1;
  namespace "urn:nokia.com:srlinux:linux:platform-cgroup";
  prefix srl_nokia-platform-cgroup;

  import srl_nokia-platform {
    prefix srl-platform;
  }
  import srl_nokia-extensions {
    prefix srl-ext;
  }
  import srl_nokia-platform-control {
    prefix srl-platform-control;
  }
  import srl_nokia-features {
    prefix srl_nokia-feat;
  }

  organization
    "Nokia";
  contact
    "Nokia SR Linux Support
     Web: <http://www.nokia.com>";
  description
    "This module defines configuration and operational state data related to cgroups.";

  revision 2026-07-31 {
    description
      "SRLinux 26.7.1";
  }
  revision 2024-03-31 {
    description
      "SRLinux 24.3.1";
  }
  revision 2022-03-31 {
    description
      "SRLinux 22.3.1";
  }
  revision 2021-03-31 {
    description
      "SRLinux 21.3.1";
  }

  grouping memory-event-top {
    description
      "Grouping for cgroup memory events";
    container memory-events {
      srl-ext:delivery-node-override "true";
      description
        "Enter the memory-events context

         Top-level container for cgroup memory events";
      leaf low {
        type uint64;
        description
          "The number of times the cgroup is reclaimed due to high memory pressure
           even though its usage is under the low boundary.";
      }
      leaf high {
        type uint64;
        description
          "The number of times processes of the cgroup are throttled and routed to perform direct memory reclaim
           because the high memory boundary was exceeded.";
      }
      leaf max {
        type uint64;
        description
          "The number of times the cgroup’s memory usage was about to go over the max boundary";
      }
      leaf oom {
        type uint64;
        description
          "The number of time the cgroup’s memory usage had reached the limit and allocation was about to fail";
      }
      leaf oom-kill {
        type uint64;
        description
          "The number of processes belonging to this cgroup killed by any kind of out-of-memory killer";
      }
    }
  }

  grouping memory-statistics-top {
    description
      "Grouping for cgroup memory statistics";
    container memory-statistics {
      config false;
      srl-ext:delivery-node-override "true";
      srl-ext:stream-mode "sample=5";
      description
        "Enter the memory-statistics context

         Top-level container for cgroup memory statistics";
      leaf current {
        type uint64;
        units "bytes";
        description
          "The total amount of memory currently being used by the cgroup and its descendants. Read from memory.current";
      }
      leaf current-swap {
        type uint64;
        units "bytes";
        description
          "The total amount of swap currently being used by the cgroup and its descendants. Read from memory.swap.current";
      }
      leaf anon {
        type uint64;
        units "bytes";
        description
          "Amount of memory used in anonymous mappings such as brk(), sbrk(), and mmap(MAP_ANONYMOUS)";
      }
      leaf kernel-stack {
        type uint64;
        units "bytes";
        description
          "Amount of memory allocated to kernel stacks";
      }
      leaf slab {
        type uint64;
        units "bytes";
        description
          "Amount of memory used for storing in-kernel data structures";
      }
      leaf sock {
        type uint64;
        units "bytes";
        description
          "Amount of memory used in network transmission buffers";
      }
      leaf anon-thp {
        type uint64;
        units "bytes";
        description
          "Amount of memory used in anonymous mappings backed by transparent hugepages";
      }
      leaf file {
        type uint64;
        units "bytes";
        description
          "Amount of memory used to cache filesystem data, including tmpfs and shared memory";
      }
      leaf file-writeback {
        type uint64;
        units "bytes";
        description
          "Amount of cached filesystem data that was modified and is currently being written back to disk";
      }
      leaf file-dirty {
        type uint64;
        units "bytes";
        description
          "Amount of cached filesystem data that was modified but not yet written back to disk";
      }
      uses memory-event-top;
    }
  }

  grouping cpuacct-statistics-top {
    description
      "Grouping for cgroup memory statistics";
    container cpuacct-statistics {
      config false;
      srl-ext:delivery-node-override "true";
      srl-ext:stream-mode "sample=5";
      description
        "Enter the cpuacct-statistics context

         Top-level container for cgroup cpuacct statistics";
      leaf user {
        type uint64;
        units "useconds";
        description
          "CPU usage user mode";
      }
      leaf system {
        type uint64;
        units "useconds";
        description
          "CPU usage user system";
      }
    }
  }

  grouping cgroup-state-top {
    description
      "Grouping for cgroup state";
    uses memory-statistics-top;
    uses cpuacct-statistics-top;
  }

  grouping memory-controller-top {
    description
      "Grouping for cgroup memory controller configuration";
    container memory-controller {
      description
        "Enter the memory-controller context

         Top-level container for cgroup memory controller configuration";
      leaf memory-max {
        type uint64;
        units "bytes";
        default "0";
        description
          "Memory limit for the cgroup. Write to this leaf to set the memory usage hard limit (memory.max) for the cgroup. Setting this leaf to 0 means no limit.";
      }
    }
  }

  grouping cpu-controller-top {
    description
      "Grouping for cgroup cpu controller configuration";
    container cpu-controller {
      description
        "Enter the cpu-controller context

         Top-level container for cgroup cpu controller configuration";
      leaf cpu-weight {
        type uint64 {
          range "1..10000";
        }
        default "100";
        description
          "CPU bandwidth weight for the cgroup. Write to this leaf to set the CPU bandwidth weight (cpu.weight) for the cgroup. The default value is 100.";
      }
      leaf cpu-max {
        type uint64 {
          range "0..100000";
        }
        default "0";
        description
          "CPU bandwidth limit for the cgroup. Write to this leaf to set the CPU bandwidth limit (cpu.max) for the cgroup. Setting this leaf to 0 means no limit. The PERIOD is set to 100000.
           Note: The configured quota is multiplied by number of available CPUs internally before setting the final value to cpu.max to scale across available system CPU resources.";
      }
    }
  }

  grouping cgroup-config-top {
    description
      "Grouping for cgroup configuration";
    uses memory-controller-top;
    uses cpu-controller-top;
  }

  grouping cgroup-top {
    description
      "Grouping for cgroup configuration and state";
    list cgroup {
      description
        "List of cgroups present in the system";
      key "name";
      leaf name {
        type string;
        description
          "Name of the cgroup, as defined by its directory location in the filesystem relative to the cgroup root.";
      }
      uses cgroup-state-top;
      uses cgroup-config-top {
        if-feature "srl_nokia-feat:containerz-cgroup";
      }
    }
  }

  augment "/srl-platform:platform/srl-platform-control:control" {
    uses cgroup-top;
  }
}
