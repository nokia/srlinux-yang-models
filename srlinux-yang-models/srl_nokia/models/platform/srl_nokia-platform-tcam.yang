module srl_nokia-platform-tcam {
  yang-version 1.1;
  namespace "urn:nokia.com:srlinux:chassis:platform-tcam";
  prefix srl_nokia-platform-tcam;

  import srl_nokia-common {
    prefix srl_nokia-comm;
  }
  import srl_nokia-extensions {
    prefix srl_nokia-ext;
  }
  import srl_nokia-platform {
    prefix srl_nokia-platform;
  }
  import srl_nokia-platform-lc {
    prefix srl_nokia-platform-lc;
  }
  import srl_nokia-platform-control-fp {
    prefix srl_nokia-platform-cfp;
  }
  import srl_nokia-platform-control {
    prefix srl_nokia-platform-control;
  }
  import srl_nokia-platform-resource-monitoring {
    prefix srl_nokia-platform-res-mon;
  }
  import srl_nokia-features {
    prefix srl_feat;
  }

  organization
    "Nokia";
  contact
    "Nokia SR Linux Support
     Web: <http://www.nokia.com>";
  description
    "This module defines configuration and operational state related to TCAM resources in the system";

  revision 2026-07-31 {
    description
      "SRLinux 26.7.1";
  }
  revision 2026-03-31 {
    description
      "SRLinux 26.3.1";
  }
  revision 2025-10-31 {
    description
      "SRLinux 25.10.1";
  }
  revision 2025-07-31 {
    description
      "SRLinux 25.7.1";
  }
  revision 2025-03-31 {
    description
      "SRLinux 25.3.1";
  }
  revision 2024-10-31 {
    description
      "SRLinux 24.10.1";
  }
  revision 2024-07-31 {
    description
      "SRLinux 24.7.1";
  }
  revision 2024-03-31 {
    description
      "SRLinux 24.3.1";
  }
  revision 2023-10-31 {
    description
      "SRLinux 23.10.1";
  }
  revision 2023-03-31 {
    description
      "SRLinux 23.3.1";
  }
  revision 2022-11-30 {
    description
      "SRLinux 22.11.1";
  }

  identity tcam-resources {
    description
      "Base type for TCAM resources";
  }

  identity tcam-cpm-resources {
    description
      "Base type for XDP-CPM TCAM resources";
  }

  identity match-action-ipv4 {
    if-feature "srl_feat:ixr-dnx-gen3 and srl_feat:policy-based-forwarding-match-action-type";
    base tcam-resources;
    description
      "Resource pool of TCAM entries used by match-action policies with IPv4 rules";
  }

  identity match-action-ipv6 {
    if-feature "srl_feat:ixr-dnx-gen3 and srl_feat:policy-based-forwarding-match-action-type";
    base tcam-resources;
    description
      "Resource pool of TCAM entries used by match-action policies with IPv6 rules";
  }

  identity if-input-ipv4 {
    base tcam-resources;
    base tcam-cpm-resources;
    description
      "Resource pool of TCAM entries used by IPv4 ACLs applied as subinterface-input filters";
  }

  identity if-output-ipv4 {
    if-feature "srl_feat:ixr-dnx";
    base tcam-resources;
    base tcam-cpm-resources;
    description
      "Resource pool of TCAM entries used by IPv4 ACLs applied as subinterface-output filters";
  }

  identity if-input-ipv6 {
    base tcam-resources;
    base tcam-cpm-resources;
    description
      "Resource pool of TCAM entries used by IPv6 ACLs applied as subinterface-input filters";
  }

  identity if-output-ipv6 {
    if-feature "srl_feat:ixr-dnx";
    base tcam-resources;
    base tcam-cpm-resources;
    description
      "Resource pool of TCAM entries used by IPv6 ACLs applied as subinterface-output filters";
  }

  identity cpm-capture-ipv4 {
    if-feature "srl_feat:ixr-dnx";
    base tcam-resources;
    base tcam-cpm-resources;
    description
      "Resource pool of TCAM entries used by IPv4 cpm-filter ACLs and capture-filter ACLs";
  }

  identity cpm-capture-ipv6 {
    if-feature "srl_feat:ixr-dnx";
    base tcam-resources;
    base tcam-cpm-resources;
    description
      "Resource pool of TCAM entries used by IPv6 cpm-filter ACLs and capture-filter ACLs";
  }

  identity system-capture-ipv4 {
    if-feature "srl_feat:trident3 or srl_feat:tomahawk5 or srl_feat:tomahawk6";
    base tcam-resources;
    description
      "Resource pool of TCAM entries used by IPv4 capture-filter ACLs and IPv4 system-filter ACLs";
  }

  identity system-capture-ipv6 {
    if-feature "srl_feat:trident3 or srl_feat:tomahawk5 or srl_feat:tomahawk6";
    base tcam-resources;
    description
      "Resource pool of TCAM entries used by IPv6 capture-filter ACLs and IPv6 system-filter ACLs";
  }

  identity system-capture {
    if-feature "srl_feat:trident4";
    base tcam-resources;
    description
      "Resource pool of TCAM entries used by IPv4 + IPv6 capture-filter ACLs and system-filter ACLs";
  }

  identity capture-ipv4 {
    if-feature "srl_feat:ac5x or srl_feat:tomahawk3 or srl_feat:tomahawk4";
    base tcam-resources;
    description
      "Resource pool of TCAM entries used by IPv4 capture-filter ACLs";
  }

  identity capture-ipv6 {
    if-feature "srl_feat:ac5x or srl_feat:tomahawk3 or srl_feat:tomahawk4";
    base tcam-resources;
    description
      "Resource pool of TCAM entries used by IPv6 capture-filter ACLs";
  }

  identity if-output-cpm-ipv4 {
    if-feature "srl_feat:ac5x or srl_feat:trident3 or srl_feat:tomahawk3 or srl_feat:tomahawk4 or srl_feat:fpcx";
    base tcam-resources;
    description
      "Resource pool of TCAM entries used by IPv4 egress ACLs and cpm-filter ACLs";
  }

  identity if-output-cpm-ipv6 {
    if-feature "srl_feat:ac5x or srl_feat:trident3 or srl_feat:tomahawk3 or srl_feat:tomahawk4 or srl_feat:fpcx";
    base tcam-resources;
    description
      "Resource pool of TCAM entries used by IPv6 egress ACLs and cpm-filter ACLs";
  }

  identity if-output-cpm {
    if-feature "srl_feat:trident4 or srl_feat:tomahawk5 or srl_feat:tomahawk6";
    base tcam-resources;
    description
      "Resource pool of TCAM entries used by IPv4 + IPv6 egress ACLs and cpm-filter ACLs";
  }

  identity if-input-mac {
    if-feature "srl_feat:ixr-dnx or srl_feat:ac5x or (srl_feat:trident3 and (not srl_feat:platform-7220-d1)) or srl_feat:trident4";
    base tcam-resources;
    description
      "Resource pool of TCAM entries used by MAC ACLs applied as subinterface-input filters";
  }

  identity if-output-mac {
    if-feature "srl_feat:ixr-dnx";
    base tcam-resources;
    description
      "Resource pool of TCAM entries used by MAC egress ACLs";
  }

  identity if-output-cpm-mac {
    if-feature "(srl_feat:trident3 and (not srl_feat:platform-7220-d1)) or srl_feat:trident4";
    base tcam-resources;
    description
      "Resource pool of TCAM entries used by MAC egress ACLs and MAC cpm-filter ACLs";
  }

  identity policy-forwarding-vrf-selection-ipv4 {
    if-feature "srl_feat:policy-based-forwarding-dscp-ip-protocol and srl_feat:ixr-dnx";
    base tcam-resources;
    base tcam-cpm-resources;
    description
      "Resource pool of TCAM entries used by IPv4 policy-forwarding entries that redirect flows to a different network-instance";
  }

  identity policy-forwarding-vrf-selection-ipv6 {
    if-feature "srl_feat:policy-based-forwarding-decap-actions and srl_feat:ixr-dnx";
    base tcam-resources;
    base tcam-cpm-resources;
    description
      "Resource pool of TCAM entries used by IPv6 policy-forwarding entries that redirect flows to a different network-instance";
  }

  identity policy-forwarding-nhg-ipv4 {
    if-feature "srl_feat:dynamic-tcam";
    base tcam-resources;
    base tcam-cpm-resources;
    description
      "Resource pool of TCAM entries used by IPv4 policy-forwarding entries that redirect flows to a NHG of IP next-hops or tunnels

       On TD4 systems IPv6 policy-forwarding entries share this resource with IPv4 entries.";
  }

  identity policy-forwarding-nhg-ipv6 {
    if-feature "srl_feat:dynamic-tcam and (not srl_feat:trident4)";
    base tcam-resources;
    base tcam-cpm-resources;
    description
      "Resource pool of TCAM entries used by IPv6 policy-forwarding entries that redirect flows to a NHG of IP next-hops or tunnels";
  }

  identity if-input-policer {
    if-feature "srl_feat:ingress-subif-policing";
    base tcam-resources;
    description
      "Resource pool of TCAM entries used by ingress subinterface policer templates";
  }

  identity if-input-ipv4-qos {
    if-feature "srl_feat:ip-qos-multifield";
    base tcam-resources;
    description
      "Resource pool of TCAM entries associated with IPv4 multi-field QoS classification entries, when applied to subinterface input";
  }

  identity if-input-ipv6-qos {
    if-feature "srl_feat:ip-qos-multifield";
    base tcam-resources;
    description
      "Resource pool of TCAM entries associated with IPv6 multi-field QoS classification entries, when applied to subinterface input";
  }

  identity mrouter-mfib-redirect {
    if-feature "srl_feat:platform-7220-d2 or srl_feat:platform-7220-d3 or srl_feat:trident4";
    base tcam-resources;
    description
      "Resource pool of TCAM entries used by multicast snooping protocols in MAC-VRF network-instances

       One TCAM entry is used per multicast snooping protocol enabled in a MAC-VRF. For instance,
       if igmp-snooping and mld-snooping are enabled on a MAC-VRF, two entries are used. If only
       igmp-snooping is enabled, only one entry is used.";
  }

  identity tunnel-decap-ipv4-ipv6 {
    if-feature "srl_feat:ip-tunnel-decap-groups";
    base tcam-resources;
    description
      "Resource pool of TCAM entries used for IPv4 and IPv6 tunnel-decapsulation groups";
  }

  identity if-output-evpn-mh-multicast-non-df {
    if-feature "srl_feat:evpn-mh-multicast-non-df-tcam-resource";
    base tcam-resources;
    description
      "Resource pool of TCAM entries used by egress filtering of IP multicast traffic to non-Designated Forwarder subinterfaces

       One TCAM entry is used when multicast snooping protocols are enabled on at least one MAC-VRF that
       has one or more subinterfaces associated with Ethernet Segments.";
  }

  identity dot1x-multi-host-authentication-guard {
    if-feature "srl_feat:dot1x-authenticator-multi-host-auth-tcam-res-mgmt";
    base tcam-resources;
    description
      "Resource pool of TCAM entries used for dot1x multi host authentication

       This is used for any protocol that uses multi host including dot1x or MBA.";
  }

  identity input-first-hop-security-ip-source-guard {
    if-feature "srl_feat:first-hop-security and srl_feat:future-0-0";
    base tcam-resources;
    description
      "Resource pool of TCAM entries used for IP source guard.";
  }

  identity input-first-hop-security-ipv4-source-guard {
    if-feature "srl_feat:first-hop-security and srl_feat:trident3";
    base tcam-resources;
    description
      "Resource pool of TCAM entries used for IPv4 source guard entries.";
  }

  identity input-first-hop-security-ipv6-source-guard {
    if-feature "srl_feat:first-hop-security and srl_feat:trident3";
    base tcam-resources;
    description
      "Resource pool of TCAM entries used for IPv6 source guard entries.";
  }

  identity gbp-ingress {
    if-feature "srl_feat:group-based-policy";
    base tcam-resources;
    description
      "Resource pool of TCAM entries used for Group Based Policy entries.";
  }

  identity combined-ecmp-redirect {
    if-feature "srl_feat:combined-ecmp-redirect";
    base tcam-resources;
    description
      "Resource pool of TCAM entries used for combined ECMP and gateway-IP load balancing with data path egress filtering

       One TCAM entry is used per NHG for combined ECMP and gateway-IP load balancing with data path egress filtering.
       The TCAM entry is used to override the ECMP group ID obtained from route lookup with an alternate ECMP group containing
       only access next hops.";
  }

  grouping tcam-resource-monitoring {
    container tcam {
      list resource {
        key "name";
        leaf name {
          type identityref {
            base tcam-resources;
          }
          description
            "The name of the TCAM resource";
        }
        leaf rising-threshold-log {
          type srl_nokia-comm:percentage;
          default "90";
          description
            "Sets the threshold that triggers the generation of a WARNING log whenever the utilization of the TCAM resource in any linecard/complex/core reaches this value in a rising direction

             On platforms that support dynamic TCAM the utilization considers both free-dynamic and free-static.";
        }
        leaf falling-threshold-log {
          type srl_nokia-comm:percentage;
          default "70";
          description
            "Sets the threshold that triggers the generation of a NOTICE log whenever the utilization of the TCAM resource in any linecard/complex/core falls reaches this value in a falling direction.

             On platforms that support dynamic TCAM the utilization considers both free-dynamic and free-static.";
        }
      }
      description
        "Enter the tcam context";
    }
  }

  grouping tcam-utilization {
    container tcam {
      config false;
      list resource {
        srl_nokia-ext:delivery-node-override "true";
        srl_nokia-ext:stream-mode "sample=5";
        key "name";
        leaf name {
          type identityref {
            base tcam-resources;
          }
          description
            "The name of the TCAM resource";
        }
        leaf free-static {
          type uint32;
          description
            "The number of available and unused TCAM entries for the entry type, assuming that the number of dynamic TCAM slices that are currently allocated to the entry type remains constant at its current value.";
        }
        leaf free-dynamic {
          if-feature "srl_feat:dynamic-tcam";
          type uint32;
          description
            "The number of available and unused TCAM entries for the entry type, assuming that all the remaining unused TCAM slices would be dynamically allocated to this one type of entry (subject to chip level constraints on the placement of double-wide and triple-wide TCAM slice groups).";
        }
        leaf requested {
          if-feature "srl_feat:algorithmic-tcam";
          type uint32;
          description
            "The number of logical uncompressed TCAM entries requested by config in this resource pool.";
        }
        leaf reserved {
          type uint32;
          description
            "The number of TCAM entries that are currently reserved in this resource pool. Reservation happens when a configuration change is committed. Reserved entries may not be programmed yet if the commit has just occurred.";
        }
        leaf programmed {
          type uint32;
          description
            "The number of TCAM entries belonging to this resource that are currently programmed into hardware. When the number of programmed entries equals the number of reserved entries HW programming of this resource type has finished.";
        }
      }
      description
        "Enter the tcam context";
    }
  }

  grouping cpm-tcam-utilization {
    container tcam {
      config false;
      list resource {
        srl_nokia-ext:delivery-node-override "true";
        srl_nokia-ext:stream-mode "sample=5";
        key "name";
        leaf name {
          type identityref {
            base tcam-cpm-resources;
          }
          description
            "The name of the TCAM resource";
        }
        leaf free {
          type uint32;
          description
            "The number of available and unused TCAM entries for the entry type, assuming that the maximum number of dynamic TCAM slices are allocated";
        }
        leaf requested {
          if-feature "srl_feat:algorithmic-tcam";
          type uint32;
          description
            "The number of logical uncompressed TCAM entries requested by config in this resource pool.";
        }
        leaf reserved {
          type uint32;
          description
            "The number of TCAM entries that are currently reserved in this resource pool. Reservation happens when a configuration change is committed. Reserved entries may not be programmed yet if the commit has just occurred.";
        }
        leaf programmed {
          type uint32;
          description
            "The number of TCAM entries belonging to this resource that are currently programmed into hardware. When the number of programmed entries equals the number of reserved entries HW programming of this resource type has finished.";
        }
      }
      description
        "Enter the tcam context";
    }
  }

  augment "/srl_nokia-platform:platform/srl_nokia-platform-res-mon:resource-monitoring" {
    uses tcam-resource-monitoring;
  }

  augment "/srl_nokia-platform:platform/srl_nokia-platform-lc:linecard/srl_nokia-platform-lc:forwarding-complex" {
    uses tcam-utilization;
  }

  augment "/srl_nokia-platform:platform/srl_nokia-platform-control:control/srl_nokia-platform-cfp:forwarding-plane" {
    if-feature "srl_feat:cpm-datapath-resources";
    uses cpm-tcam-utilization;
  }
}
