module srl_nokia-platform-psu {
  yang-version 1.1;
  namespace "urn:nokia.com:srlinux:chassis:platform-psu";
  prefix srl_nokia-platform-psu;

  import srl_nokia-platform {
    prefix srl-platform;
  }
  import srl_nokia-common {
    prefix srl-comm;
  }
  import srl_nokia-extensions {
    prefix srl-ext;
  }
  import srl_nokia-features {
    prefix srl-feat;
  }

  organization
    "Nokia";
  contact
    "Nokia SR Linux Support
     Web: <http://www.nokia.com>";
  description
    "This module defines configuration and operational state data related to power supplies.";

  revision 2026-07-31 {
    description
      "SRLinux 26.7.1";
  }
  revision 2025-10-31 {
    description
      "SRLinux 25.10.1";
  }
  revision 2025-03-31 {
    description
      "SRLinux 25.3.1";
  }
  revision 2024-03-31 {
    description
      "SRLinux 24.3.1";
  }
  revision 2023-07-31 {
    description
      "SRLinux 23.7.1";
  }
  revision 2021-03-31 {
    description
      "SRLinux 21.3.1";
  }
  revision 2019-11-30 {
    description
      "SRLinux 19.11.1";
  }

  grouping psu-input-output-common {
    description
      "Grouping of common fields used with both input and output";
    leaf voltage {
      description
        "Current voltage input/output for the power-supply";
      units "volts";
      type decimal64 {
        fraction-digits 2;
      }
    }
    leaf current {
      description
        "Current amperage input/output for the power-supply";
      units "amps";
      type decimal64 {
        fraction-digits 2;
      }
    }
    leaf power {
      description
        "Current power input/output for the power-supply";
      units "watts";
      type decimal64 {
        fraction-digits 2;
      }
    }
  }

  grouping psu-state-top {
    description
      "Grouping for power supply module state";
    leaf id {
      type uint8 {
        range "1..255";
      }
      description
        "Numeric identifier for the power supply module";
    }
    leaf type {
      type string;
      srl-ext:show-importance "high";
      description
        "Power-supply type, as translated from the components EEPROM";
    }
    leaf capacity {
      type uint32;
      srl-ext:show-importance "low";
      description
        "The total capacity the power supply module can provide";
      units "watts";
    }
    container fan {
      if-feature "srl-feat:platform-7250-ixr or srl-feat:platform-7250-ixr-e-unified or srl-feat:platform-7250-ixr-18e-unified";
      description
        "Enter the fan context

         Top-level container for state relating to fans";
      leaf speed {
        type srl-comm:percentage;
        description
          "The current speed of the fan";
      }
      leaf speed-rpm {
        type uint16;
        description
          "The current RPM of the fan";
      }
    }
    container input {
      srl-ext:delivery-node-override "true";
      srl-ext:stream-mode "sample=5";
      description
        "Enter the input context

         Top-level container for power-supply input state";
      uses psu-input-output-common;
    }
    container output {
      if-feature "srl-feat:platform-7250-ixr or srl-feat:platform-7250-ixr-e-unified or srl-feat:platform-7250-ixr-18e-unified";
      srl-ext:delivery-node-override "true";
      srl-ext:stream-mode "sample=5";
      description
        "Enter the output context

         Top-level container for power-supply output state";
      uses psu-input-output-common;
    }
    list feed {
      if-feature "srl-feat:platform-7250-ixr-e-unified or srl-feat:platform-7250-ixr-18e-unified";
      key "id";
      description
        "List of feeds on this power-supply";
      leaf id {
        type uint8;
        description
          "ID of the feed";
      }
      leaf voltage {
        description
          "Current input voltage for this feed";
        units "volts";
        type decimal64 {
          fraction-digits 2;
        }
      }
      leaf current {
        description
          "Current input amperage of this feed";
        units "amps";
        type decimal64 {
          fraction-digits 2;
        }
      }
    }
    leaf oper-reason {
      description
        "Indicates the reason for the current state of the component";
      type enumeration {
        enum no-input/fault {
          description
            "No power input, or other hardware fault detected";
        }
        enum eeprom-invalid {
          description
            "EEPROM of this power supply is either invalid or corrupt";
        }
        enum airflow-mismatch {
          description
            "The detected airflow of this power supply does not match the system-calculated airflow direction

             The logic for determining the system-calculated direction is:
             - Majority wins between present fan trays
             - In the case where there are equal F2B or B2F fan-trays, PSUs are used as a tie break (PSUs only are counted in the event a tie breaker is needed)
             - F2B wins if no tie break can be used";
        }
      }
    }
  }

  grouping psu-top {
    description
      "Grouping for power supply module configuration and state";
    list power-supply {
      config false;
      key "id";
      description
        "Top-level container for power supply module configuration and state";
      uses psu-state-top;
      uses srl-platform:component-common-state-top;
      uses srl-platform:component-common-eeprom;
      uses srl-platform:component-temperature-no-thresh-state-top;
    }
  }

  augment "/srl-platform:platform" {
    uses psu-top;
  }
}
