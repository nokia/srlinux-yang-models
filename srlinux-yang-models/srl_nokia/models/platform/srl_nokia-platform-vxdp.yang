module srl_nokia-platform-vxdp {
  yang-version 1.1;
  namespace "urn:nokia.com:srlinux:chassis:platform-vxdp";
  prefix srl_nokia-platform-vxdp;

  import srl_nokia-common {
    prefix srl-comm;
  }
  import srl_nokia-features {
    prefix srl-feat;
  }
  import srl_nokia-platform {
    prefix srl-plat;
  }
  import srl_nokia-platform-chassis {
    prefix srl-plat-chassis;
  }
  import srl_nokia-platform-cpu {
    prefix srl-cpu;
  }

  organization
    "Nokia";
  contact
    "Nokia SR Linux Support
     Web: <http://www.nokia.com>";
  description
    "This module defines configuration and operational state data related to vXDP";

  revision 2026-07-31 {
    description
      "SRLinux 26.7.1";
  }
  revision 2026-03-31 {
    description
      "SRLinux 26.3.1";
  }
  revision 2022-11-30 {
    description
      "SRLinux 22.11.1";
  }
  revision 2021-11-30 {
    description
      "SRLinux 21.11.1";
  }

  grouping cpu-idle {
    description
      "Definition of idle CPU leaf";
    leaf idle {
      description
        "The aggregate idle percentage of threads";
      type srl-comm:percentage;
    }
  }

  grouping vxdp-config-top {
    description
      "Grouping for vXDP configuration";
    leaf-list cpu-set {
      min-elements 1;
      description
        "The list of CPUs used for vXDP PMD threads

         These CPUs should be isolated out-of-band of SR Linux, and are used for forwarder and NIC threads for vhost-user, physical, and lif interfaces.
         It is expected that the sibling of a CPU is always passed to vXDP, and in order to enforce this if a single CPU of a core is passed, vXDP will derive and bind to the undefined sibling. vXDP supports the passing of both single and both siblings together, and will perform a merge to ensure all siblings are consumed.";
      type uint16 {
        range "0..1024";
      }
    }
  }

  grouping vxdp-state-top {
    description
      "Grouping for vXDP state";
    list cpu {
      config false;
      key "id";
      description
        "State information relating to the list of CPUs pinned to vXDP threads";
      leaf id {
        description
          "Reference to a CPU within the configured cpu-set";
        type uint16;
      }
      leaf oper-state {
        description
          "The operational state of the CPU";
        type srl-comm:oper-state;
      }
      leaf oper-reason {
        description
          "The reason (if any) that this CPU is in its current operational state";
        type enumeration {
          enum not-isolated;
          enum no-hugepages;
          enum irq-not-masked;
          enum sibling-not-isolated;
          enum invalid-cpu-id;
        }
      }
      leaf socket-id {
        description
          "The socket this CPU resides on";
        type uint8;
      }
      leaf core-id {
        description
          "The physical core this CPU resides on";
        type uint8;
      }
      leaf sibling-id {
        description
          "The sibling CPU (if any) residing on the same core";
        type uint16;
      }
    }
    container statistics {
      config false;
      description
        "Enter the statistics context

         Top-level container for statistics relating to vXDP thread utilization";
      container nic {
        description
          "Enter the nic context

           Top-level container for NIC thread statistics";
        uses cpu-idle;
        uses srl-cpu:per-type-statistics;
      }
      container forwarder {
        description
          "Enter the forwarder context

           Top-level container for forwarder thread statistics";
        uses cpu-idle;
        uses srl-cpu:per-type-statistics;
      }
    }
  }

  grouping vxdp-top {
    description
      "Grouping for vXDP configuration and state";
    container vxdp {
      presence "Enable vXDP - requiring a cpu-set to be configured";
      description
        "Top-level container for vXDP configuration and state";
      if-feature "srl-feat:vsrl-generic-hw";
      uses vxdp-config-top;
      uses vxdp-state-top;
    }
  }

  augment "/srl-plat:platform" {
    uses vxdp-top;
  }

  augment "/srl-plat:platform/srl-plat-chassis:chassis" {
    if-feature "srl-feat:platform-vsrl";
    leaf uuid {
      type srl-comm:uuid;
      description
        "The system-generated or user-configured UUID for the chassis";
    }
    leaf mac-address-allocation {
      type uint32 {
        range "1..8192";
      }
      description
        "The number of MAC addresses to generate from the chassis MAC address

         These MAC addresses are used for interfaces that need MAC addresses generated by the system.";
      default "1024";
    }
    leaf mac-address {
      type srl-comm:mac-address;
      description
        "The configured or derived MAC address of the chassis

         If not configured, this is set to the hw-mac-address, which is populated depending on system type:

         - For systems with a discoverable chassis MAC address (either populated by an external system or present in hardware) the discovered value is populated.
         - For systems without a discoverable MAC address, the address is generated from a hash of the systems UUID.

         When deleted, will revert back to the value of hw-mac-address.

         This MAC address is used by the system as a base to generate MAC addresses for interfaces (when needed).";
    }
  }
}
