module srl_nokia-platform-redundancy {
  yang-version 1.1;
  namespace "urn:nokia.com:srlinux:chassis:platform-redundancy";
  prefix srl_nokia-platform-redundancy;

  import srl_nokia-common {
    prefix srl-comm;
  }
  import srl_nokia-platform {
    prefix srl-platform;
  }
  import srl_nokia-features {
    prefix srl-feat;
  }

  organization
    "Nokia";
  contact
    "Nokia SR Linux Support
     Web: <http://www.nokia.com>";
  description
    "This module defines configuration and operational state data related platform redundancy.";

  revision 2026-07-31 {
    description
      "SRLinux 26.7.1";
  }
  revision 2026-03-31 {
    description
      "SRLinux 26.3.1";
  }
  revision 2025-10-31 {
    description
      "SRLinux 25.10.1";
  }
  revision 2025-07-31 {
    description
      "SRLinux 25.7.1";
  }
  revision 2025-03-31 {
    description
      "SRLinux 25.3.1";
  }
  revision 2024-10-31 {
    description
      "SRLinux 24.10.1";
  }
  revision 2021-03-31 {
    description
      "SRLinux 21.3.1";
  }
  revision 2020-06-30 {
    description
      "SRLinux 20.6.1";
  }
  revision 2019-11-30 {
    description
      "SRLinux 19.11.1";
  }

  typedef sync-options {
    type enumeration {
      enum overlay {
        description
          "Synchronize all system, as well as ancillary files";
      }
      enum system {
        description
          "Synchronize system-related data only";
      }
    }
  }

  typedef sync-state {
    type enumeration {
      enum synchronized {
        description
          "Standby control module is ready and synchronized";
      }
      enum synchronizing {
        description
          "Standby control module is currently synchronizing";
      }
      enum not-ready {
        description
          "Standby control module is not synchronized";
      }
    }
  }

  grouping redundancy-state-top {
    description
      "Grouping for global redundancy operational state";
    leaf active-module {
      type enumeration {
        enum A;
        enum B;
      }
      config false;
      description
        "Control module currently active";
    }
    leaf failover-time {
      type srl-comm:date-and-time-delta;
      config false;
      description
        "Date and time of the last control module failover";
    }
  }

  grouping redundancy-synchronization-top {
    container synchronization {
      description
        "Enter the synchronization context

         Top-level container for redundancy synchronization";
      leaf state {
        type sync-state;
        config false;
        description
          "Current synchronization status";
      }
      leaf state-reason {
        if-feature "srl-feat:application-hot-restart";
        type string;
        config false;
        description
          "One or more reasons separated by semicolons for the current synchronization state

           This field is not populated when synchronized.";
      }
      leaf last-synchronization {
        type srl-comm:date-and-time-delta;
        config false;
        description
          "Last date and time a synchronization of system files occurred";
      }
      container overlay {
        description
          "Enter the overlay context

           Top-level container for overlay synchronization";
        leaf synchronization-frequency {
          type uint32 {
            range "30..65535";
          }
          default "60";
          units "seconds";
          description
            "Sets the frequency of overlay synchronizations

             This has no effect if overlay is not a configured synchronization mode. Changing this value results in the timer to the next synchronization being reset.";
        }
        leaf last-synchronization {
          config false;
          type srl-comm:date-and-time-delta;
          description
            "Last date and time a synchronization of the overlay occurred";
        }
        leaf next-synchronization {
          config false;
          type srl-comm:date-and-time-delta;
          description
            "Next date and time a synchronization of the overlay will occur";
        }
      }
    }
  }

  grouping redundancy-configuration-top {
    description
      "Grouping for global redundancy configuration";
  }

  grouping redundancy-top {
    description
      "Grouping for global redundancy configuration and state";
    container redundancy {
      description
        "Enter the redundancy context

         Top-level container for platform redundancy";
      container control-plane {
        if-feature "srl-feat:redundant-cpms";
        description
          "Enter the control-plane context

           Top-level container for control plane redundancy";
        uses redundancy-configuration-top;
        uses redundancy-state-top;
        uses redundancy-synchronization-top;
      }
      container linecard {
        if-feature "srl-feat:cpiom-linecard-redundancy";
        list iom {
          config false;
          description
            "Top-level container for line card redundancy";
          key "cpiom";
          leaf cpiom {
            type enumeration {
              enum A;
              enum B;
            }
            description
              "Linecard";
          }
          leaf-list mda-binding {
            type string {
              length "1";
            }
            config false;
            description
              "MDAs serviced via given Line Card";
          }
          leaf forwarding-since {
            type srl-comm:date-and-time-delta;
            config false;
            description
              "Date and time since given IOM is in active forwarding mode. Can be forwarding for half of the node or can be forwarding for the entire node";
          }
        }
        leaf forwarding-takeover {
          type boolean;
          default "true";
          description
            "The behavior when an inactive line card boots up and reconciles with active one

             Set to false and forwarding for all MDAs remain on the active line card, forwarding is not shared with newly active line card.
             Set to true and forwarding for half of the MDAs to be passed to newly active line card as soon as both CPIOMs are in full sync.

             When both CPIOMs are booting, typically a chassis reboot, each CPIOM attempt ownership of forwarding operations for half of the MDAs, unless the first CPIOM times out waiting for boot completion of the other CPIOM.
             If the first CPIOM times out, then the second CPIOM assumes forwarding operations of all MDAs.
             When CPM and IOM sync is completed among two CPIOMs and if forwarding-takeover is enabled, half of the MDAs are re-homed and forwarding is shared among two CPIOMs";
        }
        leaf forwarder {
          config false;
          type enumeration {
            enum iom-A {
              description
                "Forwarding functionality for all MDAs is handled via IOM A.
                 When a new MDA is plugged in, iom A assumes forwarding functionality.";
            }
            enum iom-B {
              description
                "Forwarding functionality for all MDAs is handled via IOM B.
                 When a new MDA is plugged in, iom B assumes forwarding functionality.";
            }
            enum both {
              description
                "Forwarding functionality is distributed among iom A and iom B. Each IOM owns the forwarding operations for half of the MDAs.
                 When a new MDA is plugged in, distributed ownership model is maintained. Forwarding for MDAs in odd slots is carried out via iom A whereas iom B is the forwarding owner for MDAs in even slots.";
            }
          }
          description
            "Displays the forwarding ownership for the node.";
        }
        description
          "Enter the linecard context";
      }
    }
  }

  augment "/srl-platform:platform" {
    if-feature "srl-feat:redundant-cpms or srl-feat:cpiom-linecard-redundancy";
    uses redundancy-top;
  }
}
