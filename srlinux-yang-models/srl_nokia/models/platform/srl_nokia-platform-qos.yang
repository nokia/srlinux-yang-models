module srl_nokia-platform-qos {
  yang-version 1.1;
  namespace "urn:nokia.com:srlinux:chassis:platform-qos";
  prefix srl_nokia-platform-qos;

  import srl_nokia-common {
    prefix srl_nokia-comm;
  }
  import srl_nokia-platform {
    prefix srl_nokia-platform;
  }
  import srl_nokia-platform-lc {
    prefix srl_nokia-platform-lc;
  }
  import srl_nokia-platform-resource-monitoring {
    prefix srl_nokia-platform-res-mon;
  }
  import srl_nokia-features {
    prefix srl-feat;
  }
  import srl_nokia-extensions {
    prefix srl-ext;
  }

  organization
    "Nokia";
  contact
    "Nokia SR Linux Support
     Web: <http://www.nokia.com>";
  description
    "This module defines configuration and operational state related to QoS resources in the system";

  revision 2026-07-31 {
    description
      "SRLinux 26.7.1";
  }
  revision 2026-03-31 {
    description
      "SRLinux 26.3.1";
  }
  revision 2025-10-31 {
    description
      "SRLinux 25.10.1";
  }
  revision 2025-07-31 {
    description
      "SRLinux 25.7.1";
  }
  revision 2025-03-31 {
    description
      "SRLinux 25.3.1";
  }
  revision 2024-10-31 {
    description
      "SRLinux 24.10.1";
  }
  revision 2024-07-31 {
    description
      "SRLinux 24.7.1";
  }
  revision 2024-03-31 {
    description
      "SRLinux 24.3.1";
  }
  revision 2023-10-31 {
    description
      "SRLinux 23.10.1";
  }
  revision 2023-03-31 {
    description
      "SRLinux 23.3.1";
  }
  revision 2022-11-30 {
    description
      "SRLinux 22.11.1";
  }
  revision 2022-03-31 {
    description
      "SRLinux 22.3.1";
  }
  revision 2021-11-30 {
    description
      "SRLinux 21.11.1";
  }
  revision 2021-06-30 {
    description
      "SRLinux 21.6.1";
  }
  revision 2021-03-31 {
    description
      "SRLinux 21.3.1";
  }
  revision 2020-06-30 {
    description
      "SRLinux 20.6.1";
  }
  revision 2019-11-30 {
    description
      "SRLinux 19.11.1";
  }

  identity qos-resources {
    description
      "Base type for QoS resources";
  }

  identity core-qos-resources {
    description
      "Base type for per-core QoS resources";
  }

  identity classifier-profiles {
    if-feature "srl-feat:ixr-dnx";
    base qos-resources;
    description
      "A classifier-profile resource is used every time a different combination of IPv4 DSCP classifier and IPv6 DSCP classifier is applied to an ingress subinterface. One is always used by the combination of the default IPv4 DSCP classifier and the default IPv6 DSCP classifier.";
  }

  identity rewrite-profiles {
    if-feature "srl-feat:ixr-dnx or srl-feat:fpcx";
    base qos-resources;
    description
      "A rewrite-profile resource is used every time a different combination of IPv4 DSCP rewrite-rule and IPv6 DSCP rewrite-rule is applied to an egress subinterface.";
  }

  identity dscp-classifier-policies {
    if-feature "srl-feat:qos-dscp-classifier-policy";
    base qos-resources;
    description
      "Every user-defined DSCP classifier policy that is configured uses one of these resources";
  }

  identity dscp-mpls-rewrite-policies {
    if-feature "srl-feat:ixr-dnx";
    base qos-resources;
    description
      "A rewrite-policy resource is used every time a different DSCP or MPLS traffic-class rewrite-rule policy is applied to an egress subinterface.";
  }

  identity mpls-classifier-policies {
    if-feature "srl-feat:fpcx";
    base qos-resources;
    description
      "Every user-defined mpls traffic class classifier policy that is configured uses one of these resources";
  }

  identity mpls-rewrite-policies {
    if-feature "srl-feat:fpcx";
    base qos-resources;
    description
      "An mpls-rewrite-policy resource is used every time a different MPLS traffic-class rewrite-rule policy is applied to at least one egress subinterface on this forwarding-complex.";
  }

  identity dscp-rewrite-policies {
    if-feature "srl-feat:qos-dscp-rewrite-policy";
    base qos-resources;
    description
      "Every user-defined dscp rewrite policy that is configured uses one of these resources.";
  }

  identity dot1p-classifier-policies {
    if-feature "srl-feat:qos-dot1p-classifier-policy";
    base qos-resources;
    description
      "Every user-defined dot1p classifier policy that is configured uses one of these resources";
  }

  identity dot1p-rewrite-policies {
    if-feature "srl-feat:qos-dot1p-rewrite-policy";
    base qos-resources;
    description
      "Every user-defined dot1p rewrite policy that is configured uses one of these resources";
  }

  identity input-policers {
    if-feature "srl-feat:qos-policer-policies";
    base qos-resources;
    description
      "Every input-policer that is allocated to the configured subinterfaces based on input-class-map";
  }

  identity output-class-maps {
    if-feature "srl-feat:qos-output-class-map";
    base qos-resources;
    description
      "Every output class map that is applied to at least one egress subinterface on this forwarding-complex, uses one of these resources.";
  }

  identity slope-policies {
    if-feature "srl-feat:qos-slope-policy";
    base qos-resources;
    description
      "Every user-defined qos buffer management slope policy that is configured uses one of these resources";
  }

  identity input-class-maps {
    if-feature "srl-feat:qos-input-class-map";
    base qos-resources;
    description
      "Every qos input class map that is applied to at least one qos subinterface input on this forwarding-complex, uses one of these resources.";
  }

  identity dscp-reclassify-policies {
    if-feature "srl-feat:qos-dscp-reclassifier-policy";
    base qos-resources;
    description
      "Every user-defined dscp reclassify policy that is configured uses one of these resources";
  }

  identity ip-rewrite-policies {
    if-feature "srl-feat:qos-ip-rewrite-policy";
    base qos-resources;
    description
      "Every user-defined ip rewrite policy that is configured uses one of these resources";
  }

  identity voq-connector-set {
    if-feature "srl-feat:qos-subinterface-queuing";
    base core-qos-resources;
    description
      "VoQ connector set resources allocated per core

       Each subinterface that has per-subinterface queuing enabled consumes one voq-connector-set
       on every core that hosts an interface in the subinterface's parent interface or LAG. A
       voq-connector-set represents the per-core hardware resource that connects a global VoQ-id
       to the local set of 8 queues on that core.";
  }

  grouping qos-resource-monitoring {
    container qos {
      srl-ext:delivery-node-override "true";
      srl-ext:stream-mode "sample=5";
      list resource {
        key "name";
        leaf name {
          type identityref {
            base qos-resources;
          }
          description
            "The name of the QoS resource";
        }
        leaf rising-threshold-log {
          type srl_nokia-comm:percentage;
          default "90";
          description
            "Sets the threshold that triggers the generation of a WARNING log whenever the utilization of the QoS resource in any linecard/complex/core reaches this value in a rising direction";
        }
        leaf falling-threshold-log {
          type srl_nokia-comm:percentage;
          default "70";
          description
            "Sets the threshold that triggers the generation of a NOTICE log whenever the utilization of the QoS resource in any linecard/complex/core falls reaches this value in a falling direction";
        }
      }
      description
        "Enter the qos context";
    }
  }

  grouping core-qos-resource-monitoring {
    container core {
      container qos {
        srl-ext:delivery-node-override "true";
        srl-ext:stream-mode "sample=5";
        list resource {
          key "name";
          leaf name {
            type identityref {
              base core-qos-resources;
            }
            description
              "The name of the per-core QoS resource";
          }
          leaf rising-threshold-log {
            type srl_nokia-comm:percentage;
            default "90";
            description
              "Sets the threshold that triggers the generation of a WARNING log whenever the utilization of the per-core QoS resource in any linecard/complex/core reaches this value in a rising direction";
          }
          leaf falling-threshold-log {
            type srl_nokia-comm:percentage;
            default "70";
            description
              "Sets the threshold that triggers the generation of a NOTICE log whenever the utilization of the per-core QoS resource in any linecard/complex/core falls reaches this value in a falling direction";
          }
        }
        description
          "Enter the qos context";
      }
      description
        "Enter the core context";
    }
  }

  grouping scheduling-resources-utilization {
    list resource-set-pool {
      key "index";
      leaf index {
        type uint8 {
          range "0..1";
        }
        description
          "Resource-set-pool resources for the given forwarding-complex

           Contains resource-group resources.";
      }
      container resource-groups {
        leaf used {
          type uint32;
          description
            "The number of resource-groups that are in use";
        }
        leaf free {
          type uint32;
          description
            "The number of resource-groups that are unused and available";
        }
        description
          "Enter the resource-groups context";
      }
      list interface-group-resource-pool {
        key "index";
        leaf index {
          type uint8 {
            range "0..15";
          }
        }
        description
          "Interface-group-resource-pool resources for the given resource-set-pool

           Contains the resource-groups which have been allocated to this interface-group-resource-pool.";
        list resource-group {
          key "index";
          leaf index {
            type uint8 {
              range "0..61";
            }
          }
          description
            "Resource-group resources for the given interface-group-resource-pool

             Describes the number of resource-sets used and free within the resource-group.
             A resource-set consists of 1 output-queue, and 1 tier-0 queue-scheduler, which is allocated to every configured subinterface.";
          container resource-sets {
            leaf used {
              type uint32;
              description
                "The number of resource-sets that are in use";
            }
            leaf free {
              type uint32;
              description
                "The number of resource-sets that are unused and available";
            }
            description
              "Enter the resource-sets context";
          }
        }
        container tier-0-schedulers {
          leaf used {
            type uint32;
            description
              "The number of tier 0 schedulers that are in use by virtual interfaces";
          }
          leaf free {
            type uint32;
            description
              "The number of tier 0 schedulers that are unused and available";
          }
          description
            "Enter the tier-0-schedulers context";
        }
        container tier-1-schedulers {
          leaf used {
            type uint32;
            description
              "The number of tier 1 schedulers that are in use by virtual interfaces";
          }
          leaf free {
            type uint32;
            description
              "The number of tier 1 schedulers that are unused and available";
          }
          description
            "Enter the tier-1-schedulers context";
        }
      }
    }
  }

  grouping qos-utilization {
    container qos {
      srl-ext:delivery-node-override "true";
      srl-ext:stream-mode "sample=5";
      config false;
      list resource {
        key "name";
        leaf name {
          type identityref {
            base qos-resources;
          }
          description
            "The name of the QoS resource";
        }
        leaf used {
          type uint32;
          description
            "The number of resources that are in use";
        }
        leaf free {
          type uint32;
          description
            "The number of resources that are unused and available";
        }
      }
      uses scheduling-resources-utilization {
        if-feature "srl-feat:fpcx";
      }
      description
        "Enter the qos context";
    }
  }

  grouping core-qos-utilization {
    list core {
      key "index";
      config false;
      description
        "List of cores within the forwarding-complex that expose per-core QoS resource usage";
      leaf index {
        type uint8 {
          range "0..7";
        }
        description
          "Numeric index of the core within the parent forwarding-complex";
      }
      container qos {
        srl-ext:delivery-node-override "true";
        srl-ext:stream-mode "sample=5";
        description
          "Enter the qos context

           QoS resource utilization for this core";
        list resource {
          key "name";
          description
            "List of per-core QoS resources";
          leaf name {
            type identityref {
              base core-qos-resources;
            }
            description
              "The name of the QoS resource";
          }
          leaf used {
            type uint32;
            description
              "The number of resources that are in use";
          }
          leaf free {
            type uint32;
            description
              "The number of resources that are unused and available";
          }
        }
      }
    }
  }

  grouping buffer-memory {
    container buffer-memory {
      srl-ext:delivery-node-override "true";
      srl-ext:stream-mode "sample=5";
      description
        "Enter the buffer-memory context

         Container for utilization statistics of the packet buffer memory";
      leaf used {
        config false;
        if-feature "srl-feat:ixr-xgs";
        type uint64;
        units "bytes";
        description
          "Used buffer memory, excluding reserved memory.";
      }
      leaf free {
        config false;
        if-feature "srl-feat:ixr-xgs";
        type uint64;
        units "bytes";
        description
          "Available buffer memory, which equals the total memory less the used memory and the reserved memory.";
      }
      leaf reserved {
        config false;
        if-feature "srl-feat:ixr-xgs";
        type uint64;
        units "bytes";
        description
          "Buffer memory reserved for proper system operation and by the user (due to assignment of non-zero CBS for certain queues, on platforms that support CBS).";
      }
      container sram {
        srl-ext:delivery-node-override "true";
        config false;
        if-feature "srl-feat:ixr-dnx";
        description
          "Enter the sram context

           Container for utilization statistics of the on-chip SRAM memory.";
        leaf used {
          type uint64;
          units "bytes";
          description
            "Used SRAM memory";
        }
        leaf free {
          type uint64;
          units "bytes";
          description
            "Available SRAM memory";
        }
      }
      container dram {
        srl-ext:delivery-node-override "true";
        config false;
        if-feature "srl-feat:ixr-dnx";
        description
          "Enter the dram context

           Container for utilization statistics of the DRAM memory.";
        leaf used {
          type srl_nokia-comm:percentage;
          description
            "Used DRAM memory";
        }
      }
      container pfc-headroom-buffer {
        srl-ext:delivery-node-override "true";
        if-feature "srl-feat:qos-pfc-headroom-buffer";
        config false;
        description
          "Enter the pfc-headroom-buffer context

           Container for utilization statistics of the pfc-headroom-buffer";
        leaf used {
          type uint32;
          description
            "Used pfc-headroom-buffer";
        }
        leaf free {
          type uint32;
          description
            "Remaining pfc-headroom-buffer";
        }
      }
      container system-reserved-pool {
        srl-ext:delivery-node-override "true";
        if-feature "srl-feat:qos-fp-pool-policy";
        description
          "Enter the system-reserved-pool context

           Operational size and the current usage of system-reserved-pool";
        config false;
        leaf operational-size {
          description
            "Operational size of the system-reserved-pool";
          type uint32;
          units "bytes";
        }
      }
      list root-pool {
        if-feature "srl-feat:qos-fp-pool-policy";
        config false;
        key "index";
        leaf index {
          type uint8;
          description
            "Root-pool index";
        }
        leaf operational-size {
          description
            "Operational size of the root-pool";
          type uint32;
          units "bytes";
        }
        leaf used {
          description
            "Actual usage of the root-pool";
          type uint32;
          units "bytes";
        }
        list mid-pool {
          key "index";
          leaf index {
            description
              "Mid-pool index";
            type uint8;
          }
          leaf operational-size {
            description
              "Operational size of the mid-pool";
            type uint32;
            units "bytes";
          }
          leaf used {
            description
              "Actual usage of the mid-pool";
            type uint32;
            units "bytes";
          }
        }
      }
    }
  }

  grouping platform-qos-top {
    container qos {
      leaf traffic-management-mode {
        type srl_nokia-comm:scheduler-priority;
        if-feature "srl-feat:qos-traffic-management-mode";
        description
          "Defines traffic-management-mode at system level.

           Changing the traffic-management-mode requires the system reboot";
        default "eight-priorities";
      }
      leaf bank-stats-mode {
        if-feature "srl-feat:qos-bank-stats-mode-ecn";
        description
          "Defines bank-stats-mode at system level.

           Changing the bank-stats-mode requires the system reboot";
        type enumeration {
          enum multicast;
          enum ecn {
            if-feature "srl-feat:qos-bank-stats-mode-ecn";
          }
        }
        default "multicast";
      }
      leaf chassis-reboot-required {
        if-feature "srl-feat:qos-traffic-management-mode or srl-feat:qos-bank-stats-mode-ecn";
        config false;
        type boolean;
        description
          "Reads true if the user has committed a change in traffic-management-mode or bank-stats-mode. The change will take effect only after reboot";
      }
      description
        "Enter the qos context";
    }
  }

  augment "/srl_nokia-platform:platform" {
    if-feature "srl-feat:qos";
    uses platform-qos-top;
  }

  augment "/srl_nokia-platform:platform/srl_nokia-platform-res-mon:resource-monitoring" {
    if-feature "srl-feat:qos";
    uses qos-resource-monitoring;
  }

  augment "/srl_nokia-platform:platform/srl_nokia-platform-res-mon:resource-monitoring" {
    if-feature "srl-feat:qos and srl-feat:qos-subinterface-queuing";
    uses core-qos-resource-monitoring;
  }

  augment "/srl_nokia-platform:platform/srl_nokia-platform-lc:linecard/srl_nokia-platform-lc:forwarding-complex" {
    if-feature "srl-feat:qos";
    uses qos-utilization;
  }

  augment "/srl_nokia-platform:platform/srl_nokia-platform-lc:linecard/srl_nokia-platform-lc:forwarding-complex" {
    if-feature "srl-feat:qos and srl-feat:qos-subinterface-queuing";
    uses core-qos-utilization;
  }

  augment "/srl_nokia-platform:platform/srl_nokia-platform-lc:linecard/srl_nokia-platform-lc:forwarding-complex" {
    if-feature "srl-feat:qos";
    uses buffer-memory;
  }
}
