module srl_nokia-platform-resource-monitoring {
  yang-version 1.1;
  namespace "urn:nokia.com:srlinux:chassis:platform-resource-monitoring";
  prefix srl_nokia-platform-res-monitor;

  import srl_nokia-platform {
    prefix srl_nokia-platform;
  }

  organization
    "Nokia";
  contact
    "Nokia SR Linux Support
     Web: <http://www.nokia.com>";
  description
    "This module defines configuration and operational data for system-wide monitoring of critical resources";

  revision 2026-07-31 {
    description
      "SRLinux 26.7.1";
  }
  revision 2019-11-30 {
    description
      "SRLinux 19.11.1";
  }

  augment "/srl_nokia-platform:platform" {
    container resource-monitoring {
      description
        "Enter the resource-monitoring context";
    }
  }
}
