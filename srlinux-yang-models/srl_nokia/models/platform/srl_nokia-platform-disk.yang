module srl_nokia-platform-disk {
  yang-version 1.1;
  namespace "urn:nokia.com:srlinux:linux:platform-disk";
  prefix srl_nokia-platform-disk;

  import srl_nokia-common {
    prefix srl-comm;
  }
  import srl_nokia-platform {
    prefix srl-platform;
  }
  import srl_nokia-platform-control {
    prefix srl-platform-control;
  }
  import srl_nokia-features {
    prefix srl-feat;
  }

  organization
    "Nokia";
  contact
    "Nokia SR Linux Support
     Web: <http://www.nokia.com>";
  description
    "This module defines configuration and operational state data related to disks.";

  revision 2026-07-31 {
    description
      "SRLinux 26.7.1";
  }
  revision 2026-03-31 {
    description
      "SRLinux 26.3.1";
  }
  revision 2025-03-31 {
    description
      "SRLinux 25.3.1";
  }
  revision 2024-07-31 {
    description
      "SRLinux 24.7.1";
  }
  revision 2023-10-31 {
    description
      "SRLinux 23.10.1";
  }
  revision 2023-07-31 {
    description
      "SRLinux 23.7.1";
  }
  revision 2019-11-30 {
    description
      "SRLinux 19.11.1";
  }

  grouping partition-state-top {
    description
      "Grouping for partition state";
    list partition {
      description
        "List of partitions available on this disk";
      key "name";
      leaf name {
        type string;
        description
          "Name of the partition";
      }
      leaf uuid {
        type string;
        description
          "UUID of the partition";
      }
      leaf mount-point {
        type string;
        description
          "Path to where this partition is mounted";
      }
      leaf mount-status {
        description
          "Current mount status of this partition";
        type enumeration {
          enum ro {
            description
              "Partition is currently mounted read-only";
          }
          enum rw {
            description
              "Partition is currently mounted read-write";
          }
        }
      }
      leaf label {
        type string;
        description
          "Label name of the partition";
      }
      leaf size {
        type uint64;
        description
          "Size of the partition";
        units "bytes";
      }
      leaf used {
        type uint64;
        description
          "Space used on the partition";
        units "bytes";
      }
      leaf free {
        type uint64;
        description
          "Space free on the partition";
        units "bytes";
      }
      leaf percent-used {
        type srl-comm:percentage;
        description
          "Percentage of the partition in use";
      }
      leaf encrypted {
        if-feature "srl-feat:disk-encryption";
        description
          "Indicates if the partition is encrypted using disk encryption";
        type boolean;
      }
    }
  }

  grouping disk-statistics-top {
    description
      "Grouping for disk statistics";
    container statistics {
      config false;
      description
        "Enter the statistics context

         Top-level container for disk statistics";
      leaf utilization {
        type srl-comm:percentage;
        description
          "The current tps utilization of the disk, expressed as a percentage";
      }
      leaf transfers-per-second {
        type decimal64 {
          fraction-digits 2;
        }
        description
          "Indicates the number of transfers per second that were issued to the device
           A transfer is an I/O request to the device. Multiple logical requests can be combined into a single I/O request to the device. A transfer is of indeterminate size.";
      }
      leaf read-per-second {
        type decimal64 {
          fraction-digits 2;
        }
        description
          "Indicates the amount of data read from the device per second";
        units "bytes";
      }
      leaf written-per-second {
        type decimal64 {
          fraction-digits 2;
        }
        description
          "Indicates the amount of data written to the device per second";
        units "bytes";
      }
      leaf io-errors {
        type uint64;
      }
      leaf max-erase-count {
        type uint64;
      }
      leaf soft-read-error-rate {
        type uint64;
        description
          "Uncorrected read errors reported to the operating system. SMART ID
           201.";
        reference
          "S.M.A.R.T. Attribute: Soft Read Error Rate / Off Track Errors (Maxtor)
           | Knowledge Base. kb.acronis.com.";
      }
      leaf reallocated-sectors {
        type uint64;
        description
          "Count of reallocated sectors. The raw value represents a count of
           the bad sectors that have been found and remapped. SMART ID 5.";
        reference
          "S.M.A.R.T. Attribute: Reallocated Sectors Count | Knowledge Base -
           kb.acronis.com";
      }
      leaf end-to-end-error {
        type uint64;
        description
          "Count of parity errors which occur in the data path to the media.
           SMART ID 184.";
        reference
          "Acronis Drive Monitor: Disk Health Calculation Knowledge Base -
           kb.acronis.com";
      }
      leaf offline-uncorrectable-sectors-count {
        type uint64;
        description
          "The total count of uncorrectable errors when reading/writing a
           sector. SMART ID 198.";
        reference
          "Acronis Drive Monitor: Disk Health Calculation Knowledge Base -
           kb.acronis.com";
      }
      leaf life-left {
        type uint8;
        description
          "Indicates the approximate SSD life left, in terms of program/erase
           cycles or available reserved blocks. A normalized value of 100
           represents a new drive, with a threshold value at 10 indicating a need
           for replacement. A value of 0 may mean that the drive is operating in
           read-only mode to allow data recovery. SMART ID 231.";
        reference
          "SMART attribute details,
           https://media.kingston.com/support/downloads/MKP_306_SMART_attribute.pdf";
      }
      leaf percentage-used {
        type uint8;
        description
          "Contains a vendor specific estimate of the percentage of NVM
           subsystem life used based on the actual usage and the manufacturer's
           prediction of NVM life. A value of 100 indicates that the estimated
           endurance of the NVM in the NVM subsystem has been consumed, but may
           not indicate an NVM subsystem failure. The value is allowed to exceed
           100. Percentages greater than 254 shall be represented as 255.";
        reference
          "NVM Express Base Specification Revision 2.0a
           https://nvmexpress.org/wp-content/uploads/NVMe-NVM-Express-2.0a-2021.07.26-Ratified.pdf";
      }
    }
  }

  grouping disk-state-top {
    description
      "Grouping for disk state";
    leaf name {
      type string;
      description
        "Name of the disk, as defined by its physical location in the system";
    }
    leaf model-number {
      type string;
      description
        "Model name of the disk";
    }
    leaf part-number {
      type string;
      description
        "Nokia orderable 3HE part-number matching the capacity of the installed SD card

         Note: The returned part-number is based on the capacity of the SD card, and does not indicate the installed SD card is a Nokia supplied component.";
    }
    leaf serial-number {
      type string;
      description
        "Serial number of the disk";
    }
    leaf size {
      type uint64;
      description
        "Total size of the disk";
    }
    leaf type {
      description
        "Type of disk";
      type enumeration {
        enum compactflash;
        enum ssd;
        enum hdd;
        enum usb;
        enum mmc {
          if-feature "srl-feat:platform-7215-a1";
        }
      }
    }
    leaf install-position {
      type enumeration {
        enum internal;
        enum external;
      }
      description
        "Physical installation position of the compactflash disk on the control card";
    }
    leaf encrypted {
      if-feature "srl-feat:disk-encryption";
      description
        "Indicates if the disk is encrypted";
      type boolean;
    }
    uses partition-state-top;
    uses disk-statistics-top;
  }

  grouping disk-top {
    description
      "Grouping for disk configuration and state";
    list disk {
      description
        "List of disks present in the system";
      key "name";
      config false;
      uses disk-state-top;
    }
  }

  augment "/srl-platform:platform/srl-platform-control:control" {
    uses disk-top;
  }
}
