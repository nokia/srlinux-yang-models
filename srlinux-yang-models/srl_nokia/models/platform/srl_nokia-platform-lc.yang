module srl_nokia-platform-lc {
  yang-version 1.1;
  namespace "urn:nokia.com:srlinux:chassis:platform-lc";
  prefix srl_nokia-platform-lc;

  import srl_nokia-platform {
    prefix srl-platform;
  }
  import srl_nokia-platform-pipeline-counters {
    prefix srl-platform-pipeline;
  }
  import srl_nokia-extensions {
    prefix srl-ext;
  }
  import srl_nokia-common {
    prefix srl-comm;
  }
  import srl_nokia-features {
    prefix srl-feat;
  }

  organization
    "Nokia";
  contact
    "Nokia SR Linux Support
     Web: <http://www.nokia.com>";
  description
    "This module defines configuration and operational state data related to line cards.";

  revision 2026-07-31 {
    description
      "SRLinux 26.7.1";
  }
  revision 2026-03-31 {
    description
      "SRLinux 26.3.1";
  }
  revision 2025-10-31 {
    description
      "SRLinux 25.10.1";
  }
  revision 2025-07-31 {
    description
      "SRLinux 25.7.1";
  }
  revision 2025-03-31 {
    description
      "SRLinux 25.3.1";
  }
  revision 2024-10-31 {
    description
      "SRLinux 24.10.1";
  }
  revision 2024-07-31 {
    description
      "SRLinux 24.7.1";
  }
  revision 2024-03-31 {
    description
      "SRLinux 24.3.1";
  }
  revision 2023-07-31 {
    description
      "SRLinux 23.7.1";
  }
  revision 2023-03-31 {
    description
      "SRLinux 23.3.1";
  }
  revision 2022-11-30 {
    description
      "SRLinux 22.11.1";
  }
  revision 2022-06-30 {
    description
      "SRLinux 22.6.1";
  }
  revision 2022-03-31 {
    description
      "SRLinux 22.3.1";
  }
  revision 2021-11-30 {
    description
      "SRLinux 21.11.1";
  }
  revision 2021-03-31 {
    description
      "SRLinux 21.3.1";
  }
  revision 2020-06-30 {
    description
      "SRLinux 20.6.1";
  }
  revision 2019-11-30 {
    description
      "SRLinux 19.11.1";
  }

  typedef hash-user-type {
    type enumeration {
      enum level-1-fec {
        description
          "Level 1 (top level) ECMP hash user";
      }
      enum level-2-fec {
        description
          "Level 2 (middle level) ECMP hash user";
      }
      enum level-3-fec {
        description
          "Level 3 (bottom level) ECMP hash user";
      }
      enum lag {
        description
          "LAG hash user";
      }
      enum network-header {
        description
          "Network header entropy hash user";
      }
    }
  }

  grouping fc-load-balancing {
    container load-balancing {
      config false;
      description
        "Enter the load-balancing context

         Load-balancing state presented on a per-forwarding-complex basis";
      list hash-user {
        key "user";
        leaf user {
          type hash-user-type;
          description
            "A user of a load-balancing hash calculation";
        }
        leaf hash-polynomial {
          type uint8 {
            range "1..8";
          }
          description
            "An identifier for the polynomial used to calculate the load-balancing key";
        }
      }
    }
  }

  grouping fabric-state {
    srl-ext:stream-mode "sample=5";
    description
      "Grouping for linecard/forwarding-complex fabric availability and utilization state";
    leaf availability {
      config false;
      type srl-comm:percentage;
      description
        "Details the percentage bandwidth available to the fabric for the line card";
    }
    leaf total-capacity {
      if-feature "srl-feat:backplane-facing-capacity";
      config false;
      type uint64;
      units "bits per second";
      description
        "Total backplane-facing capacity that is available in the presence of no link failures or degradation";
    }
    leaf operational-capacity {
      if-feature "srl-feat:backplane-facing-capacity";
      config false;
      type uint64;
      units "bits per second";
      description
        "Total backplane-facing capacity that is currently available based on the active links";
    }
    leaf consumed-capacity {
      if-feature "srl-feat:backplane-facing-capacity";
      config false;
      type uint64;
      units "bits per second";
      description
        "Backplane-facing capacity that is consumed by front-panel ports that are connected to the integrated circuit and are operationally up";
    }
    leaf utilization-ingress {
      config false;
      type srl-comm:gauge64;
      description
        "Provides the linecard bandwidth utilization into the switch fabric";
    }
    leaf utilization-egress {
      config false;
      type srl-comm:gauge64;
      description
        "Provides the linecard bandwidth utilization from the switch fabric";
    }
  }

  grouping mda-top {
    description
      "Grouping for mda configuration and state";
    list mda {
      if-feature "srl-feat:mda";
      description
        "Top-level container for mda configuration and state";
      key "slot";
      leaf slot {
        type uint8 {
          range "1..8";
        }
        description
          "Numeric identifier for the mda position within the parent linecard";
      }
      uses srl-platform:component-common-config-top;
      uses srl-platform:component-common-state-top;
      uses srl-platform:component-common-eeprom;
      uses srl-platform:component-delayed-reboot-state;
      leaf type {
        config false;
        type string;
        srl-ext:show-importance "high";
        description
          "MDA type, as read from the physical assembly";
      }
      leaf-list interfaces {
        config false;
        type srl-comm:interface-all;
        description
          "List of interfaces that belong to this mda";
      }
      uses srl-platform:component-locator;
      uses srl-platform:component-temperature-state-top;
    }
  }

  grouping linecard-top {
    description
      "Grouping for linecard configuration and state";
    list linecard {
      description
        "Top-level container for linecard configuration and state";
      key "slot";
      leaf slot {
        type uint8 {
          range "1..16";
        }
        description
          "Numeric identifier for the linecard";
      }
      uses srl-platform:component-common-config-top {
        if-feature "srl-feat:chassis";
      }
      uses srl-platform:component-common-state-top;
      uses srl-platform:component-common-eeprom;
      uses srl-platform:component-bios-common {
        if-feature "not srl-feat:vsrl";
      }
      uses srl-platform:component-delayed-reboot-state {
        if-feature "srl-feat:chassis";
      }
      leaf type {
        config false;
        type string;
        srl-ext:show-importance "high";
        description
          "Linecard type, as read from the physical assembly";
      }
      list forwarding-complex {
        description
          "List of forwarding complexes on the linecard";
        key "name";
        leaf name {
          type enumeration {
            enum 0;
            enum 1 {
              if-feature "srl-feat:forwarding-complex-1";
            }
          }
          description
            "The identifier of the forwarding complex";
        }
        leaf-list interfaces {
          config false;
          type srl-comm:interface-all;
          description
            "List of interfaces that belong to this forwarding complex";
        }
        uses srl-platform:component-common-state-top;
        container fabric {
          srl-ext:first-released "20.6.1";
          srl-ext:delivery-node-override "true";
          description
            "Enter the fabric context

             Top-level container for fabric configuration and state";
          if-feature "srl-feat:chassis";
          uses fabric-state;
        }
        list pipeline {
          if-feature "srl-feat:tomahawk3 or srl-feat:oc-extracted-cpm-traffic-stats";
          description
            "List of pipelines that make up one forwarding complex.";
          key "index";
          leaf index {
            type union {
              type uint8 {
                range "0..7";
              }
              type enumeration {
                enum egress {
                  if-feature "srl-feat:oc-extracted-cpm-traffic-stats";
                  description
                    "Applicable to J2 and J2C+ systems only";
                }
                enum ingress {
                  if-feature "srl-feat:oc-extracted-cpm-traffic-stats";
                  description
                    "Applicable to J2 and J2C+ systems only";
                }
              }
            }
            description
              "The pipeline number (TH3 systems) or direction (J2 and J2C+ systems).";
          }
          uses srl-platform-pipeline:pipeline-counters {
            if-feature "srl-feat:oc-extracted-cpm-traffic-stats";
          }
        }
        container control-plane-traffic {
          if-feature "srl-feat:forwarding-complex-pipeline-counters";
          config false;
          description
            "Enter the control-plane-traffic context

             Counters related to traffic destined to the control-plane";
          leaf queued-aggregate {
            type srl-comm:zero-based-counter64;
            description
              "The aggregation of all counters where the switch has enqueued traffic related to the control plane";
          }
          leaf queued-bytes-aggregate {
            type srl-comm:zero-based-counter64;
            description
              "The aggregation of all counters in bytes where the switch has enqueued traffic related to the control plane";
          }
          leaf dropped-aggregate {
            type srl-comm:zero-based-counter64;
            description
              "The aggregation of all counters where the switch has dropped traffic related to the control plane";
          }
          leaf dropped-bytes-aggregate {
            type srl-comm:zero-based-counter64;
            description
              "Te aggregation of all counters in bytes where the switch has dropped traffic related to the control plane";
          }
        }
        container drop-counters {
          if-feature "srl-feat:forwarding-complex-pipeline-counters";
          config false;
          description
            "Enter the drop-counters context

             State container for forwarding-complex drop counters";
          leaf adverse-aggregate {
            type srl-comm:zero-based-counter64;
            description
              "Aggregation of all counters incremented when packets are dropped unexpectedly

               This leaf counts packet discarded as result of corrupted programming state or data structures in the forwarding-complex integrated circuit.

               Note: corrupted packets received on ingress interfaces are not counted in this leaf. This is because incoming corrupted packets are not a signal of adverse state within the integrated circuit, but rather of an adjacent entity, such as a cable or transceiver.";
          }
          leaf congestion-aggregate {
            type srl-comm:zero-based-counter64;
            description
              "Aggregation of all counters incremented when packets are dropped because the aggregate ingress traffic rate exceeds internal performance limits of the integrated circuit";
          }
          leaf packet-processing-aggregate {
            type srl-comm:zero-based-counter64;
            description
              "Aggregation of all counters incremented when packets are dropped due to legitimate programming decisions

               This is derived by summing:
               * subinterface-level in-discarded counters (counts FIB lookup failures, packets dropped due to ACL drop action, packets dropped due to TTL expiry)
               * subinterface-level out-error counters (packets dropped due to IP MTU exceeded)
               * port-level out-error counters (packets dropped due to port MTU exceeded)
               * port-level in-error counters (packets dropped due to MRU exceeded oe packet CRC error)";
          }
          leaf no-route {
            type srl-comm:zero-based-counter64;
            description
              "Aggregation of all counters incremented when packets are dropped due to no FIB entry for an IPv4 or IPv6 packet

               This counter and the packet-processing-aggregate counter should be incremented for each no-route packet drop.";
          }
          leaf urpf-aggregate {
            if-feature "srl-feat:unicast-rpf-check";
            description
              "Total packets dropped due to uRPF lookup check failure

               This counter and the packet-processing-aggregate counter should be incremented for each uRPF packet drop.";
            type srl-comm:zero-based-counter64;
          }
        }
        container counter-banks {
          if-feature "srl-feat:platform-counter-bank-allocation";
          config false;
          description
            "Enter the counter-banks context

             Bank allocation across different stake-holders. Banks are required by policers to function as well for various stats collection such as Per-Prefix Stats, LSP Stats and alike";
          list bank {
            config false;
            key "bank-id";
            leaf bank-id {
              type uint16 {
                range "1..34";
              }
              description
                "Unique bank location identifier";
            }
            leaf bank-size {
              type enumeration {
                enum 4K;
                enum 6K;
                enum 8K;
                enum 12K;
                enum 16K;
                enum 24K;
              }
              description
                "Bank size. Counter banks are in different sizes and applications can make use of different bank sizes for scale";
            }
            leaf-list banks-in-group {
              if-feature "srl-feat:platform-counter-bank-allocation-subintf-parent-policers-and-stats";
              description
                "Certain applications mandate allocation of another corresponding bank to function properly as mandated by datapath
                 When given application requires to be grouped with another bank, assuming bank is available at the time of allocation, is displayed in this field";
              type uint16 {
                range "1..34";
              }
            }
            list application {
              key "name";
              leaf name {
                type identityref {
                  base srl-comm:applications-utilizing-banks-state;
                }
                description
                  "Bank binding. Displays the name of the application bank is assigned to";
              }
              leaf entries {
                type uint64;
                description
                  "Bank entries reserved for a given application";
              }
            }
          }
        }
        uses fc-load-balancing {
          if-feature "srl-feat:platform-hash-polynomial-visibility";
        }
      }
      uses srl-platform:component-common-state-sw;
      uses srl-platform:component-locator {
        if-feature "srl-feat:chassis";
      }
      uses srl-platform:component-power-state-top {
        if-feature "srl-feat:chassis";
      }
      uses srl-platform:component-temperature-state-top {
        if-feature "srl-feat:chassis";
      }
      uses mda-top;
    }
  }

  augment "/srl-platform:platform" {
    uses linecard-top;
  }
}
