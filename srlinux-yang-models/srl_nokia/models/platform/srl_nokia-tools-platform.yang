module srl_nokia-tools-platform {
  yang-version 1.1;
  namespace "urn:nokia.com:srlinux:chassis:tools-platform";
  prefix srl_nokia-tools-platform;

  import srl_nokia-features {
    prefix srl-feat;
  }
  import srl_nokia-common {
    prefix srl-comm;
  }

  organization
    "Nokia";
  contact
    "Nokia SR Linux Support
     Web: <http://www.nokia.com>";
  description
    "Model for operational commands for platform.";

  revision 2026-07-31 {
    description
      "SRLinux 26.7.1";
  }
  revision 2026-03-31 {
    description
      "SRLinux 26.3.1";
  }
  revision 2025-10-31 {
    description
      "SRLinux 25.10.1";
  }
  revision 2025-07-31 {
    description
      "SRLinux 25.7.1";
  }
  revision 2025-03-31 {
    description
      "SRLinux 25.3.1";
  }
  revision 2024-10-31 {
    description
      "SRLinux 24.10.1";
  }
  revision 2024-07-31 {
    description
      "SRLinux 24.7.1";
  }
  revision 2023-07-31 {
    description
      "SRLinux 23.7.1";
  }
  revision 2023-03-31 {
    description
      "SRLinux 23.3.1";
  }
  revision 2022-11-30 {
    description
      "SRLinux 22.11.1";
  }
  revision 2021-03-31 {
    description
      "SRLinux 21.3.1";
  }
  revision 2020-06-30 {
    description
      "SRLinux 20.6.1";
  }
  revision 2019-11-30 {
    description
      "SRLinux 19.11.1";
  }

  grouping locator-tools {
    container locator {
      description
        "Enter the locator context

         Operational commands for the locator LED";
      container enable {
        presence "Activate the locator LED for this component";
        description
          "Activate the locator LED for this component";
        leaf duration {
          type uint16 {
            range "10..3600";
          }
          units "seconds";
          description
            "Sets the duration to activate the locator LED, after which it will disable automatically";
        }
      }
      leaf disable {
        type empty;
        description
          "Deactivates the locator LED for this component";
      }
    }
  }

  grouping reboot-options-no-force {
    description
      "Grouping for force leaf used with reboots";
    leaf cancel {
      type empty;
      must 'not(../delay)' {
        error-message "cancel cannot be used with a delay";
      }
      description
        "Cancels a pending reboot on this component";
    }
  }

  grouping reboot-options-force {
    description
      "Grouping for force leaf used with reboots";
    leaf cancel {
      type empty;
      must 'not(../delay)' {
        error-message "cancel cannot be used with a delay";
      }
      must 'not(../force)' {
        error-message "cancel cannot be used with force";
      }
      description
        "Cancels a pending reboot on this component";
    }
    leaf force {
      type empty;
      description
        "Force a reboot of this component, overriding any synchronizations or other activities in progress

         This option can be dangerous, and may result in a module booting on an older image if used after an image change";
    }
  }

  grouping common-tools-no-force {
    description
      "Grouping for common component commands";
    container reboot {
      presence "Trigger or cancel a reboot of this component";
      description
        "Trigger or a reboot of this component";
      uses reboot-options;
      uses reboot-options-no-force;
    }
  }

  grouping common-tools-force {
    description
      "Grouping for common component commands";
    container reboot {
      presence "Trigger or cancel a reboot of this component";
      description
        "Trigger or a reboot of this component";
      uses reboot-options;
      uses reboot-options-force;
    }
  }

  grouping reboot-options {
    description
      "Grouping for reboot options";
    leaf message {
      type string;
      description
        "A user-defined message to broadcoast to other users of the system";
    }
    leaf delay {
      type uint64;
      units "seconds";
      description
        "The amount of time to delay the reboot

         During this period, the reboot can be cancelled.";
    }
  }

  grouping disk-encryption {
    description
      "Grouping for Disk Encryption options";
    container disk-encryption {
      if-feature "srl-feat:disk-encryption";
      description
        "Enter the disk-encryption context

         Operational commands related to Disk Encryption";
      list control {
        description
          "Operational commands related to Disk Encryption for control modules";
        key "slot";
        leaf slot {
          type string {
            pattern 'A|B';
          }
          description
            "Slot identifier for the control module";
        }
        container activate {
          presence "Activate Disk Encryption for a control module";
          description
            "Activate Disk Encryption for a control module";
        }
      }
    }
  }

  grouping chassis-mode-options-top {
    description
      "Grouping for chassis mode";
    leaf type {
      if-feature "srl-feat:chassis-mode";
      type srl-comm:chassis-mode-options;
      description
        "Chassis type";
    }
  }

  grouping tools-platform-top {
    container chassis {
      description
        "Enter the chassis context

         Operational commands related to the chassis";
      container reboot {
        presence "Trigger a reboot of the chassis";
        description
          "Trigger a reboot of the chassis";
        uses reboot-options;
        uses reboot-options-force;
        container warm {
          if-feature "srl-feat:warm-reboot";
          presence "Trigger a warm reboot operation on the system";
          description
            "Perform a warm reboot of the system

             This option will perform checks against the current configuration, before prompting to confirm the reboot, and then rebooting the system without impacting the datapath - if a new image has been configured, this will upgrade the system.";
          container force {
            presence "Force a warm reboot of the system";
            description
              "Force a warm reboot of the system, overriding any validation, synchronizations or other activities in progress

               This option can be dangerous, and may result in an outage - but can be used to support a fast reboot of the system.";
          }
          container validate {
            presence "Validate a warm reboot is supported";
            description
              "Validate that the system's current configuration and state supports a warm reboot operation";
          }
        }
      }
      uses chassis-mode-options-top;
    }
    list linecard {
      if-feature "srl-feat:chassis or srl-feat:mda";
      description
        "Operational commands related to line cards";
      key "slot";
      leaf slot {
        type uint8;
        description
          "Numeric identifier for the line card";
      }
      uses common-tools-no-force {
        if-feature "srl-feat:linecard-reboot";
      }
      uses locator-tools {
        if-feature "srl-feat:linecard-locator";
      }
      list mda {
        if-feature "srl-feat:mda";
        description
          "operational commands related to mda";
        key "slot";
        leaf slot {
          type uint8 {
            range "1..8";
          }
          description
            "Numeric identifier for the mda position within the parent linecard";
        }
        uses common-tools-no-force;
        uses locator-tools;
      }
    }
    leaf show-fabric-bandwidth {
      if-feature "srl-feat:chassis";
      type empty;
      description
        "Show fabric bandwidth";
    }
    list fabric {
      if-feature "srl-feat:chassis";
      description
        "Operational commands related to fabric modules";
      key "slot";
      leaf slot {
        type uint8;
        description
          "Numeric identifier for the fabric module";
      }
      uses common-tools-no-force;
      uses locator-tools;
    }
    list control {
      if-feature "not srl-feat:vsrl";
      description
        "Operational commands related to control modules";
      key "slot";
      leaf slot {
        type string;
        description
          "Slot identifier for the control module";
      }
      uses common-tools-force {
        if-feature "srl-feat:control-card-reboot";
      }
      uses locator-tools;
    }
    list fan-tray {
      if-feature "not srl-feat:vsrl and not srl-feat:platform-7215-a1";
      description
        "Operational commands related to fan modules";
      key "id";
      leaf id {
        type uint8;
        description
          "Numeric identifier for the fan module";
      }
      uses locator-tools;
    }
    container trust {
      if-feature "srl-feat:secure-boot or srl-feat:measured-boot or srl-feat:disk-encryption";
      description
        "Enter the trust context

         Operational commands related to Platform Trust";
      uses disk-encryption;
    }
  }

  container platform {
    description
      "Enter the platform context

       Top-level container for platform operational commands";
    uses tools-platform-top;
  }
}
