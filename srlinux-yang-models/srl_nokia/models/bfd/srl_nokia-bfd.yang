module srl_nokia-bfd {
  yang-version 1.1;
  namespace "urn:nokia.com:srlinux:bfd:bfd";
  prefix srl_nokia-bfd;

  import srl_nokia-common {
    prefix srl_nokia-comm;
  }
  import srl_nokia-extensions {
    prefix srl_nokia-ext;
  }
  import srl_nokia-features {
    prefix srl_nokia-feat;
  }
  import srl_nokia-interfaces {
    prefix srl_nokia-if;
  }

  organization
    "Nokia";
  contact
    "Nokia SR Linux Support
     Web: <http://www.nokia.com>";
  description
    "This yang file gives a description of bfd protocol
     configuration.";

  revision 2026-07-31 {
    description
      "SRLinux 26.7.1";
  }
  revision 2026-03-31 {
    description
      "SRLinux 26.3.1";
  }
  revision 2025-07-31 {
    description
      "SRLinux 25.7.1";
  }
  revision 2025-03-31 {
    description
      "SRLinux 25.3.1";
  }
  revision 2024-10-31 {
    description
      "SRLinux 24.10.1";
  }
  revision 2024-03-31 {
    description
      "SRLinux 24.3.1";
  }
  revision 2022-11-30 {
    description
      "SRLinux 22.11.1";
  }
  revision 2022-06-30 {
    description
      "SRLinux 22.6.1";
  }
  revision 2021-03-31 {
    description
      "SRLinux 21.3.1";
  }
  revision 2020-06-30 {
    description
      "SRLinux 20.6.1";
  }
  revision 2019-11-30 {
    description
      "SRLinux 19.11.1";
  }

  typedef bfd-session-state {
    type enumeration {
      enum ADMIN_DOWN {
        value 0;
        description
          "BFD session is administratively disabled";
      }
      enum DOWN {
        value 1;
        description
          "BFD session is perceived to be down by the system";
      }
      enum INIT {
        value 2;
        description
          "BFD session is perceived to be initialising by the system";
      }
      enum UP {
        value 3;
        description
          "BFD session is perceived to be up by the system";
      }
    }
    description
      "State of the BFD session according to the system referred to by the context of the leaf";
    reference
      "RFC5880 - Bidirectional Forwarding Detection, Section 4.1";
  }

  typedef bfd-diagnostic-code {
    type enumeration {
      enum NO_DIAGNOSTIC {
        value 0;
        description
          "No diagnostic code was specified or the session has not changed state";
      }
      enum DETECTION_TIMEOUT {
        value 1;
        description
          "Control detection time expired: no BFD packet was received within the required period";
      }
      enum ECHO_FAILED {
        value 2;
        description
          "BFD echo function failed and echo packets were not received for the required period of time";
      }
      enum NEIGHBOR_SIGNALED_DOWN {
        value 3;
        description
          "Neighbor signaled session down";
      }
      enum FORWARDING_RESET {
        value 4;
        description
          "Forwarding plane in the local system was reset

           The remote system cannot rely on the forwarding state of the device
           specifying this error code.";
      }
      enum PATH_DOWN {
        value 5;
        description
          "Signalling outside of BFD specifies that the path underlying this session has failed";
      }
      enum CONCATENATED_PATH_DOWN {
        value 6;
        description
          "Segment on the path between source and destination has failed

           When a BFD session runs over a series of path segments, this error code indicates that a subsequent path
           segment (i.e., one in the transmit path between the source and destination of the session) has failed.";
      }
      enum ADMIN_DOWN {
        value 7;
        description
          "BFD session has been administratively disabled by the peer";
      }
      enum REVERSE_CONCATENATED_PATH_DOWN {
        value 8;
        description
          "Segment on the reverse path between destination and source has failed

           In the case that a BFD session is running over a series of path segments, this error code indicates that a
           path segment on the reverse path (i.e., in the transmit direction from the destination to the source of the
           session) has failed.";
      }
    }
    description
      "Diagnostic codes defined by BFD

          These typically indicate the reason for a change of session state.";
    reference
      "RFC5880 - Bidirectional Forwarding Detection, Section 4.1";
  }

  typedef te-policy-origin {
    type enumeration {
      enum LOCAL {
        value 0;
        description
          "Associated TE-Policy originated from local configuration";
      }
      enum PCEP {
        value 1;
        description
          "Associated TE-Policy from a PCEP controller";
      }
      enum BGP {
        value 2;
        description
          "Associated TE-Policy from BGP peer";
      }
    }
    description
      "Source protocols for TE-Policies";
  }

  grouping bfd-top {
    container bfd {
      if-feature "srl_nokia-feat:bfd";
      presence "Configure BFD";
      description
        "Context to configure BFD parameters and report BFD sessions state";
      list subinterface {
        key "id";
        description
          "List of subinterface references to associating BFD config and state";
        leaf id {
          description
            "Reference ID for associated subinterface
             Example: ethernet-2/1.100 (Reference Interface ethernet-2/1, subinterface 100).";
          type srl_nokia-comm:subinterface-no-mgmt;
          must "/srl_nokia-if:interface[srl_nokia-if:name=substring-before(current(), '.')]/srl_nokia-if:subinterface[srl_nokia-if:index=substring-after(current(), '.')]" {
            error-message "Must be an existing subinterface name";
          }
        }
        leaf admin-state {
          type srl_nokia-comm:admin-state;
          default "disable";
          description
            "Administratively enable or disable BFD for this subinterface";
        }
        leaf desired-minimum-transmit-interval {
          type uint32 {
            range "10000..100000000";
          }
          default "1000000";
          must '. >= 1000000' {
            error-message "Minimum value is 1000000 on this platform";
            srl_nokia-ext:if-feature "srl_nokia-feat:vsrl";
          }
          units "microseconds";
          description
            "Minimum interval between transmission of BFD control packets

             This value is advertised to the peer, however the actual interval used is specified
             by taking the maximum of desired-minimum-transmit-interval and the value of the remote
             required-minimum-receive interval value.
             This value is specified as an integer number of microseconds.
             [Note: On vSRL instances this must be set to a value of 1000000 or greater]";
        }
        leaf required-minimum-receive {
          type uint32 {
            range "10000..100000000";
          }
          default "1000000";
          must '. >= 1000000' {
            error-message "Minimum value is 1000000 on this platform";
            srl_nokia-ext:if-feature "srl_nokia-feat:vsrl";
          }
          units "microseconds";
          description
            "Minimum interval between received BFD control packets that this system should support

             This value is advertised to the remote peer to indicate the maximum frequency (i.e., minimum
             inter-packet interval) between BFD control packets that is acceptable to the local system.
             This value is specified as an integer number of microseconds.
             [Note: On vSRL instances this must be set to a value of 1000000 or greater]";
        }
        leaf detection-multiplier {
          type uint8 {
            range "3..20";
          }
          default "3";
          description
            "Number of packets that must be missed to declare this session as down

             The detection interval for the BFD session is calculated by multiplying the
             value of the negotiated transmission interval by this value.";
        }
        leaf minimum-echo-receive-interval {
          type uint32 {
            range "0 | 250000..100000000";
          }
          default "0";
          description
            "Minimum interval between echo packets the local node can receive

             Implicitly enabled echo mode on the associated interface.";
        }
        leaf max-hop-count {
          type uint8 {
            range "2..255";
          }
          default "255";
          description
            "TTL to be used in the BFD IP header for multihop BFD";
        }
      }
      list network-instance {
        key "name";
        config false;
        description
          "Network-instance context for the BFD session";
        leaf name {
          type string;
          description
            "Unique name identifying the network instance";
        }
        list peer {
          key "local-discriminator";
          config false;
          description
            "BFD session state related to this peer";
          leaf local-discriminator {
            srl_nokia-ext:show-importance "high";
            type uint32;
            description
              "BFD session local discriminator";
          }
          leaf oper-state {
            srl_nokia-ext:show-importance "high";
            type srl_nokia-comm:oper-state;
            description
              "Details the operational state of the session";
          }
          leaf ipv6-link-local-interface {
            type string;
            description
              "For IPv6 link local sessions only, indicates the local interface with which the session is associated";
          }
          leaf ipv4-unnumbered-interface {
            type string;
            description
              "For IPv4 unnumbered sessions only, indicates the local interface with which the session is associated";
          }
          leaf local-address {
            srl_nokia-ext:show-importance "high";
            type srl_nokia-comm:ip-address;
            description
              "IP address to be used as source address in BFD packets";
          }
          leaf remote-address {
            srl_nokia-ext:show-importance "high";
            type srl_nokia-comm:ip-address;
            description
              "Remote IP address for the far-end of the BFD session

               This must be the same IP version as the local-address.";
          }
          leaf remote-discriminator {
            srl_nokia-ext:show-importance "high";
            type uint32;
            description
              "Unique identifier used by the remote system to identify this BFD session";
          }
          leaf subscribed-protocols {
            srl_nokia-ext:show-importance "high";
            type string;
            description
              "Indicates the set of protocols that currently use this BFD session for liveliness detection";
          }
          leaf session-state {
            srl_nokia-ext:show-importance "high";
            type bfd-session-state;
            description
              "State of the BFD session perceived by the local system";
          }
          leaf remote-session-state {
            srl_nokia-ext:show-importance "high";
            type bfd-session-state;
            description
              "Reported state of the BFD session according to the remote system

               This state reflects the last state reported in a BFD control packet.";
          }
          leaf last-state-transition {
            type srl_nokia-comm:date-and-time-delta;
            description
              "Timestamp of the last BFD session transition from any state to any state
               Time of the session in the current state can be calculated from this value.";
          }
          leaf last-failure-time {
            type srl_nokia-comm:date-and-time-delta;
            description
              "Timestamp of the last BFD session transition out of the up state to down state";
          }
          leaf failure-transitions {
            type uint64;
            description
              "Number of times that the BFD session transitioned out of the up state";
          }
          leaf local-diagnostic-code {
            srl_nokia-ext:show-importance "high";
            type bfd-diagnostic-code;
            description
              "Local BFD diagnostic code indicating the most recent reason for failure of this BFD session";
          }
          leaf remote-diagnostic-code {
            srl_nokia-ext:show-importance "high";
            type bfd-diagnostic-code;
            description
              "Remote BFD diagnostic code indicating the remote system's reason for failure of the BFD session";
          }
          leaf remote-minimum-receive-interval {
            type uint32;
            description
              "Value of the minimum receive interval that was specified by the peer

               This value references the value in the most recent BFD control packet
               received from the peer.";
          }
          leaf remote-control-plane-independent {
            type boolean;
            description
              "Indicates if the remote neighbor has set the control independent flag";
          }
          leaf active-transmit-interval {
            srl_nokia-ext:show-importance "high";
            type uint32;
            description
              "Transmit interval currently being used by this BFD session

               This is the amount of time the local BFD agent will wait between the
               sending of BFD messages to the remote peer.";
          }
          leaf active-receive-interval {
            srl_nokia-ext:show-importance "high";
            type uint32;
            description
              "Receive interval currently being used by this BFD session

               This is the amount of time the BFD state machine expects between
               receiving BFD messages from the remote peer.";
          }
          leaf remote-multiplier {
            srl_nokia-ext:show-importance "high";
            type uint8;
            description
              "Current number of packets that must be missed to declare the session as down

               The detection interval for the BFD session is calculated by multiplying the
               value of the negotiated transmission interval by this value.";
          }
          leaf te-policy-name {
            config false;
            type string;
            description
              "Name of the TE-Policy associated with this seamless BFD session";
          }
          leaf te-policy-type {
            config false;
            type srl_nokia-comm:te-policy-type;
            description
              "Type of TE-Policy associated with this seamless BFD session";
          }
          leaf te-policy-candidate-path-name {
            config false;
            type srl_nokia-comm:name;
            description
              "Colored TE-Policy candidate path name";
          }
          leaf te-policy-color {
            config false;
            type uint32;
            description
              "Color associated with the (colored) TE-Policy";
          }
          leaf te-policy-segment-list-index {
            config false;
            type uint32;
            description
              "Indicates the segment list index of the TE-Policy associated with this seamless BFD session";
          }
          leaf te-policy-protocol-origin {
            config false;
            type te-policy-origin;
            description
              "Indicates the protocol type used to originate the TE-Policy associated with this seamless BFD session";
          }
          leaf te-policy-segment-list-lsp-index {
            config false;
            type uint32;
            description
              "Indicates the lsp index for the segement list of the TE-Policy associated with this seamless BFD session";
          }
          leaf sr-policy-endpoint {
            config false;
            type srl_nokia-comm:ip-address;
            description
              "SR-Policy endpoint IP address associated with this seamless BFD session";
          }
          container async {
            srl_nokia-ext:delivery-node-override "true";
            srl_nokia-ext:stream-mode "sample=5";
            presence "State async operational parameters";
            description
              "Container for async BFD operational state parameters";
            leaf last-packet-transmitted {
              type srl_nokia-comm:date-and-time-delta;
              description
                "Timestamp for when the last BFD packet was transmitted for this session";
            }
            leaf last-packet-received {
              type srl_nokia-comm:date-and-time-delta;
              description
                "Timestamp for when the last BFD packet was received for this session";
            }
            leaf transmitted-packets {
              srl_nokia-ext:show-importance "high";
              type srl_nokia-comm:zero-based-counter64;
              description
                "Counter for the number of BFD packets transmitted for this session";
            }
            leaf received-packets {
              srl_nokia-ext:show-importance "high";
              type srl_nokia-comm:zero-based-counter64;
              description
                "Counter for the number of BFD packets received for this session";
            }
            leaf up-transitions {
              type srl_nokia-comm:zero-based-counter64;
              description
                "Counter for the number of UP transitions for this BFD session";
            }
            leaf received-errored-packets {
              type srl_nokia-comm:zero-based-counter64;
              description
                "Counter for the number of BFD packets received with BFD level errors";
            }
            leaf last-clear {
              type srl_nokia-comm:date-and-time-delta;
              description
                "Timestamp of the last time the session counters were cleared";
            }
          }
        }
      }
      list peer {
        if-feature "srl_nokia-feat:tools-as-modeled-actions-different-output";
        key "local-discriminator";
        config false;
        description
          "The list of local-discriminators associated with BFD";
        leaf local-discriminator {
          config false;
          type uint32;
          description
            "BFD session local discriminator";
        }
        action clear {
          description
            "Clear the associated BFD sessions

             Clearing a BFD sessions causes the associated BFD sessions ot transition to a Down state";
        }
      }
      container statistics {
        if-feature "srl_nokia-feat:tools-as-modeled-actions-different-output";
        config false;
        list peer {
          key "local-discriminator";
          config false;
          description
            "The list of local-discriminators associated with BFD";
          leaf local-discriminator {
            config false;
            type uint32;
            description
              "BFD session local discriminator";
          }
          action clear {
            description
              "Clear the BFD statistics associated with the BFD sessions";
          }
        }
        description
          "Enter the statistics context";
      }
      leaf total-bfd-sessions {
        type srl_nokia-comm:zero-based-counter32;
        config false;
        description
          "Counter for the total number of BFD sessions";
      }
      leaf total-unmatched-bfd-packets {
        type srl_nokia-comm:zero-based-counter64;
        config false;
        description
          "Counter for the total number of BFD packets received not matching a BFD session";
      }
    }
  }

  uses bfd-top;
}
