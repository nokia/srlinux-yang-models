module srl_nokia-oam-pm-ethcfm {
  yang-version 1.1;
  namespace "urn:nokia.com:srlinux:ethcfm:oam-pm-ethcfm";
  prefix srl_nokia-oam-pm-ethcfm;

  import srl_nokia-features {
    prefix srl_nokia-feat;
  }
  import srl_nokia-oam {
    prefix srl_nokia-oam;
  }
  import srl_nokia-oam-pm {
    prefix srl_nokia-oam-pm;
  }
  import srl_nokia-oam-pm-types {
    prefix srl_nokia-pm-types;
  }
  import srl_nokia-common {
    prefix srl_nokia-comm;
  }
  import srl_nokia-ethcfm {
    prefix srl_nokia-ethcfm;
  }
  import srl_nokia-ethcfm-types {
    prefix srl_nokia-ethcfm-types;
  }
  import srl_nokia-extensions {
    prefix srl_nokia-ext;
  }
  import srl_nokia-qos {
    prefix srl_nokia-qos;
  }

  organization
    "Nokia";
  contact
    "Nokia SR Linux Support
     Web: <http://www.nokia.com>";
  description
    "This YANG module contains the management data definitions for the
     Ethernet CFM Performance Monitoring.";

  revision 2026-07-31 {
    description
      "SRLinux 26.7.1";
  }
  revision 2025-10-31 {
    description
      "SRLinux 25.10.1";
  }
  revision 2025-07-31 {
    description
      "SRLinux 25.7.1";
  }
  revision 2025-03-31 {
    description
      "SRLinux 25.3.1";
  }
  revision 2024-07-31 {
    description
      "SRLinux 24.7.1";
  }
  revision 2024-03-31 {
    description
      "SRLinux 24.3.1";
  }
  revision 2023-10-31 {
    description
      "SRLinux 23.10.1";
  }

  augment "/srl_nokia-oam:oam/srl_nokia-oam:performance-monitoring" {
    if-feature "srl_nokia-feat:oam-pm and srl_nokia-feat:oam-pm-ethcfm";
    container ethcfm {
      presence "OAM Performance Monitoring using Ethernet CFM";
      uses srl_nokia-oam-pm:oam-pm-resources;
      container delay {
        if-feature "srl_nokia-feat:oam-pm-ethcfm-dmm";
        uses srl_nokia-oam-pm:bin-group;
        description
          "Enter the delay context";
      }
      container loss {
        if-feature "srl_nokia-feat:oam-pm-ethcfm-slm";
        uses srl_nokia-oam-pm:loss-events;
        description
          "Enter the loss context";
      }
      list session {
        key "session-name";
        description
          "Enter the session list instance which contains the test session configuration";
        uses srl_nokia-oam-pm:session;
        uses srl_nokia-oam-pm:measurement-interval;
        container source {
          leaf domain-id {
            mandatory true;
            type leafref {
              path "/srl_nokia-oam:oam/srl_nokia-ethcfm:ethcfm/srl_nokia-ethcfm:domain/srl_nokia-ethcfm:domain-id";
            }
            description
              "The maintenance domain identifier";
          }
          leaf association-id {
            mandatory true;
            type leafref {
              path "/srl_nokia-oam:oam/srl_nokia-ethcfm:ethcfm/srl_nokia-ethcfm:domain[srl_nokia-ethcfm:domain-id=current()/../domain-id]/srl_nokia-ethcfm:association/srl_nokia-ethcfm:association-id";
            }
            description
              "The maintenance association identifier specific to the domain identifier";
          }
          leaf mep-id {
            mandatory true;
            type leafref {
              path "/srl_nokia-oam:oam/srl_nokia-ethcfm:ethcfm/srl_nokia-ethcfm:domain[srl_nokia-ethcfm:domain-id=current()/../domain-id]/srl_nokia-ethcfm:association[srl_nokia-ethcfm:association-id=current()/../association-id]/srl_nokia-ethcfm:mep/srl_nokia-ethcfm:mep-id";
            }
            description
              "The MEP identifier specific to the domain and association identifier";
          }
          description
            "Enter the source context";
        }
        leaf target {
          mandatory true;
          type union {
            type srl_nokia-comm:unicast-mac-address;
            type srl_nokia-ethcfm-types:mep-id-type;
          }
          description
            "Target MAC address or remote MEP ID for the test";
        }
        leaf priority {
          type srl_nokia-ethcfm-types:priority-type;
          default "7";
          description
            "The priority used when generating CFM test frames";
        }
        leaf forwarding-class {
          if-feature "srl_nokia-feat:qos";
          type leafref {
            path "/srl_nokia-qos:qos/srl_nokia-qos:forwarding-classes/srl_nokia-qos:forwarding-class/srl_nokia-qos:name";
          }
          description
            "The forwarding class

             When value not specified, the sgt-qos value will be used";
        }
        leaf profile {
          if-feature "srl_nokia-feat:qos";
          type srl_nokia-comm:rewrite-profile;
          description
            "The profile or drop precedence

             When value not specified, the sgt-qos value will be used";
        }
        container eth-cfm-single-ended-dmm-test {
          if-feature "srl_nokia-feat:oam-pm-ethcfm-dmm";
          leaf admin-state {
            type srl_nokia-comm:admin-state;
            srl_nokia-ext:show-importance "high";
            default "disable";
            description
              "Administrative state of the single ended test";
          }
          uses srl_nokia-oam-pm:operational-states-errors;
          uses srl_nokia-oam-pm:test-session;
          leaf interval {
            type srl_nokia-pm-types:oam-pm-interval-cfm-dmm;
            default "1s";
            description
              "The transmission rate of the CFM packets";
          }
          leaf bin-group {
            srl_nokia-ext:show-importance "high";
            type leafref {
              path "../../../delay/bin-group/bin-group-name";
            }
            default "default";
            description
              "Reference the bin group to be used for this session

               If not specified the 'default' bin-group will be used";
          }
          uses srl_nokia-oam-pm:bin-group-state;
          list measurement-result {
            config false;
            description
              "The test statistics for a delay measurement";
            key "mi-ro-type";
            leaf mi-ro-type {
              type srl_nokia-pm-types:measurement-interval-ro-duration-type;
              description
                "The duration of the measurement interval";
            }
            uses srl_nokia-oam-pm:measurement-interval-index-tracking;
            list index {
              key "index";
              leaf index {
                type uint32;
                description
                  "Measurement interval unique identifier";
              }
              uses srl_nokia-oam-pm:mi-common-state;
              container statistics {
                leaf nominal-frame-count {
                  type union {
                    type srl_nokia-comm:zero-based-counter32;
                    type enumeration {
                      enum not-applicable;
                    }
                  }
                  description
                    "Number of test frames that comprise a completed measurement interval
                     The value of this field is equal to the full length of the measurement-interval duration multiplied by the interval.
                     This value is 'not-applicable to the 'raw' measurement-interval, as it is unbounded.";
                }
                uses srl_nokia-oam-pm:mi-delay-statistics;
                description
                  "Enter the statistics context";
              }
            }
          }
          uses srl_nokia-oam-pm:delay-events-state;
          description
            "Enter the eth-cfm-single-ended-dmm-test context";
        }
        container eth-cfm-single-ended-slm-test {
          if-feature "srl_nokia-feat:oam-pm-ethcfm-slm";
          leaf admin-state {
            type srl_nokia-comm:admin-state;
            default "disable";
            description
              "Administrative state of the single ended test";
          }
          uses srl_nokia-oam-pm:operational-states-errors;
          uses srl_nokia-oam-pm:test-session;
          leaf data-tlv-size {
            type srl_nokia-pm-types:data-tlv-size;
            default "0";
            description
              "The Data TLV byte count used to increase the size of the base CFM PDU
               A value '0' means no Data TLV is added.  Any other value represents the size of the Data TLV.";
          }
          leaf interval {
            description
              "The transmission rate of the CFM packets";
            type srl_nokia-pm-types:oam-pm-interval-cfm-slm;
            default "1s";
          }
          uses srl_nokia-oam-pm:frame-loss-configuration;
          leaf loss-event {
            type leafref {
              path "../../../loss/loss-events-template/loss-events-template-name";
            }
            description
              "The loss event template associated with this loss test session and measurement interval";
          }
          list measurement-result {
            config false;
            description
              "The test statistics for a delay measurement.";
            key "mi-ro-type";
            leaf mi-ro-type {
              type srl_nokia-pm-types:measurement-interval-ro-duration-type;
              description
                "The duration of the measurement interval";
            }
            uses srl_nokia-oam-pm:measurement-interval-index-tracking;
            list index {
              key "index";
              leaf index {
                description
                  "Measurement interval unique identifier";
                type uint32;
              }
              uses srl_nokia-oam-pm:mi-common-state;
              container statistics {
                uses srl_nokia-oam-pm:mi-general-loss-statistics;
                container forward {
                  uses srl_nokia-oam-pm:mi-forward-loss;
                  uses srl_nokia-oam-pm:mi-directional-loss-statistics;
                  description
                    "Enter the forward context";
                }
                container backward {
                  uses srl_nokia-oam-pm:mi-backward-loss;
                  uses srl_nokia-oam-pm:mi-directional-loss-statistics;
                  description
                    "Enter the backward context";
                }
                description
                  "Enter the statistics context";
              }
            }
          }
          uses srl_nokia-oam-pm:loss-events-state;
          description
            "Enter the eth-cfm-single-ended-slm-test context";
        }
      }
    }
  }
}
