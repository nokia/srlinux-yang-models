module srl_nokia-link-measurement {
  yang-version 1.1;
  namespace "urn:nokia.com:srlinux:twamp:link-measurement";
  prefix srl_nokia-link-measurement;

  import srl_nokia-common {
    prefix srl_nokia-comm;
  }
  import srl_nokia-extensions {
    prefix srl_nokia-ext;
  }
  import srl_nokia-features {
    prefix srl_nokia-feat;
  }
  import srl_nokia-interfaces {
    prefix srl_nokia-if;
  }
  import srl_nokia-ippm-source-udp-pool {
    prefix srl_nokia-source-udp;
  }
  import srl_nokia-oam {
    prefix srl_nokia-oam;
  }
  import srl_nokia-network-instance {
    prefix srl_nokia-netinst;
  }
  import srl_nokia-qos {
    prefix srl_nokia-qos;
  }

  organization
    "Nokia";
  contact
    "Nokia SR Linux Support
     Web: <http://www.nokia.com>";
  description
    "This module contains configuration and state data definitions for the dynamic link measurement
     template and the subinterface configuration and state";

  revision 2026-07-31 {
    description
      "SRLinux 26.7.1";
  }
  revision 2026-03-31 {
    description
      "SRLinux 26.3.1";
  }
  revision 2025-03-31 {
    description
      "SRLinux 25.3.1";
  }
  revision 2024-10-31 {
    description
      "SRLinux 24.10.1";
  }
  revision 2024-07-31 {
    description
      "SRLinux 24.7.1";
  }

  grouping link-measurement-template {
    list measurement-template {
      key "template-name";
      max-elements 255;
      description
        "List of measurement templates";
      leaf template-name {
        type srl_nokia-comm:name;
        description
          "Measurement template name";
      }
      leaf admin-state {
        type srl_nokia-comm:admin-state;
        srl_nokia-ext:show-importance "high";
        default "disable";
        description
          "Administrative state of the measurement template.";
      }
      leaf description {
        type srl_nokia-comm:description;
        description
          "Text description for the measurement template";
      }
      leaf unidirectional-measurement {
        type enumeration {
          enum derived {
            value 1;
            description
              "Computes forward unidirectional measurement using round-trip divide by 2";
          }
          enum actual {
            value 2;
            description
              "Computes forward unidirectional measurements using (T2-T1)";
          }
        }
        default "derived";
        description
          "Method used to compute the forward unidirectional delay value";
      }
      leaf delay {
        type enumeration {
          enum minimum {
            value 1;
          }
          enum maximum {
            value 2;
          }
          enum average {
            value 3;
          }
          enum min-of-max {
            value 4;
          }
          enum max-of-min {
            value 5;
          }
        }
        default "minimum";
        description
          "Delay measurement type of interest";
      }
      leaf interval {
        type uint32 {
          range "1..10";
        }
        units "seconds";
        default "1";
        description
          "Interval between test packet transmissions";
      }
      leaf last-reported-dynamic-delay-hold {
        type uint32 {
          range "0..86400";
        }
        units "seconds";
        default "86400";
        description
          "Wait time to flush the last reported delay after operational change

           This command configures the timer that specifies the wait time before the last reported
           delay measurement is flushed after a link measurement test enters the operationally
           down state.

           When 0 the last reported delay is flushed immediately without delay.";
      }
      leaf reporting {
        type boolean;
        default "true";
        description
          "Report value reaching the threshold

           When true threshold events are reported to the routing engine.  When false threshold events are not reported
           to the routing engine";
      }
      leaf reference-active {
        config false;
        type uint8;
        srl_nokia-ext:show-importance "high";
        description
          "Number of interface leaf-refs to this specific measurement-template with admin-state enable";
      }
      leaf reference-total {
        config false;
        type uint8;
        srl_nokia-ext:show-importance "high";
        description
          "Total number of interface leaf-refs to this specific measurement-template";
      }
      container aggregate-sample-window {
        description
          "Enter the aggregate-sample-window context

           Context for aggregate sample window

           The aggregate sample window is a collection of sample windows.  It executes threshold comparisons
           based on the results in each sample window.";
        leaf multiplier {
          type uint32 {
            range "1..12";
          }
          default "12";
          description
            "Number of sample windows comprising the aggregate sample window";
        }
        leaf window-integrity {
          type uint32 {
            range "1..100";
          }
          units "percent";
          description
            "Required sample count to consider window integral

             When not configured, results are compared to the configured thresholds regardless of sample count.";
        }
        container threshold {
          description
            "Enter the threshold context

             Context for threshold configuration";
          leaf relative {
            type uint32 {
              range "1..100";
            }
            units "percent";
            description
              "Percentage of change compared to previously reported result";
          }
          leaf absolute {
            type uint32 {
              range "1..100000";
            }
            units "microseconds";
            description
              "Absolute change compared to previously reported result";
          }
        }
      }
      container sample-window {
        description
          "Enter the sample-window context

           Context for sample window

           The  sample window is a collection of individual test packet results.  It executes threshold comparisons
           using the results in the sample window.";
        leaf multiplier {
          type uint32 {
            range "1..900";
          }
          default "10";
          description
            "Defines the length of the measurement window, multiplier times interval";
        }
        leaf window-integrity {
          type uint32 {
            range "1..100";
          }
          units "percent";
          description
            "Required sample count to consider window integral

             When not configured, results are compared to the configured thresholds regardless of sample count.";
        }
        container threshold {
          description
            "Enter the threshold context

             Context for threshold configuration";
          leaf relative {
            type uint32 {
              range "1..500";
            }
            units "percent";
            description
              "Percentage of change compared to previously reported result";
          }
          leaf absolute {
            type uint32 {
              range "1..100000";
            }
            units "microseconds";
            description
              "Absolute change compared to previously reported result";
          }
        }
      }
      container ip {
        description
          "Enter the ip context

           Context for IP attributes used by the measurement template";
        leaf destination-udp-port {
          type srl_nokia-comm:port-number {
            range "1..65535";
          }
          default "862";
          description
            "Destination UDP port";
        }
        leaf source-udp-port {
          type srl_nokia-comm:port-number {
            range "0 | 64374..64383";
          }
          default "0";
          must "(. = 0) or /srl_nokia-oam:oam/srl_nokia-source-udp:ippm/srl_nokia-source-udp:source-udp-port-pools/srl_nokia-source-udp:port[srl_nokia-source-udp:port-number = current ()]/srl_nokia-source-udp:application-assignment = 'link-measurement'" {
            error-message "The source UDP port must be assigned to the link-measurement application and the UDP port application-assignment cannot be modified if it is configured for link-measurement session";
          }
          description
            "Automatically allocate or statically configure the source UDP port

             When 0 source UDP Port will automatically select an available source UDP port from the dynamic range.  Configuring a specific value requires
             the UDP port to be assigned to the link-measurement application /oam ippm source-udp-port-pools port application-assignment.";
        }
        leaf dscp {
          type srl_nokia-comm:dscp;
          default "CS6";
          description
            "DSCP value";
        }
        leaf forwarding-class {
          if-feature "srl_nokia-feat:qos";
          type leafref {
            path "/srl_nokia-qos:qos/srl_nokia-qos:forwarding-classes/srl_nokia-qos:forwarding-class/srl_nokia-qos:name";
          }
          description
            "The forwarding class

             When value not specified, the sgt-qos value will be used";
        }
        leaf profile {
          if-feature "srl_nokia-feat:qos";
          type srl_nokia-comm:rewrite-profile;
          description
            "The profile or drop precedence

             When value not specified, the sgt-qos value will be used";
        }
        leaf ttl {
          type uint32 {
            range "1..255";
          }
          default "1";
          description
            "Time to live";
        }
        container ipv6-destination-discovery {
          description
            "Enter the ipv6-destination-discovery context

             Context for IPv6 destination discovery

             Ping well-known multicast address ff02::2 (all routers) to solicit response from the peer.  Use the
             source address in the response as the destination address in the STAMP test packets.";
          leaf admin-state {
            type srl_nokia-comm:admin-state;
            default "disable";
            description
              "Administrative state of IPv6 destination discovery";
          }
          leaf discovery-timer {
            type uint32 {
              range "1..1800";
            }
            units "seconds";
            default "60";
            description
              "Maximum time to remain in the discovery phase

               The discovery phase will end when the IPv6 peer is discovered or this timer expires.";
          }
          leaf discovery-interval {
            type uint32 {
              range "1..10";
            }
            units "seconds";
            default "10";
            description
              "Transmission frequency while in discovery phase";
          }
          leaf update-interval {
            type uint32 {
              range "0..3600";
            }
            units "seconds";
            default "600";
            description
              "Transmission frequency to maintain the peer address after discovery phase completes

               When 0 no maintenance of the peer address once the discovery phase ends.";
          }
        }
      }
      container pdu-type {
        description
          "Enter the pdu-type context

           Selection of the test PDU to transmit";
        choice pdu-type {
          description
            "Link measurement protocol selection";
          case stamp-pdu {
            description
              "STAMP protocol format is used to collect performance information";
            reference
              "RFC8972 Section 3";
            container stamp {
              presence "Enables STAMP Protocol";
              description
                "Context for STAMP options used by the measurement template";
              leaf pad-tlv-size {
                type uint32 {
                  range "4..9714";
                }
                units "bytes";
                description
                  "Increase the STAMP PDU by including the PAD TLV";
                reference
                  "RFC8972 Section 4.1";
              }
              container return-path {
                description
                  "Enter the return-path context

                   Context for the STAMP return-path control";
                reference
                  "RFC9503 Section 4";
                choice path-control {
                  case control-code {
                    leaf selection {
                      type enumeration {
                        enum link {
                          value 1;
                          description
                            "Include Return Path sub-TLV instructing session-reflector to use same IP Interface for return packets";
                        }
                      }
                      description
                        "Influence return path processing at session-reflector";
                      reference
                        "RFC9503 Section 4.1.1";
                    }
                  }
                }
              }
            }
          }
          case twamp-light-pdu {
            description
              "TWAMP Light protocol format is used to collect performance information";
            container twamp-light {
              presence "Enables TWAMP Light Protocol";
              description
                "Context for TWAMP-Light options used by the measurement template";
            }
          }
        }
      }
    }
  }

  grouping link-measurement-resources {
    container resources {
      config false;
      description
        "Enter the resources context

         Link Measurement resources";
      container template {
        description
          "Enter the template context

           Session-Sender Link Measurement template resource";
        leaf limit {
          type uint16;
          description
            "Number of Link Measurement templates";
        }
        leaf in-use {
          type uint16;
          description
            "Number of configured Link Measurement templates";
        }
      }
      container interface {
        description
          "Enter the interface context

           Session-Sender Link Measurement IP interface resource";
        leaf limit {
          type uint16;
          description
            "Number of Link Measurement IP interface";
        }
        leaf in-use {
          type uint16;
          description
            "Number of Link Measurement IP interface in use";
        }
      }
      container transmit {
        description
          "Enter the transmit context

           Session-Sender Link Measurement transmit resource";
        leaf limit {
          type uint16;
          description
            "Number of Link Measurement transmit resources";
        }
        leaf in-use {
          type decimal64 {
            fraction-digits 2;
          }
          description
            "Number of Link Measurement transmit resources in use";
        }
      }
      container waiting-for-resources {
        description
          "Enter the waiting-for-resources context

           L3 subinterfaces or lag members waiting for Link Measurement Resources";
        leaf count {
          type uint16;
          description
            "Count of sessisons waiting for resources";
        }
        list interface {
          key "name";
          description
            "List of interface names";
          leaf name {
            type string;
            description
              "The interface name";
          }
          list member {
            description
              "List Ethernet interface";
            key "name";
            leaf name {
              type string;
              description
                "Ethernet interface name associated with the LAG interface";
            }
          }
        }
      }
    }
  }

  grouping interface-configuration {
    container dynamic-measurement {
      presence "Enable dynamic measurements for an IP interface";
      description
        "Context for Dynamic Measurement of IP interface";
      container link-measurement {
        description
          "Enter the link-measurement context

           Context to configure link-measurement interface parameters";
        leaf link-measurement-template {
          type leafref {
            path "/srl_nokia-oam:oam/srl_nokia-link-measurement:link-measurement/srl_nokia-link-measurement:measurement-template/srl_nokia-link-measurement:template-name";
          }
          description
            "The link measurement template assigned to the subinterface";
          mandatory true;
        }
        leaf lag-micro-sessions {
          if-feature "srl_nokia-feat:link-measurement-lag-micro-sessions";
          type boolean;
          description
            "Instantiate link measurement micro sessions for IP subinterfaces with LAG members";
          default "false";
        }
      }
      container protocol {
        description
          "Enter the protocol context

           Context for IP protocol used by the measurement template";
        container ipv4 {
          description
            "Enter the ipv4 context

             Context for ipv4 address configuration";
          leaf admin-state {
            type srl_nokia-comm:admin-state;
            must "not(. = 'enable' and ../../ipv6/admin-state = 'enable')" {
              error-message "IPv4 STAMP link measurement testing cannot be enabled when IPv6 STAMP link measurement testing is enabled";
            }
            default "disable";
            description
              "Administrative state of STAMP IPv4 packets";
          }
          leaf destination-ip {
            type srl_nokia-comm:ipv4-address-excluding-all-zero;
            description
              "Unicast IPv4 destination address

               When not specified and the primary local IP address has a prefix length of 30 or 31 the destination
               address will be the compliment.  Otherwise, must be specified.";
          }
          leaf source-ip {
            type srl_nokia-comm:ipv4-address-excluding-all-zero;
            description
              "Unicast IPv4 source address

               When not specified the primary local interface address will be used.";
          }
        }
        container ipv6 {
          description
            "Enter the ipv6 context

             Context for ipv6 address";
          leaf admin-state {
            type srl_nokia-comm:admin-state;
            default "disable";
            must "not(. = 'enable' and ../../ipv4/admin-state = 'enable')" {
              error-message "IPv6 STAMP link measurement testing cannot be enabled when IPv4 STAMP link measurement testing is enabled";
            }
            description
              "Administrative state of STAMP IPv6 packets";
          }
          leaf destination-ip {
            type srl_nokia-comm:ipv6-address-excluding-all-zero;
            description
              "Global unicast or link-local unicast IPv6 destination address

               When not specified the IPv6 destination discovery is an option for the measurement template.";
          }
          leaf source-ip {
            type srl_nokia-comm:ipv6-address-excluding-all-zero;
            description
              "Global unicast or link-local unicast IPv6 source address

               When not specified the link-local interface address will be used.";
          }
        }
      }
    }
  }

  grouping reported-delay-value {
    leaf last-reported-dynamic-delay {
      srl_nokia-ext:show-importance "high";
      config false;
      type union {
        type int32 {
          range "0..2147483647";
        }
        type enumeration {
          enum none {
            value -1;
            description
              "No value has been reported";
          }
        }
      }
      units "microseconds";
      description
        "Last delay measurement reported";
    }
  }

  grouping link-measurement-interface {
    description
      "Routed subinterface in the network-instance with type default";
    list interface {
      key "name";
      description
        "List of interface names";
      leaf name {
        type srl_nokia-netinst:network-instance-subintf-name;
        description
          "The interface name

           This can be configured in one of two forms.  Fully qualified reference to an interface subinterface,
           example ethernet-1/1.1, or symbolic alias, example interface-1.  When the fully qualified name is
           specified the 'interface-ref' should not be configured.  When the symbolic alias is specified the
           'interface-ref' must be configured.";
        must '(. or ../interface-ref/interface)' {
          error-message "Interface name must be configured";
        }
      }
      container interface-ref {
        if-feature "srl_nokia-feat:interface-references";
        description
          "Enter the interface-ref context

           Reference to a subinterface

           If interface-ref is configured the ../interface/name will be considered as an alias regardless of its form.";
        leaf interface {
          type leafref {
            path "/srl_nokia-if:interface/srl_nokia-if:name";
          }
          description
            "Reference to a base interface";
          must "starts-with(.,'eth') or starts-with(.,'lag')" {
            error-message "Link measurement is supported only on Ethernet and Lag interfaces";
          }
          must 'not(/srl_nokia-if:interface[srl_nokia-if:name=current()]/srl_nokia-if:breakout-mode)' {
            error-message "Breakout interfaces are not supported";
          }
          must '../subinterface >= 0' {
            error-message "subinterface must be configured when interface is set";
          }
        }
        leaf subinterface {
          type leafref {
            path "/srl_nokia-if:interface[srl_nokia-if:name=current()/../interface]/srl_nokia-if:subinterface/srl_nokia-if:index";
          }
          description
            "Reference to a subinterface

             This requires the base interface to be specified using the interface leaf in this container.";
          must '../interface' {
            error-message "interface must be configured when subinterface is set";
          }
        }
      }
      uses interface-configuration;
      uses link-measurement-interface-state;
    }
  }

  grouping link-measurement-sample-windows {
    container aggregate-sample-window {
      description
        "Enter the aggregate-sample-window context

         Context for aggregate sample window statistics

          Rolling buffer maintains the last 20 results.";
      list index {
        key "index";
        description
          "The index list instance";
        leaf index {
          type srl_nokia-comm:counter32;
          description
            "Index used to differentiate aggregate sample windows on the same subinterface";
        }
        leaf end-timestamp-utc {
          srl_nokia-ext:show-importance "high";
          type srl_nokia-comm:date-and-time;
          description
            "Time (UTC) at which this aggregate sample window closed";
        }
        leaf window-state {
          srl_nokia-ext:show-importance "high";
          type enumeration {
            enum completed {
              value 1;
              description
                "Window ran to completion";
            }
            enum in-progress {
              value 2;
              description
                "Window currently active";
            }
            enum sw-reported {
              value 3;
              description
                "Sample window threshold triggered report, aggregated sample window restarted";
            }
            enum asw-reported {
              value 4;
              description
                "Aggregate sample window threshold triggered report";
            }
            enum terminated {
              value 5;
              description
                "Window terminated prior to completion";
            }
          }
        }
        leaf sample-window-count {
          srl_nokia-ext:show-importance "high";
          type srl_nokia-comm:zero-based-counter32;
          description
            "Number of sample windows completed meeting integrity requirement";
        }
        leaf minimum {
          srl_nokia-ext:show-importance "high";
          type uint32;
          units "microseconds";
          description
            "Minimum delay measurement reported to the aggregate sample window";
        }
        leaf maximum {
          srl_nokia-ext:show-importance "high";
          type uint32;
          units "microseconds";
          description
            "Maximum delay measurement reported to the aggregate sample window";
        }
        leaf average {
          srl_nokia-ext:show-importance "high";
          type uint32;
          units "microseconds";
          description
            "Average delay measurement reported to the aggregate sample window";
        }
        leaf result {
          srl_nokia-ext:show-importance "high";
          type uint32;
          units "microseconds";
          description
            "Delay being evaluated for reporting";
        }
        leaf integrity {
          srl_nokia-ext:show-importance "high";
          type boolean;
          description
            "Percentage of results meets integrity criteria";
        }
      }
    }
    container sample-window {
      description
        "Enter the sample-window context

         Context for sample window statistics

          Rolling buffer maintains the last 50 results.";
      list index {
        key "index";
        description
          "Index list instance";
        leaf index {
          type srl_nokia-comm:counter32;
          description
            "Index used to differentiate sample windows on the same subinterface";
        }
        leaf end-timestamp-utc {
          srl_nokia-ext:show-importance "high";
          type srl_nokia-comm:date-and-time;
          description
            "Time (UTC) at which this sample window closed";
        }
        leaf window-state {
          srl_nokia-ext:show-importance "high";
          type enumeration {
            enum completed {
              value 1;
              description
                "Window ran to completion";
            }
            enum in-progress {
              value 2;
              description
                "Window currently active";
            }
            enum sw-reported {
              value 3;
              description
                "Sample window threshold triggered report, aggregated sample window restarted";
            }
            enum terminated {
              value 4;
              description
                "Window terminated prior to completion";
            }
          }
        }
        leaf transmitted-packets {
          srl_nokia-ext:show-importance "high";
          type srl_nokia-comm:zero-based-counter32;
          description
            "Number of STAMP packets transmitted to the session-reflector";
        }
        leaf received-packets {
          srl_nokia-ext:show-importance "high";
          type srl_nokia-comm:zero-based-counter32;
          description
            "Number of STAMP packets received from the session-reflector";
        }
        leaf minimum {
          srl_nokia-ext:show-importance "high";
          type uint32;
          units "microseconds";
          description
            "Minimum delay computed";
        }
        leaf maximum {
          srl_nokia-ext:show-importance "high";
          type uint32;
          units "microseconds";
          description
            "Maximum delay computed";
        }
        leaf average {
          srl_nokia-ext:show-importance "high";
          type uint32;
          units "microseconds";
          description
            "Average delay computed";
        }
        leaf result {
          srl_nokia-ext:show-importance "high";
          type uint32;
          units "microseconds";
          description
            "Delay evaluated for reporting";
        }
        leaf integrity {
          srl_nokia-ext:show-importance "high";
          type boolean;
          description
            "Percentage of results meets integrity criteria";
        }
        leaf error-count {
          srl_nokia-ext:show-importance "high";
          type srl_nokia-comm:zero-based-counter32;
          description
            "Number of erroneous delay measurements that occurred in this sample window";
        }
        leaf stamp-unrecognized-flag-count {
          type srl_nokia-comm:zero-based-counter32;
          description
            "Number of packets in this sample window with the U (Unrecognized) bit set";
        }
        leaf stamp-malformed-flag-count {
          type srl_nokia-comm:zero-based-counter32;
          description
            "Count of packets in this sample window with the M (Malformed) bit set";
        }
        leaf zero-or-negative-delay-count {
          type srl_nokia-comm:zero-based-counter32;
          description
            "Count of packets that have a zero or negative computed delay during this sample window";
        }
        leaf duplicate-packet-count {
          type srl_nokia-comm:zero-based-counter32;
          description
            "Count of duplicate packets that have arrived during this sample window";
        }
      }
    }
  }

  grouping link-measurement-interface-state {
    leaf oper-state {
      config false;
      srl_nokia-ext:show-importance "high";
      type srl_nokia-comm:oper-state;
      description
        "Operational state of link measurement on this interface";
    }
    leaf waiting-for-resource {
      config false;
      type enumeration {
        enum transmit-resource {
          description
            "No transmit resources available";
        }
      }
      description
        "The resource unavailable preventing the instantiation of the session";
    }
    leaf-list operational-failure {
      config false;
      srl_nokia-ext:show-importance "high";
      type enumeration {
        enum no-protocol {
          value 1;
        }
        enum template-admin-down {
          value 2;
        }
        enum udp-port-unavailable {
          value 3;
        }
        enum internal-error {
          value 4;
        }
        enum subinterface-not-found-in-network-instance {
          value 5;
        }
        enum network-instance-type-not-supported {
          value 6;
        }
        enum subinterface-type-not-supported {
          value 7;
        }
        enum no-template {
          value 8;
        }
        enum interface-not-lag {
          value 9;
          description
            "lag-micro-sessions configured against non-lag interface";
        }
      }
      description
        "Reason(s) why this interface's link measurement is operationally disabled";
    }
    leaf detectable-transmit-error {
      config false;
      srl_nokia-ext:show-importance "high";
      type enumeration {
        enum none {
          value 1;
          description
            "No errors found";
        }
        enum subinterface-down {
          value 2;
          description
            "Subinterface is down";
        }
        enum unexpected-error {
          value 3;
          description
            "Resource or system error";
        }
        enum source-ip-not-local {
          value 5;
          description
            "Source IP is not found in the default network-instance";
        }
        enum invalid-dest-ip {
          value 6;
          description
            "Unresolved or invalid destination IP address";
        }
        enum subinterface-type-not-supported {
          value 7;
          description
            "Subinterace not type routed";
        }
        enum same-source-ip-destination-ip {
          value 8;
          description
            "Same source and destination IP address";
        }
      }
      description
        "Detectable error interrupting Link Measurement tests

         Packet transmission is prevented for the following detectable transmit errors; subinterface-down,
         invalid-dest-ip, invalid-subinterface-type, same-source-ip-destination-ip.";
    }
    leaf interface {
      config false;
      srl_nokia-ext:show-importance "high";
      type leafref {
        path "/srl_nokia-if:interface/srl_nokia-if:name";
      }
      description
        "Ethernet interface displayed when IP interface link measurement is not configured on LAG and lag-micro-sessions is false";
    }
    leaf lag {
      config false;
      srl_nokia-ext:show-importance "high";
      type leafref {
        path "/srl_nokia-if:interface/srl_nokia-if:name";
      }
      description
        "LAG interface displayed when IP interface link measurement is configured on LAG";
    }
    leaf lag-micro-sessions-count {
      config false;
      srl_nokia-ext:show-importance "high";
      type uint8;
      description
        "Number of session-sender test sessions displayed when IP interface is configured on LAG and lag-micro-sessions is true";
    }
    leaf operational-source-address {
      config false;
      type srl_nokia-comm:ip-address;
      description
        "Source IP address used by STAMP test packets";
    }
    leaf source-ip-auto-assigned {
      config false;
      type boolean;
      description
        "Source IP address auto assigned";
    }
    leaf operational-destination-address {
      config false;
      type srl_nokia-comm:ip-address;
      description
        "Destination IP address used by STAMP test packets";
    }
    leaf destination-ip-auto-assigned {
      config false;
      type boolean;
      description
        "Destination IP address auto assigned";
    }
    leaf in-use-source-udp-port {
      config false;
      type uint32;
      description
        "Source UDP port in use";
    }
    leaf in-use-destination-udp-port {
      config false;
      type uint32;
      description
        "Destination UDP port in use";
    }
    leaf stamp-session-identifier {
      srl_nokia-ext:show-importance "high";
      config false;
      type uint16;
      description
        "Automatically generated Session Sender ID (SSID) assigned to the session";
    }
    leaf reporting {
      srl_nokia-ext:show-importance "high";
      config false;
      type boolean;
      description
        "IP interface reporting to the routing engine";
    }
    uses reported-delay-value;
    leaf report-timestamp {
      config false;
      srl_nokia-ext:show-importance "high";
      type srl_nokia-comm:date-and-time;
      description
        "Time a threshold event was last reported to the routing engine

         When ./last-reported-dynamic-delay > 0, report-timestamp holds the time at which
         ./last-reported-dynamic-delay was reported to the routing engine.

         When ./last-reported-dynamic-delay = 0, report-timestamp holds the time at which
         ./last-reported-dynamic-delay was 'cleared' (because aging timer expired).

         When ./last-reported-dynamic-delay = 'none', report-timestamp holds '1970-Jan-01 00:00:00.0'
         UTC as a placeholder representing a delay has not yet been reported to the routing
         engine.";
    }
    leaf report-triggered-by {
      config false;
      type enumeration {
        enum none {
          value 1;
        }
        enum sample-threshold-absolute {
          value 2;
        }
        enum sample-threshold-relative {
          value 3;
        }
        enum aggregate-threshold-absolute {
          value 4;
        }
        enum aggregate-threshold-relative {
          value 5;
        }
        enum expired {
          value 6;
        }
        enum reporting-disabled {
          value 7;
        }
      }
      description
        "Triggering event for the report";
    }
    leaf measurement-source {
      config false;
      type string;
      description
        "IP Interface name or Ethernet interface name which triggered the report

         IP interface name will be used when lag-micro-sessions is false.
         Ethernet interface name will be used when lag-micro-sessions is true.";
    }
    leaf aggregate-newest-index {
      config false;
      type srl_nokia-comm:counter32;
      description
        "Index of the newest aggregate sample window for this subinterface";
    }
    leaf sample-newest-index {
      config false;
      srl_nokia-ext:show-importance "high";
      type srl_nokia-comm:counter32;
      description
        "Index of the newest sample window for this subinterface";
    }
    container statistics {
      config false;
      description
        "Enter the statistics context

         Aggregate sample window information and sample window statistics when lag-micro-sessions false";
      uses link-measurement-sample-windows;
    }
    container lag-micro-sessions {
      config false;
      description
        "Enter the lag-micro-sessions context

         Entry for LAG Micro Session statistics";
      list lag {
        description
          "List LAG interface displayed when lag-micro-sessions true";
        key "name";
        leaf name {
          srl_nokia-ext:show-importance "high";
          type leafref {
            path "/srl_nokia-if:interface/srl_nokia-if:name";
          }
          description
            "LAG interface name the IP interface is configured over";
        }
        list member {
          srl_nokia-ext:show-importance "high";
          description
            "List Ethernet interface";
          key "name";
          leaf name {
            srl_nokia-ext:show-importance "high";
            type leafref {
              path "/srl_nokia-if:interface/srl_nokia-if:name";
            }
            description
              "Ethernet interface name associated with the LAG interface";
          }
          leaf oper-state {
            srl_nokia-ext:show-importance "high";
            type srl_nokia-comm:oper-state;
            description
              "Operational state of link measurement on this member";
          }
          leaf waiting-for-resource {
            srl_nokia-ext:show-importance "high";
            type enumeration {
              enum transmit-resource {
                description
                  "No transmit resources available";
              }
            }
            description
              "The resource unavailable preventing the instantiation of the session";
          }
          leaf aggregate-newest-index {
            type srl_nokia-comm:counter32;
            description
              "Index of the newest aggregate sample window for this subinterface";
          }
          leaf sample-newest-index {
            srl_nokia-ext:show-importance "high";
            type srl_nokia-comm:counter32;
            description
              "Index of the newest sample window for this subinterface";
          }
          leaf stamp-session-identifier {
            srl_nokia-ext:show-importance "high";
            type uint16;
            description
              "Automatically generated Session Sender ID (SSID) assigned to the session";
          }
          leaf detectable-transmit-error {
            srl_nokia-ext:show-importance "high";
            type enumeration {
              enum none {
                value 1;
                description
                  "No errors found";
              }
              enum unexpected-error {
                value 2;
                description
                  "Resource or system error";
              }
              enum interface-down {
                value 3;
                description
                  "Ethernet interface is down";
              }
            }
            description
              "Detectable error interrupting Link Measurement tests on the Ethernet interface

               Packet transmission is prevented for the following detectable transmit errors; interface-down";
          }
          leaf sender-micro-session-id {
            srl_nokia-ext:show-importance "high";
            type uint16;
            description
              "Automatically generated sender micro-session identifier";
          }
          leaf reflector-micro-session-id {
            srl_nokia-ext:show-importance "high";
            type uint16;
            description
              "Reflector micro-session identifier received from the session-reflector";
          }
          leaf reflector-micro-session-id-change-count {
            srl_nokia-ext:show-importance "high";
            type srl_nokia-comm:counter64;
            description
              "Count of reflector micro-session identifier changes";
          }
          container frame-discards {
            leaf sender-micro-session-id-zero {
              srl_nokia-ext:show-importance "high";
              type srl_nokia-comm:counter64;
              description
                "Count of packets sender micro-session identifier all zeros";
            }
            leaf reflector-micro-session-id-zero {
              srl_nokia-ext:show-importance "high";
              type srl_nokia-comm:counter64;
              description
                "Count of packets reflector micro-session identifier all zeros";
            }
            leaf sender-micro-session-id-mismatch {
              srl_nokia-ext:show-importance "high";
              type srl_nokia-comm:counter64;
              description
                "Count of packets sender micro-session identifier does not match intended value";
            }
            description
              "Enter the frame-discards context";
          }
          container statistics {
            description
              "Enter the statistics context

               Aggregate sample window information and sample window statistics when lag-micro-sessions ture";
            uses link-measurement-sample-windows;
          }
        }
      }
    }
  }

  augment "/srl_nokia-oam:oam" {
    if-feature "srl_nokia-feat:link-measurement";
    container link-measurement {
      presence "Enable Link Measurement context";
      description
        "Context for Link Measurement";
      uses link-measurement-resources;
      uses link-measurement-template;
      uses link-measurement-interface;
    }
  }
}
