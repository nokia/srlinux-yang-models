module srl_nokia-macsec {
  yang-version 1.1;
  namespace "urn:srl_nokia-macsec";
  prefix srl_nokia-macsec;

  import srl_nokia-common {
    prefix srl_nokia-comm;
  }
  import srl_nokia-features {
    prefix srl_nokia-feat;
  }
  import srl_nokia-extensions {
    prefix srl_nokia-ext;
  }
  import srl_nokia-interfaces {
    prefix srl_nokia-if;
  }
  import srl_nokia-keychains {
    prefix srl-keychain;
  }
  import srl_nokia-system {
    prefix srl_nokia-system;
  }

  description
    "Model for managing Radio subinterfaces";

  revision 2022-11-30 {
    description
      "SRLinux 22.11.1";
  }

  typedef macsec-cipher-suite {
    type enumeration {
      enum GCM_AES_128 {
        description
          "GCM-AES-128 Cipher Suite";
      }
      enum GCM_AES_256 {
        description
          "GCM-AES-256 Cipher Suite";
      }
      enum GCM_AES_XPN_128 {
        description
          "GCM-AES-XPN-128 Cipher Suite";
      }
      enum GCM_AES_XPN_256 {
        description
          "GCM-AES-XPN-256 Cipher Suite";
      }
    }
    description
      "Set Cipher suite(s) for SAK derivation";
  }

  typedef confidentiality-offset {
    type enumeration {
      enum 0_BYTES {
        description
          "No octets are sent unencrypted";
      }
      enum 30_BYTES {
        description
          "30 octects are sent unencrypted";
      }
      enum 50_BYTES {
        description
          "50 octects are sent unencrypted";
      }
    }
    description
      "The confidentiality offset specifies a number of octets in an Ethernet
       frame that are sent in unencrypted plain-text";
  }

  typedef tag-mode {
    type enumeration {
      enum no-tag {
        description
          "don't put any tags into clear";
      }
      enum single-tag {
        description
          "put 4 bytes after the MAC header into clear";
      }
      enum double-tag {
        description
          "put 8 bytes after the MAC header into clear";
      }
    }
    description
      "By default macsec encrypts the 802.1q and q-in-q tags.
       Clear-tag-mode specifies if the user desires to put a single tag or double tag into clear.";
  }

  typedef protocols {
    type enumeration {
      enum lacp {
        description
          "lacp protocol";
      }
      enum lldp {
        description
          "lldp protocol";
      }
      enum cdp {
        description
          "cisco discovery protocol";
      }
      enum eapol-start {
        description
          "eap over lan start packets";
      }
      enum efm-oam {
        description
          "ethernet in first mile protocol";
      }
      enum eth-cfm {
        description
          "connectivity fault management protocol";
      }
      enum ptp {
        description
          "Precision Time Protocol";
      }
      enum ubfd {
        description
          "micro bfd protocol";
      }
    }
    description
      "protocols that can be excluded from macsec";
  }

  grouping macsec-mka-policy-config {
    description
      "MKA policy config grouping";
    leaf name {
      type string;
      description
        "Name of the MKA policy.";
    }
    leaf max-peers {
      type int32 {
        range "1..512";
      }
      description
        "max mka peers allowed";
    }
    leaf key-server-priority {
      type uint8;
      default "16";
      description
        "Specifies the key server priority used by the MACsec Key Agreement
         (MKA) protocol to select the key server when MACsec is enabled using
         static connectivity association key (CAK) security mode. The switch with
         the lower priority-number is selected as the key server. If the
         priority-number is identical on both sides of a point-to-point link, the
         MKA protocol selects the device with the lower MAC address as the key
         server";
    }
    leaf eapol-destinatino-address {
      type srl_nokia-comm:mac-address;
      description
        "this command can be used to set eap over lan destination mac to a
         unicast mac for L2 multiple hop networks";
    }
    leaf hello-interval {
      type uint32 {
        range "0 | 1..6";
      }
      default "2";
      description
        "mka hello interval, the intervals are 500 ms and 1 to 6 seconds,
         configuration of 0 is for 500ms ";
    }
    leaf-list macsec-cipher-suite {
      type macsec-cipher-suite;
      description
        "Set Cipher suite(s) for SAK derivation";
    }
    leaf confidentiality-offset {
      type confidentiality-offset;
      default "0_BYTES";
      description
        "The confidentiality offset specifies a number of octets in an Ethernet
         frame that are sent in unencrypted plain-text";
    }
    leaf clear-tag-mode {
      type tag-mode;
      default "no-tag";
      description
        "specifies the number of tags that will be in clear infront of the sectag.";
    }
    leaf delay-protection {
      type boolean;
      default "false";
      description
        "Traffic delayed longer than 2 seconds is rejected by the interfaces
         enabled with delay protection.";
    }
    leaf encrypt {
      type boolean;
      default "true";
      description
        "Enable or disable PDU encryption, if enabled the PDUs are encrypted and authenticated
         if disabled the PDU is only authenticated and not encrypted.";
    }
    leaf sak-rekey-on-live-peer-loss {
      type boolean;
      default "false";
      description
        "Rekey on peer loss";
    }
  }

  grouping macsec-mka-error-counters {
    description
      "MKA error counters grouping";
    leaf out-mkpdu-errors-pdu-too-small {
      type srl_nokia-comm:zero-based-counter64;
      description
        "MKPDU TX error count";
    }
    leaf out-mkpdu-errors-pdu-too-big {
      type srl_nokia-comm:zero-based-counter64;
      description
        "MKPDU TX error count";
    }
    leaf out-mkpdu-errors-pdu-not-quad-size {
      type srl_nokia-comm:zero-based-counter64;
      description
        "MKPDU TX error count";
    }
    leaf out-mkpdu-errors-pdu-invalid-number {
      type srl_nokia-comm:zero-based-counter64;
      description
        "MKPDU TX error count";
    }
    leaf in-mkpdu-icv-verification-errors {
      type srl_nokia-comm:zero-based-counter64;
      description
        "MKPDU RX ICV verification error count";
    }
    leaf in-mkpdu-validation-errors {
      type srl_nokia-comm:zero-based-counter64;
      description
        "MKPDU RX validation error count";
    }
    leaf in-mkpdu-bad-peer-errors {
      type srl_nokia-comm:zero-based-counter64;
      description
        "MKPDU RX bad peer message number error count";
    }
    leaf in-mkpdu-peer-list-errors {
      type srl_nokia-comm:zero-based-counter64;
      description
        "MKPDU RX non-recent peer list Message Number error count";
    }
    leaf sak-generation-errors {
      type srl_nokia-comm:zero-based-counter64;
      description
        "MKA error SAK generation count";
    }
    leaf sak-hash-errors {
      type srl_nokia-comm:zero-based-counter64;
      description
        "MKA error Hash Key generation count";
    }
    leaf sak-encryption-errors {
      type srl_nokia-comm:zero-based-counter64;
      description
        "MKA error SAK encryption/wrap count";
    }
    leaf sak-decryption-errors {
      type srl_nokia-comm:zero-based-counter64;
      description
        "MKA error SAK decryption/unwrap count";
    }
    leaf sak-cipher-mismatch-errors {
      type srl_nokia-comm:zero-based-counter64;
      description
        "MKA error SAK cipher mismatch count";
    }
    leaf sak-install-fail {
      type srl_nokia-comm:zero-based-counter64;
      description
        "MKA error SAK cipher mismatch count";
    }
  }

  grouping macsec-mka-global-state {
    description
      "MKA global state grouping";
    container counters {
      description
        "MKA global counters";
      uses macsec-mka-error-counters;
    }
  }

  grouping macsec-mka-global-top {
    description
      "MKA global top level grouping";
    container state {
      config false;
      description
        "Operational state data for MKA";
      uses macsec-mka-global-state;
    }
  }

  grouping macsec-mka-interface-state {
    description
      "MKA interface specific states";
    leaf oper-state {
      srl_nokia-ext:show-importance "high";
      description
        "The operational state of the mka instance";
      type srl_nokia-comm:oper-state;
    }
    leaf encryptoin-offset {
      type confidentiality-offset;
      description
        "Indicates the operational encryption offset used for the datapath PDUs
         when all parties in the CA have the SAK. This value is specified by the key server.";
    }
    leaf oper-cipher {
      type macsec-cipher-suite;
      description
        "Indicates the operational encryption algorithm used for datapath PDUs when all
         parties in the CA have the SAK. This value is specified by the key server.";
    }
    leaf member-id {
      type binary {
        length "12";
      }
      description
        "Indicates the Member Identifier (MI) for the MKA instance.";
    }
    leaf outbound-sci {
      type binary {
        length "8";
      }
      description
        "Indicates the Secure Channel Identifier (SCI) information for transmitting MACsec frames.";
    }
    leaf message-count {
      type uint32;
      description
        "Indicates the current count of MKA messages that is attached to MKA PDUs.";
    }
    leaf key-number {
      type uint32;
      description
        "Indicates the number of the currently assigned CAK.
         When a new CAK is generated, this number is incremented.";
    }
    leaf key-server {
      type boolean;
      description
        "Indicates whether this server is the highest priority server in the peer group.";
    }
    leaf latest-sak-an {
      type uint32;
      description
        "Indicates the Association Number (AN) of the latest Secure Association Key (SAK).
         This number is concatenated with an SCI to identify a Secure Association (SA).";
    }
    leaf previous-sak-an {
      type uint32;
      description
        "Indicates the AN of the previous SAK.
         This number is concatenated with an SCI to identify an SA.";
    }
    leaf latest-sak-ki {
      type binary {
        length "16";
      }
      description
        "Indicates the Key Identifier (KI) of the latest SAK.
         This number is derived from the MI of the key server and the key number.";
    }
    leaf previous-sak-ki {
      type binary {
        length "16";
      }
      description
        "Indicates the KI of the previous SAK.
         This number is derived from the MI of the key server and the key number.";
    }
    leaf latest-sak-lpn {
      type srl_nokia-comm:counter64;
      description
        "Indicates Lowest Acceptable Packet Number of the latest SAK.";
    }
    leaf previous-sak-lpn {
      type srl_nokia-comm:counter64;
      description
        "Indicates Lowest Acceptable Packet Number of the previous SAK.";
    }
    list mka-peer {
      key "member-id";
      description
        "Enter the mka-peer list instance";
      leaf member-id {
        type binary {
          length "12";
        }
        description
          "Specifies the MI of the peer entry.";
      }
      leaf member-number {
        type srl_nokia-comm:counter64;
        description
          "Indicates the latest Member Number of the peer entry.";
      }
      leaf type {
        type enumeration {
          enum live-peer-list {
            value 1;
          }
          enum potential-peer-list {
            value 2;
          }
        }
        description
          "Indicates the type of the peer entry. live-peer-list(1): the peer entry is in the Live Peer List. potential-peer-list(2): the peer entry is in the Potential Peer List.";
      }
      leaf sci {
        type binary {
          length "8";
        }
        description
          "Indicates the SCI information of this peer list entry.";
      }
      leaf key-server-priority {
        type srl_nokia-comm:counter64;
        description
          "Indicates the priority of this MKA peer.";
      }
      leaf lowest-acceptable-packet-number {
        type srl_nokia-comm:counter64;
        description
          "Indicates the lowest acceptable packet number of this MKA peer.";
      }
    }
    container counters {
      description
        "MKA interface counters";
      uses macsec-mka-interface-counters;
      uses macsec-mka-error-counters;
    }
  }

  grouping macsec-mka-interface-counters {
    description
      "MKA interface state grouping";
    leaf in-mkpdu {
      type srl_nokia-comm:zero-based-counter64;
      description
        "Validated MKPDU received count";
    }
    leaf sak-generated {
      type srl_nokia-comm:zero-based-counter64;
      description
        "Indicates the number of SAKs generated by this MKA instance.";
    }
    leaf in-sak-mkpdu {
      type srl_nokia-comm:zero-based-counter64;
      description
        "Validated and installed MKPDU received SAK count";
    }
    leaf out-sak-mkpdu {
      type srl_nokia-comm:zero-based-counter64;
      description
        "Validated and installed MKPDU transmit SAK count";
    }
    leaf in-cak-mkpdu {
      type srl_nokia-comm:zero-based-counter64;
      description
        "Validated MKPDU received CAK count";
    }
    leaf out-mkpdu {
      type srl_nokia-comm:zero-based-counter64;
      description
        "MKPDU sent count";
    }
    leaf out-cak-mkpdu {
      type srl_nokia-comm:zero-based-counter64;
      description
        "MKPDU CAK sent count";
    }
    leaf peers-removed {
      type srl_nokia-comm:zero-based-counter64;
      description
        "Indicates the number of peers removed from the live/potential peer
         list due to not receiving an MKPDU within the MKA Live Time (6.0 sec).";
    }
    leaf ckn-not-found {
      type srl_nokia-comm:zero-based-counter64;
      description
        "Indicates the number of MKPDUs received with a CKN that
         does not match the CA configured for the port.";
    }
    leaf new-live-peer {
      type srl_nokia-comm:zero-based-counter64;
      description
        "Indicates the number of validated peers that have
         been added to the live peer list.";
    }
    leaf parameter-size-invalid {
      type srl_nokia-comm:zero-based-counter64;
      description
        "Indicates the number of MKPDUs received which contain a
         parameter set body length that exceeds the remaining length of the MKPDU.";
    }
    leaf liveness-check-fail {
      type srl_nokia-comm:zero-based-counter64;
      description
        "Indicates the number of MKPDUs received which contain
         an MN that is not acceptably recent.";
    }
    leaf parameter-not-quad-size {
      type srl_nokia-comm:zero-based-counter64;
      description
        "Indicates the number of MKPDUs received which contain
         a parameter set that is not a multiple of 4 octets.";
    }
    leaf unsupported-algorithm-agility {
      type srl_nokia-comm:zero-based-counter64;
      description
        "Indicates the number of MKPDUs received which contain
         an unsupported Algorithm Agility value.";
    }
    leaf invalid-ckn-length {
      type srl_nokia-comm:zero-based-counter64;
      description
        "Indicates the number of MKPDUs received which contain a
         CAK name that exceeds the maximum CAK name length.";
    }
    leaf peer-same-mi {
      type srl_nokia-comm:zero-based-counter64;
      description
        "Indicates the number of MKPDUs received which contain
         a peerlist with an MI entry which conflicts with the local MI.";
    }
    leaf sak-non-live-peer {
      type srl_nokia-comm:zero-based-counter64;
      description
        "Indicates the number of SAKs received from a peer that
         is not a member of the Live Peers List.";
    }
    leaf sak-no-key-server {
      type srl_nokia-comm:zero-based-counter64;
      description
        "Indicates the number of SAKs received from an MKA participant
         that has not been designated as the Key Server.";
    }
    leaf key-number-invalid {
      type srl_nokia-comm:zero-based-counter64;
      description
        "Indicates the number of SAKs received with an invalid Key Number.";
    }
    leaf cak-info-missing {
      type srl_nokia-comm:zero-based-counter64;
      description
        "Indicates the number of times internal CAK data is not available
         for the generation of the SAK.";
    }
    leaf max-peers-set-zero {
      type srl_nokia-comm:zero-based-counter64;
      description
        "Indicates the number of SecY SAK installations that have failed
         due to the max peer entry being set to 0.";
    }
  }

  grouping macsec-interface-config {
    description
      "Media Access Control Security (MACsec) config grouping";
    leaf enable {
      type srl_nokia-comm:admin-state;
      default "disable";
      description
        "Enable MACsec on an interface";
    }
    leaf replay-protection {
      type uint16;
      default "0";
      description
        "MACsec window size, as defined by the number of out-of-order frames
         that are accepted. A value of 0 means that frames are accepted only in
         the correct order.";
    }
    leaf rx-must-be-encrypted {
      type boolean;
      default "true";
      description
        "when true; only accept encrypted packets,
         if false accept a mix of encrypted and clear text packets";
    }
    list exclude-protocols {
      key "protocol";
      leaf protocol {
        type protocols;
        description
          "exclude this protocol";
      }
      description
        "protocols to be excluded from macsec";
    }
    list exclude-mac {
      key "dst-mac";
      leaf dst-mac {
        type srl_nokia-comm:mac-address;
        description
          "exclude this destination mac from encryptino";
      }
      description
        "list of destination macs to be excluded from the macsec encryptoin";
    }
  }

  grouping macsec-mka-policy-top {
    description
      "MKA policy top level grouping";
    container policies {
      description
        "Enclosing container for the list of MKA policies";
      list policy {
        key "name";
        description
          "List of MKA policies";
        leaf name {
          type leafref {
            path "../config/name";
          }
          description
            "Reference to MKA policy name";
        }
        container config {
          description
            "Configuration of the MKA policy";
          uses macsec-mka-policy-config;
        }
        container state {
          config false;
          description
            "Operational state data for MKA policy";
          uses macsec-mka-policy-config;
        }
      }
    }
  }

  grouping macsec-mka-interface-config {
    description
      "MKA interface config grouping";
    leaf mka-policy {
      type leafref {
        path "/macsec/mka/policies/policy/name";
      }
      description
        "Apply MKA policy on the interface";
    }
    leaf key-chain {
      type leafref {
        path "/srl_nokia-system:system/srl-keychain:authentication/srl-keychain:keychain/srl-keychain:name";
      }
      must '/srl_nokia-system:system/srl-keychain:authentication/srl-keychain:keychain[srl-keychain:name = current()]'
         + '/srl-keychain:type = "macsec"' {
        error-message "Only keychain of type macsec can be assigned";
      }
    }
  }

  grouping macsec-scsa-tx-interface-state {
    description
      "State leaves assigned with the TX Secure Channel and Secure
       Association";
    leaf sci-tx {
      type srl_nokia-comm:hex-string {
        length "16";
      }
      description
        "Secure Channel Identifier.
         Every Transmit Channel is uniquely identified using this field.";
    }
  }

  grouping macsec-scsa-tx-interface-stats {
    description
      "TX Secure Channel and Secure Association Information";
    leaf sc-auth-only {
      type srl_nokia-comm:zero-based-counter64;
      description
        "Secure Channel Authenticated only TX Packets counter.
         This counter reflects the number of authenticated only transmitted
         packets in a secure channel.";
    }
    leaf sc-encrypted {
      type srl_nokia-comm:zero-based-counter64;
      description
        "Secure Channel Encrypted TX Packets counter.
         This counter reflects the number of encrypted and authenticated
         transmitted packets in a secure channel.";
    }
    leaf sc-octets-auth-only {
      type srl_nokia-comm:zero-based-counter64;
      description
        "Secure Channel Authenticated only TX octets counter.
         This counter reflects the number of authenticated only transmitted
         octets in a secure channel.";
    }
    leaf sc-octets-encrypted {
      type srl_nokia-comm:zero-based-counter64;
      description
        "Secure Channel Encrypted TX octets counter.
         This counter reflects the number of encrypted and authenticated
         transmitted octets in a secure channel.";
    }
    list security-association {
      key "tx-sa-an";
      description
        "Enter the transmitting-sa list instance";
      leaf tx-sa-an {
        type uint32;
        description
          "Indicates the AN for identifying the transmitting SA.";
      }
      leaf sa-auth-only {
        type srl_nokia-comm:zero-based-counter64;
        description
          "Secure Association Authenticated only TX Packets counter.
           This counter reflects the number of authenticated only, transmitted
           packets in a secure association.";
      }
      leaf sa-encrypted {
        type srl_nokia-comm:zero-based-counter64;
        description
          "Secure Association Encrypted TX Packets counter.
           This counter reflects the number of encrypted and authenticated
           tra
           nsmitted packets in a secure association.";
      }
    }
  }

  grouping macsec-scsa-rx-interface-state {
    description
      "State associated nwith RX Secure Channel and Secure Association
       Information.";
    leaf sci-rx {
      type srl_nokia-comm:hex-string {
        length "16";
      }
      description
        "Secure Channel Identifier.
         Every Receive Channel is uniquely identified using this field.";
    }
  }

  grouping macsec-scsa-rx-interface-stats {
    description
      "RX Secure Channel and Secure Association Information";
    leaf sc-invalid {
      type srl_nokia-comm:zero-based-counter64;
      description
        "Invalid Secure Channel RX Packets counter.
         This counter reflects the number of invalid received packets in a
         secure channel.
         Indicates the summation of counter /macsec/rx-sa/not-valid-packets
         information for all the SAs which belong to this SC.";
    }
    leaf sc-valid {
      type srl_nokia-comm:zero-based-counter64;
      description
        "Valid Secure Channel RX Packets counter.
         This counter reflects the number of valid received packets in a
         secure channel.
         Indicates the summation of counter /macsec/rx-sa/ok-packets
         information for all the SAs which belong to this SC.";
    }
    leaf sc-octets-invalid {
      type srl_nokia-comm:zero-based-counter64;
      description
        "Invalid Secure Channel RX Packets counter.
         This counter reflects the number of invalid received packets in a
         secure channel.";
    }
    leaf sc-octets-valid {
      type srl_nokia-comm:zero-based-counter64;
      description
        "Valid Secure Channel RX Packets counter.
         This counter reflects the number of valid received packets in a
         secure channel.
         Indicates the number of octets of plain text recovered from
         received packets that were integrity protected and encrypted.";
    }
    leaf not-using-sa-packets {
      type srl_nokia-comm:zero-based-counter64;
      units "packets";
      description
        "Indicates the summation of counter /macsec/rx-sa/not-using-sa-packets
         information for all the SAs which belong to this SC.";
    }
    leaf late-packets {
      type srl_nokia-comm:zero-based-counter64;
      units "packets";
      description
        "Indicates the number of received packets that have been
         discarded due to replay window protection on this SC.";
    }
    leaf delayed-packets {
      type srl_nokia-comm:zero-based-counter64;
      units "packets";
      description
        "Indicates the number of received packets with the condition
         that the PN of the packets is lower than the lower bound of the replay protection PN.";
    }
    leaf unchecked-packets {
      type srl_nokia-comm:zero-based-counter64;
      units "packets";
      description
        "Indicates the number of packets that have failed the integrity check on this SC.";
    }
    list security-association {
      key "rx-sa-an";
      description
        "Enter the receiving-sa list instance";
      leaf rx-sa-an {
        type uint32;
        description
          "Indicates the AN for identifying the receiving SA.";
      }
      leaf sa-invalid {
        type srl_nokia-comm:zero-based-counter64;
        description
          "Invalid Secure Association RX Packets counter.
           This counter reflects the number of integrity check fails for received
           packets in a secure association.";
      }
      leaf discarded-inactive {
        type srl_nokia-comm:zero-based-counter64;
        units "packets";
        description
          "Indicates the number of received packets that have
           been discarded on this SA which is not currently in use.";
      }
      leaf discarded-active {
        type srl_nokia-comm:zero-based-counter64;
        units "packets";
        description
          "Indicates the number of not valid packets that have
           been discarded on this active SA.";
      }
      leaf sa-valid {
        type srl_nokia-comm:zero-based-counter64;
        description
          "Secure Association Valid RX Packets counter.
           This counter reflects the number of packets in a secure association
           that passed integrity check.";
      }
    }
  }

  grouping macsec-interface-counters {
    description
      "MACsec interface state grouping";
    leaf tx-untagged-pkts {
      type srl_nokia-comm:zero-based-counter64;
      description
        "MACsec interface level Transmit untagged Packets counter.
         This counter will increment if MACsec is enabled on interface and the
         outgoing packet is not tagged with MACsec header.";
    }
    leaf tx-too-long-packets {
      type srl_nokia-comm:zero-based-counter64;
      units "packets";
      description
        "Indicates the number of transmitted packets discarded because
         the packet length is greater than the Maximum Transmission Unit
         (MTU) of the Ethernet physical interface.";
    }
    leaf rx-untagged-pkts {
      type srl_nokia-comm:zero-based-counter64;
      description
        "MACsec interface level Receive untagged Packets counter.
         This counter will increment if MACsec is enabled on interface and the
         incoming packet does not have MACsec tag.";
    }
    leaf rx-badtag-pkts {
      type srl_nokia-comm:zero-based-counter64;
      description
        "MACsec interface level Receive Bad Tag Packets counter.
         This counter will increment if MACsec is enabled on interface and
         incoming packet has incorrect MACsec tag.";
    }
    leaf rx-unknownsci-pkts {
      type srl_nokia-comm:zero-based-counter64;
      description
        "MACsec interface level Receive Unknown SCI Packets counter.
         This counter will increment if MACsec is enabled on the interface and
         SCI present in the MACsec tag of the incoming packet does not match any
         SCI present in ingress SCI table.";
    }
    leaf rx-nosci-pkts {
      type srl_nokia-comm:zero-based-counter64;
      description
        "MACsec interface level Receive No SCI Packets counter.
         This counter will increment if MACsec is enabled on interface and
         incoming packet does not have SCI field in MACsec tag.";
    }
    leaf rx-overrun-packets {
      type srl_nokia-comm:zero-based-counter64;
      units "packets";
      description
        "Indicates the number of packets discarded because the number of
         received packets exceeded the cryptographic performance capabilities.";
    }
  }

  grouping macsec-scsa-interface-top {
    description
      "Secure channel and Secure Association Statistics";
    container scsa-tx {
      config false;
      description
        "Enclosing container for transmitted packets for Secure Channel and
         Secure Association";
      list scsa-tx {
        key "sci-tx";
        description
          "TX Secure Channel and Secure Association Statistics";
        leaf sci-tx {
          type leafref {
            path "../state/sci-tx";
          }
          description
            "TX Secure Channel and Secure Association Statistics";
        }
        container state {
          description
            "State container for macsec-scsa-tx-interface-stats";
          uses macsec-scsa-tx-interface-state;
          container counters {
            description
              "Counters container for macsec-scsa-tx-interface-stats";
            uses macsec-scsa-tx-interface-stats;
          }
        }
      }
    }
    container scsa-rx {
      config false;
      description
        "Enclosing container for received packets for Secure Channel and
         Secure Association";
      list scsa-rx {
        key "sci-rx";
        description
          "RX Secure Channel and Secure Association Statistics";
        leaf sci-rx {
          type leafref {
            path "../state/sci-rx";
          }
          description
            "RX Secure Channel and Secure Association Statistics";
        }
        container state {
          description
            "State container for macsec-scsa-rx-interface-stats";
          uses macsec-scsa-rx-interface-state;
          container counters {
            description
              "Counters container for macsec-scsa-rx-interface-stats";
            uses macsec-scsa-rx-interface-stats;
          }
        }
      }
    }
  }

  grouping macsec-mka-interface-top {
    description
      "MKA interface top level grouping";
    container mka {
      description
        "Enclosing container for the MKA interface";
      container config {
        description
          "Configuration data for MKA interface";
        uses macsec-mka-interface-config;
      }
      container state {
        config false;
        description
          "Operational state data for MKA interface";
        uses macsec-mka-interface-config;
        uses macsec-mka-interface-state;
      }
    }
  }

  grouping macsec-interface-top {
    description
      "Top-level grouping ";
    container interfaces {
      description
        "Enclosing container for the MACsec interfaces list";
      list interface {
        key "name";
        description
          "List of interfaces on which MACsec is enabled / available";
        leaf name {
          srl_nokia-ext:show-importance "high";
          description
            "Reference to a specific subinterface of the form <interface-name>.<subinterface-index>";
          type leafref {
            path "/srl_nokia-if:interface/srl_nokia-if:subinterface/srl_nokia-if:index";
          }
        }
        container config {
          description
            "Configuration data for MACsec on each interface";
          uses macsec-interface-config;
        }
        container state {
          config false;
          description
            "Operational state data ";
          uses macsec-interface-config;
          container counters {
            description
              "MACsec interface counters";
            uses macsec-interface-counters;
          }
        }
        uses macsec-scsa-interface-top;
        uses macsec-mka-interface-top;
      }
    }
  }

  grouping macsec-mka-top {
    description
      "MKA top level grouping";
    container mka {
      description
        "The MKA";
      uses macsec-mka-policy-top;
      uses macsec-mka-global-top;
    }
  }

  grouping macsec-top {
    description
      "MACsec top level grouping";
    container macsec {
      if-feature "srl_nokia-feat:macsec";
      description
        "The MACsec";
      uses macsec-mka-top;
      uses macsec-interface-top;
    }
  }

  uses macsec-top;
}
