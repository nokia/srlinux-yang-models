module srl_nokia-tools-stp {
  yang-version 1.1;
  namespace "urn:nokia.com:srlinux:stp:tools-stp";
  prefix srl_nokia-tools-stp;

  import srl_nokia-features {
    prefix srl_nokia-feat;
  }
  import srl_nokia-tools-network-instance {
    prefix srl_nokia-tools-netinst;
  }
  import srl_nokia-tools-interfaces {
    prefix srl_nokia_tools-if;
  }

  organization
    "Nokia";
  contact
    "Nokia SR Linux Support
     Web: <http://www.nokia.com>";
  description
    "Model for STP operational commands";

  revision 2026-07-31 {
    description
      "SRLinux 26.7.1";
  }
  revision 2025-07-31 {
    description
      "SRLinux 25.7.1";
  }
  revision 2025-03-31 {
    description
      "SRLinux 25.3.1";
  }

  grouping stp-tools-top {
    container stp {
      presence "Send operational commands to STP manager";
      container statistics {
        leaf clear {
          type empty;
          description
            "Clear all Stp statistics";
        }
        description
          "Enter the statistics context";
      }
      container bpdu-guard-error {
        leaf clear {
          type empty;
          description
            "Clear Bpdu Guard Error";
        }
        description
          "Enter the bpdu-guard-error context";
      }
    }
  }

  augment "/srl_nokia-tools-netinst:network-instance/srl_nokia-tools-netinst:protocols" {
    uses stp-tools-top {
      if-feature "srl_nokia-feat:stp";
    }
  }

  augment "/srl_nokia_tools-if:interface/srl_nokia_tools-if:subinterface/srl_nokia_tools-if:bridge-table" {
    uses stp-tools-top {
      if-feature "srl_nokia-feat:stp";
    }
  }
}
