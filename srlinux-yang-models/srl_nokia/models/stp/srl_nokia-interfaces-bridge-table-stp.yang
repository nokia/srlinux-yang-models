module srl_nokia-interfaces-bridge-table-stp {
  yang-version 1.1;
  namespace "urn:nokia.com:srlinux:stp:interfaces-bridge-table-stp";
  prefix srl_nokia-interfaces-bridge-table-stp;

  import srl_nokia-common {
    prefix srl_nokia-comm;
  }
  import srl_nokia-interfaces {
    prefix srl_nokia-if;
  }
  import srl_nokia-stp-types {
    prefix srl_nokia-stp-types;
  }
  import srl_nokia-stp-common {
    prefix srl_nokia-stp-common;
  }
  import srl_nokia-features {
    prefix srl_nokia-feat;
  }
  import srl_nokia-network-instance {
    prefix srl_nokia-netinst;
  }
  import srl_nokia-interfaces-l2cp {
    prefix srl_nokia-if-l2cp;
  }
  import srl_nokia-interfaces-vlans {
    prefix srl_nokia-if-vlan;
  }

  organization
    "Nokia";
  contact
    "Nokia SR Linux Support
     Web: <http://www.nokia.com>";
  description
    "This yang file provides Stp configuration under interface's bridge table.";

  revision 2026-07-31 {
    description
      "SRLinux 26.7.1";
  }
  revision 2025-10-31 {
    description
      "SRLinux 25.10.1";
  }
  revision 2025-07-31 {
    description
      "SRLinux 25.7.1";
  }
  revision 2025-03-31 {
    description
      "SRLinux 25.3.1";
  }

  grouping interface-stp-counters {
    container statistics {
      config false;
      description
        "Enter the statistics context

         Packet transmition statistics";
      leaf bad-bpdus-received {
        type srl_nokia-comm:zero-based-counter64;
        description
          "The number of Invalid BPDUs received";
      }
      leaf cfg-bpdus-received {
        type srl_nokia-comm:zero-based-counter64;
        description
          "The number of configuration BPDUs received on this interface";
      }
      leaf cfg-bpdus-transmitted {
        type srl_nokia-comm:zero-based-counter64;
        description
          "The number of configuration BPDUs sent on this interface";
      }
      leaf tcn-bpdus-received {
        type srl_nokia-comm:zero-based-counter64;
        description
          "The number of topology change notification BPDUs received on this interface";
      }
      leaf tcn-bpdus-transmitted {
        type srl_nokia-comm:zero-based-counter64;
        description
          "The number of topology change notification BPDUs sent on this interface";
      }
      leaf tc-bit-bpdus-received {
        type srl_nokia-comm:zero-based-counter64;
        description
          "The number of BPDUs received on this interface with the Topology Change bit set";
      }
      leaf tc-bit-bpdus-transmitted {
        type srl_nokia-comm:zero-based-counter64;
        description
          "The number of BPDUs sent on this interface with the Topology Change bit set";
      }
      leaf rst-bpdus-received {
        type srl_nokia-comm:zero-based-counter64;
        description
          "The number of RST BPDUs received on this interface";
      }
      leaf rst-bpdus-transmitted {
        type srl_nokia-comm:zero-based-counter64;
        description
          "The number of RST BPDUs sent on this interface";
      }
      leaf mst-bpdus-received {
        type srl_nokia-comm:zero-based-counter64;
        description
          "The number of MST BPDUs received on this interface";
      }
      leaf mst-bpdus-transmitted {
        type srl_nokia-comm:zero-based-counter64;
        description
          "The number of MST BPDUs sent on this interface";
      }
    }
  }

  grouping managed-interface-stp-state {
    uses srl_nokia-stp-common:stp-port-state;
    uses srl_nokia-stp-common:oper-mgmt-stp-name;
    uses srl_nokia-stp-common:oper-mgmt-stp-interface;
    uses srl_nokia-stp-common:oper-mgmt-stp-msti;
    uses srl_nokia-stp-common:stp-forward-transitions;
  }

  grouping interface-stp-state {
    uses srl_nokia-stp-common:stp-port-state;
    uses srl_nokia-stp-common:stp-port-num;
    uses srl_nokia-stp-common:stp-port-priority;
    uses srl_nokia-stp-common:stp-port-role;
    uses srl_nokia-stp-common:stp-oper-state;
    uses srl_nokia-stp-common:stp-designated-bridge;
    uses srl_nokia-stp-common:stp-designated-port;
    uses srl_nokia-stp-common:stp-designated-port-priority;
    uses srl_nokia-stp-common:stp-designated-port-num;
    uses srl_nokia-stp-common:stp-oper-protocol;
    uses srl_nokia-stp-common:stp-oper-bpdu-encap;
    uses srl_nokia-stp-common:stp-oper-edge;
    uses srl_nokia-stp-common:stp-forward-transitions;
  }

  grouping interface-stp-bpdu-guard-state {
    uses srl_nokia-stp-common:stp-bpdu-guard-error;
    uses srl_nokia-stp-common:stp-bpdu-guard-recovery-time-expires;
  }

  grouping interface-stp-config {
    description
      "Interface common STP configuration";
    leaf port-number {
      type srl_nokia-stp-types:port-num-type;
      description
        "Port Number associated with this interface";
    }
    leaf priority {
      type srl_nokia-stp-types:port-priority-type;
      default "128";
      description
        "Priority value coupled with port number forms 16-bit port-identifier field";
    }
    leaf path-cost {
      type srl_nokia-stp-types:path-cost-type;
      default "10";
      description
        "The interface path-cost is used by STP to calculate the path cost to the root bridge";
    }
    uses srl_nokia-stp-types:stp-edge-port;
    leaf link-type {
      type srl_nokia-stp-types:link-type-type;
      default "P2P";
      description
        "Indicates the number of bridges behind the subinterface";
    }
    leaf guard {
      type srl_nokia-stp-types:guard-type;
      default "NONE";
      description
        "Enable Guard";
    }
    uses srl_nokia-stp-common:stp-bpdu-config;
  }

  grouping interface-bridge-table-stp-top {
    description
      "Top level grouping for STP configuration under interface's bridge table";
    container stp {
      description
        "Configuration and state of the STP protocol";
      presence "Configure Interface STP";
      must 'not(/srl_nokia-if:interface[srl_nokia-if:name=current()/../../../srl_nokia-if:name]/srl_nokia-if:ethernet/srl_nokia-if:l2cp-transparency/srl_nokia-if-l2cp:tunnel-all-l2cp)' {
        error-message "STP and tunnel-all-l2cp cannot be enabled on the same interface";
      }
      must 'not(/srl_nokia-if:interface[srl_nokia-if:name=current()/../../../srl_nokia-if:name]/srl_nokia-if:ethernet/srl_nokia-if:l2cp-transparency/srl_nokia-if-l2cp:xstp/srl_nokia-if-l2cp:tunnel)' {
        error-message "STP and xSTP tunnel cannot be enabled on the same interface";
      }
      must 'not(../../srl_nokia-if-vlan:vlan/srl_nokia-if-vlan:encap/srl_nokia-if-vlan:single-tagged-range)' {
        error-message "STP cannot be enabled on sub-interface with encap vlan-range enabled";
      }
      must "not (starts-with(/srl_nokia-if:interface[srl_nokia-if:name=current()/../../../srl_nokia-if:name]/srl_nokia-if:name,'irb'))" {
        error-message "STP cannot be enabled on IRB sub-interface";
      }
      leaf admin-state {
        type srl_nokia-comm:admin-state;
        default "disable";
        description
          "Administratively enable or disable the STP protocol for interface

           When STP on the network instance is administratively disabled,
           any BPDUs are forwarded transparently.
           When STP on the network instance is administratively enabled,
           but the administrative state on a sub-interface is disabled,
           BPDUs received on such a subinterface are discarded.";
      }
      uses interface-stp-config;
      uses interface-stp-state;
      uses interface-stp-bpdu-guard-state;
      uses interface-stp-counters;
    }
  }

  grouping interface-bridge-table-managed-stp-top {
    description
      "Top level grouping for state info of mgmt-stp managed interface";
    container managed-stp {
      uses managed-interface-stp-state;
      description
        "Enter the managed-stp context";
    }
  }

  augment "/srl_nokia-if:interface/srl_nokia-if:subinterface/srl_nokia-if:bridge-table" {
    uses interface-bridge-table-stp-top {
      if-feature "srl_nokia-feat:stp";
    }
    uses interface-bridge-table-managed-stp-top {
      if-feature "srl_nokia-feat:stp";
    }
  }
}
