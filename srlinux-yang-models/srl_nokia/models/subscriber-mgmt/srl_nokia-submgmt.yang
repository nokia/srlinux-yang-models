module srl_nokia-submgmt {
  yang-version 1.1;
  namespace "urn:nokia.com:srlinux:submgmt:submgmt";
  prefix srl_nokia-submgmt;

  import srl_nokia-common {
    prefix srl_nokia-comm;
  }
  import srl_nokia-features {
    prefix srl-feat;
  }
  import srl_nokia-extensions {
    prefix srl_nokia-ext;
  }
  import srl_nokia-qos {
    prefix srl_nokia-qos;
  }
  import srl_nokia-acl {
    prefix srl_nokia-acl;
  }
  import srl_nokia-interfaces {
    prefix srl_nokia-if;
  }
  import srl_nokia-network-instance {
    prefix srl_nokia-ni;
  }

  organization
    "Nokia";
  contact
    "Nokia SR Linux Support
     Web: <http://www.nokia.com>";
  description
    "This module defines configuration and operational state data
     related to subscriber management.";

  revision 2026-07-31 {
    description
      "SRLinux 26.7.1";
  }
  revision 2025-03-31 {
    description
      "SRLinux 25.3.1";
  }

  grouping subscriber-management-hosts {
    description
      "Subscriber hosts from state";
    container hosts {
      config false;
      list host {
        key "ip-address mac-address net-inst-name";
        description
          "Host";
        leaf ip-address {
          type srl_nokia-comm:ip-address;
          description
            "IPv4 or IPv6 address of the subscriber host";
        }
        leaf mac-address {
          type srl_nokia-comm:mac-address;
          description
            "Mac address of the subscriber host";
        }
        leaf net-inst-name {
          type string;
          description
            "Network instance name of the subscriber host";
        }
        leaf ip-address-prefix-length {
          type uint32;
          description
            "IPv4 or IPv6 address prefix length of the subscriber host";
        }
        leaf global-if-id {
          type uint32;
          description
            "Global interface identifier of the subscriber host";
        }
        leaf net-inst-id {
          type uint32;
          description
            "Network instance identifier of the subscriber host";
        }
      }
      description
        "Enter the hosts context";
    }
  }

  grouping subscriber-management-top {
    description
      "Grouping of reusable elements";
    container subscriber-management {
      if-feature "srl-feat:submgmt-fpcx";
      presence "Configure subscriber-management";
      description
        "Top level container for subscriber-management data";
      container profiles {
        description
          "Enter the profiles context

           Subscriber management profiles";
      }
      container ref-points {
        description
          "Enter the ref-points context

           Properties of reference points for communication with external systems";
      }
      container services {
        description
          "Enter the services context

           Services";
      }
      uses subscriber-management-policies;
      container interfaces {
        description
          "Enter the interfaces context

           List of interfaces used by subscriber-management";
        uses subscriber-interfaces;
        uses capture-subinterface-top;
      }
      uses subscriber-management-hosts;
    }
  }

  grouping subscriber-management-policies {
    description
      "Grouping of reusable elements";
    uses sla-profile;
    uses subscriber-profile;
  }

  grouping subscriber-profile {
    description
      "Grouping of reusable elements";
    list subscriber-profile {
      key "name";
      description
        "List of subscriber-profiles";
      leaf name {
        type srl_nokia-comm:name;
        description
          "Name for the subscriber-profile";
      }
      container output {
        description
          "Enter the output context

           Parameters related to output of subscriber-profile";
        container qos {
          if-feature "srl-feat:qos";
          description
            "Enter the qos context

             QoS parameters for susbcriber-profile";
          leaf queue-scheduling-policy {
            if-feature "srl-feat:qos-queue-scheduling-policy";
            type leafref {
              path "/srl_nokia-qos:qos/srl_nokia-qos:scheduler-policies/srl_nokia-qos:queue-scheduling-policy/srl_nokia-qos:name";
            }
            description
              "Reference to the name of queue-scheduling-policy

               Such policy can contain only tier-1 scheduler definitions";
          }
        }
      }
    }
  }

  grouping classifiers {
    description
      "Grouping of reusable elements";
    container classifiers {
      description
        "Enter the classifiers context

         Input classifier policies";
      container default {
        description
          "Enter the default context

           The conatiner defining default qos parameters for packets which do not match any of the classification rules";
        leaf forwarding-class {
          type leafref {
            path "/srl_nokia-qos:qos/srl_nokia-qos:forwarding-classes/srl_nokia-qos:forwarding-class/srl_nokia-qos:name";
          }
          description
            "The default forwarding class for packets which do no match any classification rules";
        }
        leaf profile {
          type srl_nokia-comm:classify-profile;
          default "out";
          description
            "The default profile for packets that do not match any classification rules";
        }
      }
      leaf dot1p-policy {
        if-feature "srl-feat:qos-dot1p-classifier-policy";
        type leafref {
          path "/srl_nokia-qos:qos/srl_nokia-qos:classifiers/srl_nokia-qos:dot1p-policy/srl_nokia-qos:name";
        }
        description
          "Reference to the name of a dot1p classification policy";
      }
      leaf dscp-policy {
        type leafref {
          path "/srl_nokia-qos:qos/srl_nokia-qos:classifiers/srl_nokia-qos:dscp-policy/srl_nokia-qos:name";
        }
        description
          "Reference to the name of a DSCP mapping policy that applies to both IPv4 and IPv6 traffic";
      }
    }
  }

  grouping policer-policies {
    description
      "Grouping of reusable elements";
    container policer-policies {
      description
        "Enter the policer-policies context

         Policer policies";
      leaf policer-policy {
        if-feature "srl-feat:qos-policer-policies";
        type leafref {
          path "/srl_nokia-qos:qos/srl_nokia-qos:policer-policies/srl_nokia-qos:policer-policy/srl_nokia-qos:name";
        }
        description
          "Reference to the name of a policer-policy";
      }
      container overrides {
        description
          "Enter the overrides context

           Parameters overriding the policer-policy policer settings";
        list policer {
          key "policer-id";
          max-elements 32;
          description
            "The list of policer belonging to the policer-policy";
          leaf policer-id {
            type uint8 {
              range "0..31";
            }
            description
              "A number to identify given policer within policer-policy";
          }
          leaf peak-rate-kbps {
            type uint32 {
              range "64..800000000";
            }
            units "kbps";
            description
              "The peak information rate (PIR) of the policer, defined in kilobits (1024 bits) per second.

               This parameter is ignored if 'algorithm-type' is set to 'trtcm2'";
          }
          leaf committed-rate-kbps {
            type uint32 {
              range "0|64..800000000";
            }
            units "kbps";
            description
              "The committed information rate (CIR) of the policer, defined in kilobits (1024 bits) per second";
          }
          leaf excess-rate-kbps {
            type uint32 {
              range "64..800000000";
            }
            units "kbps";
            description
              "The excess information rate (EIR) of the policer, defined in kilobits (1024 bits) per second.

               This parameter is ignored if 'algorithm-type' is set to 'trtcm1'";
          }
          leaf maximum-burst-size {
            type uint32 {
              range "64..253952";
            }
            units "bytes";
            description
              "Maximum PIR bucket depth in bytes.

               This parameter is ignored if 'algorithm-type' is set to 'trtcm2'";
          }
          leaf committed-burst-size {
            type uint32 {
              range "64..190941";
            }
            units "bytes";
            description
              "Maximum CIR bucket depth in bytes";
          }
          leaf excess-burst-size {
            type uint32 {
              range "64..253952";
            }
            units "bytes";
            description
              "Maximum EIR bucket depth in bytes.

               This parameter is ignored if 'algorithm-type' is set to 'trtcm1'";
          }
        }
        leaf parent-policer-rate-kbps {
          type uint32 {
            range "64..800000000";
          }
          units "kbps";
          description
            "Defines peak-rate of the parent-policer";
        }
      }
    }
  }

  grouping acl {
    description
      "Grouping of reusable elements";
    container acl {
      description
        "Enter the acl context

         ACL filters";
      list acl-filter {
        key "name type";
        max-elements 4;
        ordered-by user;
        description
          "MAC, IPv4, IPv6 ACL filter(s) to be applied on this SLA profile";
        leaf name {
          type leafref {
            path "/srl_nokia-acl:acl/srl_nokia-acl:acl-filter/srl_nokia-acl:name";
          }
          description
            "name";
        }
        leaf type {
          type leafref {
            path "/srl_nokia-acl:acl/srl_nokia-acl:acl-filter[srl_nokia-acl:name=current()/../name]"
               + "/srl_nokia-acl:type";
          }
          description
            "type";
        }
      }
    }
  }

  grouping input-qos {
    description
      "Grouping of reusable elements";
    leaf input-class-map {
      if-feature "srl-feat:qos-input-class-map";
      type leafref {
        path "/srl_nokia-qos:qos/srl_nokia-qos:input-class-map/srl_nokia-qos:name";
      }
      description
        "Reference to the name of input-class-map that applies to sla-profile";
    }
    uses classifiers;
    uses policer-policies;
  }

  grouping rewrite-policies {
    description
      "Grouping of reusable elements";
    container rewrite-policies {
      description
        "Enter the rewrite-policies context

         Output rewrite policies";
      leaf dscp-policy {
        type leafref {
          path "/srl_nokia-qos:qos/srl_nokia-qos:rewrite-rules/srl_nokia-qos:dscp-policy/srl_nokia-qos:name";
        }
        description
          "Reference to the name of a DSCP rewrite-rule policy that applies to both IPv4 and IPv6 traffic";
      }
      leaf dot1p-policy {
        if-feature "srl-feat:qos-dot1p-rewrite-policy";
        type leafref {
          path "/srl_nokia-qos:qos/srl_nokia-qos:rewrite-rules/srl_nokia-qos:dot1p-policy/srl_nokia-qos:name";
        }
        description
          "Reference to the name of a dot1p rewrite policy";
      }
    }
  }

  grouping sla-scheduling {
    description
      "Grouping of reusable elements";
    container scheduling {
      description
        "Enter the scheduling context

         Scheduling";
      leaf queue-scheduling-policy {
        if-feature "srl-feat:qos-queue-scheduling-policy";
        type leafref {
          path "/srl_nokia-qos:qos/srl_nokia-qos:scheduler-policies/srl_nokia-qos:queue-scheduling-policy/srl_nokia-qos:name";
        }
        description
          "Reference to the name of queue-scheduling-policy

           Such policy can contain only queue and tier-0 schedulers definitions";
      }
      container overrides {
        description
          "Enter the overrides context

           Overrides";
        list queue {
          key "queue-name";
          description
            "List of queues";
          leaf queue-name {
            type leafref {
              path "/srl_nokia-qos:qos/srl_nokia-qos:queues/srl_nokia-qos:queue/srl_nokia-qos:name";
            }
            description
              "The queue name";
          }
          leaf scheduling-class {
            type uint8 {
              range "0|2|4|6";
            }
            default "0";
            description
              "Scheduling-class of the queue";
          }
          leaf weight {
            type uint8 {
              range "1..127";
            }
            default "1";
            description
              "The scheduling weight of the given queue";
          }
          container packet-length-adjustment {
            description
              "Enter the packet-length-adjustment context

               The definition on how packet-length should be adjusted for the scheduling-algorithm calculation";
            leaf add {
              type uint32 {
                range "0..32";
              }
              units "bytes";
              default "0";
              description
                "Number of bytes to be added to the packet-length for the scheduling-algorithm calculation";
            }
          }
          leaf tier-0-scheduler-rate {
            type uint64;
            description
              "Tier-0 queue-scheduler peak-rate in kilobits-per-second";
          }
        }
      }
    }
  }

  grouping output-qos {
    description
      "Grouping of reusable elements";
    leaf output-class-map {
      if-feature "srl-feat:qos-output-class-map";
      type leafref {
        path "/srl_nokia-qos:qos/srl_nokia-qos:output-class-map/srl_nokia-qos:name";
      }
      description
        "Reference to the name of output-class-map";
    }
    leaf buffer-allocation-profile {
      type leafref {
        path "/srl_nokia-qos:qos/srl_nokia-qos:buffer-management/srl_nokia-qos:buffer-allocation-profile/srl_nokia-qos:name";
      }
      description
        "reference to the name of buffer-allocation-profile";
    }
    uses rewrite-policies;
    uses sla-scheduling;
  }

  grouping sla-profile {
    description
      "Sla-profile QoS realted configuration data";
    list sla-profile {
      key "name";
      description
        "SLA profile";
      leaf name {
        type srl_nokia-comm:name;
        description
          "User-configured name for a dot1p-policy";
      }
      container input {
        description
          "Enter the input context

           Container with references to input configuration for sla-profile";
        uses acl;
        uses input-qos {
          if-feature "srl-feat:qos";
        }
      }
      container output {
        description
          "Enter the output context

           Container with references to output configuration for sla-profile";
        uses acl;
        uses output-qos {
          if-feature "srl-feat:qos";
        }
      }
    }
  }

  grouping subscriber-interfaces {
    description
      "Grouping of reusable elements";
    list subscriber-interface {
      key "name";
      description
        "Creates subscriber-interface.

         This is a new type of the interface which is not tied to a physical resource. Instead, it provides object for creating subnets and grouping of physical subinterfaces sharing these subnets.
         All subinterfaces associated under this subscriber interface must be of the same same type 'routed vs.bridged'.
         In case of routed-type, none of subinterfaces should have IPv4/Ipv6 subnet associated";
      leaf name {
        type srl_nokia-comm:name;
        description
          "User-configured name for subscriber-interface";
      }
      leaf network-instance {
        type leafref {
          path "/srl_nokia-ni:network-instance/srl_nokia-ni:name";
        }
        description
          "Defines network-instance this subscriber-interface is using";
      }
      container subnets {
        description
          "Enter the subnets context

           List of IPv4 and IPv6 subnets";
        list ipv4-subnet {
          key "ipv4-prefix";
          description
            "List of IPv4 prefixes";
          leaf ipv4-prefix {
            type srl_nokia-comm:ipv4-prefix;
            description
              "IPv4 prefix";
          }
        }
        list ipv6-subnet {
          key "ipv6-prefix";
          description
            "List of IPv6 prefixes";
          leaf ipv6-prefix {
            type srl_nokia-comm:ipv6-prefix;
            description
              "IPv6 prefix";
          }
        }
      }
      list group-interface {
        key "name";
        description
          "Creates a group-interface within subscriber-management-interface.

           Not sure this is needed. For the moment it is just a place-holder";
        leaf name {
          type srl_nokia-comm:name;
          description
            "User-configured name for group-interface";
        }
        list interface {
          key "interface-id";
          max-elements 16383;
          description
            "List of subinterfaces referenced by subscriber-management-interface";
          leaf interface-id {
            type string;
            must 'not (starts-with(., "_"))' {
              error-message "reserved interface-id cannot be configured";
            }
            must "not (/srl_nokia-if:interface[srl_nokia-if:name=current()]/srl_nokia-if:ethernet/srl_nokia-if:aggregate-id) or
                              ../interface-ref/interface" {
              error-message "subscriber-management configuration is not supported on LAG member ports";
            }
            description
              "Identifier for the interface or subinterface";
          }
          container interface-ref {
            description
              "Enter the interface-ref context

               Reference to an interface and a subinterface";
            leaf interface {
              type leafref {
                path "/srl_nokia-if:interface/srl_nokia-if:name";
              }
              must "not (string(../subinterface) != '' and starts-with(current(), 'irb'))" {
                error-message "qos configuration is not supported on IRB sub interface";
                srl_nokia-ext:if-feature "not (srl_nokia-features:qos-irb-subinterface)";
              }
              must "starts-with(current(), 'ethernet') or starts-with(current(), 'lag') or string(../subinterface) != ''" {
                error-message "qos  configuration is not supported on this interface type";
              }
              must 'not (/srl_nokia-if:interface[srl_nokia-if:name=current()]/srl_nokia-if:ethernet/srl_nokia-if:aggregate-id)' {
                error-message "qos configuration is not supported on LAG member ports";
              }
              must 'not (/srl_nokia-if:interface[srl_nokia-if:name=current()]/srl_nokia-if:breakout-mode)' {
                error-message "Interfaces with breakout-mode configured are not supported";
              }
              description
                "Reference to a base interface, for example a port or LAG";
            }
            leaf subinterface {
              type leafref {
                path "/srl_nokia-if:interface[srl_nokia-if:name=current()/../interface]/srl_nokia-if:subinterface/srl_nokia-if:index";
              }
              must '../interface' {
                error-message "interface must be configured when subinterface is set";
              }
              description
                "Reference to a subinterface

                 This requires the base interface to be specified using the interface leaf in this container";
            }
          }
          container defaults {
            description
              "Enter the defaults context

               Default subscriber-management object associated with the given subinterface";
            leaf sla-profile {
              type leafref {
                path "/subscriber-management/sla-profile/name";
              }
              description
                "Default SLA-profile for all subscriber-hosts created on the given subinterface";
            }
            leaf subscriber-profile {
              type leafref {
                path "/subscriber-management/subscriber-profile/name";
              }
              description
                "Subscriber-profile assigned to the subscriber-host";
            }
          }
          list ipv4-static-host {
            key "ipv4-address mac-address";
            description
              "List of IPv4 static-hosts on the subinterface";
            leaf ipv4-address {
              type srl_nokia-comm:ipv4-address;
              description
                "IPv4 address for a static host";
            }
            leaf mac-address {
              type srl_nokia-comm:mac-address;
              description
                "MAC address for a static host";
            }
            leaf sla-profile {
              type leafref {
                path "/subscriber-management/sla-profile/name";
              }
              description
                "SLA-profile assigned to the subscriber-host";
            }
            leaf subscriber-profile {
              type leafref {
                path "/subscriber-management/subscriber-profile/name";
              }
              description
                "Subscriber-profile assigned to the subscriber-host";
            }
          }
          list ipv6-static-host {
            key "ipv6-address mac-address";
            description
              "List of IPv6 static-hosts on the subinterface";
            leaf ipv6-address {
              type srl_nokia-comm:ipv6-address;
              description
                "IPv6 address for a static host";
            }
            leaf mac-address {
              type srl_nokia-comm:mac-address;
              description
                "MAC address for a static host";
            }
            leaf sla-profile {
              type leafref {
                path "/subscriber-management/sla-profile/name";
              }
              description
                "SLA-profile assigned to the subscriber-host";
            }
            leaf subscriber-profile {
              type leafref {
                path "/subscriber-management/subscriber-profile/name";
              }
              description
                "Subscriber-profile assigned to the subscriber-host";
            }
          }
        }
      }
    }
  }

  grouping capture-subinterface-top {
    description
      "Grouping of reusable elements";
    list capture-subinterface {
      key "name";
      description
        "Capture subinterface";
      leaf name {
        type srl_nokia-comm:name;
        description
          "User-configured name for capture-subinterface";
      }
      leaf network-instance {
        type leafref {
          path "/srl_nokia-ni:network-instance/srl_nokia-ni:name";
        }
        description
          "Defines network-instance this subscriber-interface is using";
      }
      container interface-ref {
        description
          "Enter the interface-ref context

           Reference to an interface and a subinterface";
        leaf interface {
          type leafref {
            path "/srl_nokia-if:interface/srl_nokia-if:name";
          }
          must "not (string(../subinterface) != '' and starts-with(current(), 'irb'))" {
            error-message "qos configuration is not supported on IRB sub interface";
            srl_nokia-ext:if-feature "not (srl_nokia-features:qos-irb-subinterface)";
          }
          must "starts-with(current(), 'ethernet') or starts-with(current(), 'lag') or string(../subinterface) != ''" {
            error-message "qos  configuration is not supported on this interface type";
          }
          must 'not (/srl_nokia-if:interface[srl_nokia-if:name=current()]/srl_nokia-if:ethernet/srl_nokia-if:aggregate-id)' {
            error-message "qos configuration is not supported on LAG member ports";
          }
          must 'not (/srl_nokia-if:interface[srl_nokia-if:name=current()]/srl_nokia-if:breakout-mode)' {
            error-message "Interfaces with breakout-mode configured are not supported";
          }
          description
            "Reference to a base interface, for example a port or LAG";
        }
        leaf subinterface {
          type leafref {
            path "/srl_nokia-if:interface[srl_nokia-if:name=current()/../interface]/srl_nokia-if:subinterface/srl_nokia-if:index";
          }
          must '../interface' {
            error-message "interface must be configured when subinterface is set";
          }
          description
            "Reference to a subinterface

             This requires the base interface to be specified using the interface leaf in this container";
        }
      }
      container defaults {
        description
          "Enter the defaults context

           Default subscriber-management objects associated with capture-subinterface";
        leaf sla-profile {
          type leafref {
            path "/subscriber-management/sla-profile/name";
          }
          description
            "Default SLA-profile for all subscriber-hosts created based on the capture-subinterface";
        }
        leaf subscriber-profile {
          type leafref {
            path "/subscriber-management/subscriber-profile/name";
          }
          description
            "Subscriber-profile assigned to the subscriber-hosts created based on this capture-subinterface";
        }
      }
    }
  }

  uses subscriber-management-top;
}
