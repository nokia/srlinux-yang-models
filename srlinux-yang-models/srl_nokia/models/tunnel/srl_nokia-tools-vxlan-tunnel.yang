module srl_nokia-tools-vxlan-tunnel {
  yang-version 1.1;
  namespace "urn:nokia.com:srlinux:vxlan:tools-vxlan-tunnel";
  prefix srl_nokia-tools-vxlan-tunnel;

  import srl_nokia-common {
    prefix srl_nokia-comm;
  }
  import srl_nokia-tools-tunnel {
    prefix srl_nokia-tools-tunnel;
  }
  import srl_nokia-features {
    prefix srl-feat;
  }

  organization
    "Nokia";
  contact
    "Nokia SR Linux Support
     Web: <http://www.nokia.com>";
  description
    "Model for operational commands on vxlan tunnels.";

  revision 2026-07-31 {
    description
      "SRLinux 26.7.1";
  }
  revision 2025-07-31 {
    description
      "SRLinux 25.7.1";
  }
  revision 2021-03-31 {
    description
      "SRLinux 21.3.1";
  }

  grouping tools-vxlan-tunnel-vtep-top {
    description
      "Top-level grouping for vxlan-tunnel vtep tools.";
    list vtep {
      key "address";
      description
        "IP address that identifies the remote VXLAN Termination Endpoint (VTEP)";
      leaf address {
        type srl_nokia-comm:ip-address;
        description
          "IP address that identifies the remote VXLAN Termination Endpoint (VTEP)";
      }
      container statistics {
        leaf clear {
          type empty;
        }
        description
          "Enter the statistics context";
      }
    }
  }

  grouping tools-vxlan-tunnel-top {
    description
      "Top-level grouping for vxlan-tunnel tools.";
    container vxlan-tunnel {
      if-feature "srl-feat:vxlan";
      container statistics {
        leaf clear {
          type empty;
        }
        description
          "Enter the statistics context";
      }
      uses tools-vxlan-tunnel-vtep-top;
      description
        "Enter the vxlan-tunnel context";
    }
  }

  augment "/srl_nokia-tools-tunnel:tunnel" {
    uses tools-vxlan-tunnel-top;
  }
}
