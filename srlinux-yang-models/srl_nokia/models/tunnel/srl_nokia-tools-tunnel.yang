module srl_nokia-tools-tunnel {
  yang-version 1.1;
  namespace "urn:nokia.com:srlinux:vxlan:tools-tunnel";
  prefix srl_nokia-tools-tunnel;

  import srl_nokia-common {
    prefix srl_nokia-comm;
  }
  import srl_nokia-features {
    prefix srl-feat;
  }
  import srl_nokia-extensions {
    prefix srl_nokia-ext;
  }

  organization
    "Nokia";
  contact
    "Nokia SR Linux Support
     Web: <http://www.nokia.com>";

  revision 2026-07-31 {
    description
      "SRLinux 26.7.1";
  }
  revision 2024-07-31 {
    description
      "SRLinux 24.7.1";
  }
  revision 2021-03-31 {
    description
      "SRLinux 21.3.1";
  }

  grouping tools-tunnel-top {
    container tunnel {
      description
        "Enter the tunnel context

         Top-level container for the tunnel table.";
      if-feature "srl-feat:vxlan or srl-feat:pseudowire";
      srl_nokia-ext:first-released "20.10.1";
    }
  }

  uses tools-tunnel-top;
}
