module srl_nokia-tunnel-interfaces {
  yang-version 1.1;
  namespace "urn:nokia.com:srlinux:vxlan:tunnel-interfaces";
  prefix srl_nokia-tunnel-if;

  import srl_nokia-common {
    prefix srl_nokia-comm;
  }
  import srl_nokia-features {
    prefix srl-feat;
  }
  import srl_nokia-extensions {
    prefix srl_nokia-ext;
  }
  import srl_nokia-interfaces {
    prefix srl_nokia-if;
  }
  import srl_nokia-network-instance {
    prefix srl_nokia-netinst;
  }
  import srl_nokia-tunnel {
    prefix srl_nokia-tunnel;
  }

  organization
    "Nokia";
  contact
    "Nokia SR Linux Support
     Web: <http://www.nokia.com>";
  description
    "Model for tunnel-interfaces in SRLinux.";

  revision 2026-07-31 {
    description
      "SRLinux 26.7.1";
  }
  revision 2025-10-31 {
    description
      "SRLinux 25.10.1";
  }
  revision 2025-07-31 {
    description
      "SRLinux 25.7.1";
  }
  revision 2023-10-31 {
    description
      "SRLinux 23.10.1";
  }
  revision 2022-11-30 {
    description
      "SRLinux 22.11.1";
  }
  revision 2021-06-30 {
    description
      "SRLinux 21.6.1";
  }
  revision 2021-03-31 {
    description
      "SRLinux 21.3.1";
  }

  typedef tunnel-interface-all {
    type string {
      length "6..8";
      pattern '(vxlan(0|1[0-9][0-9]|2([0-4][0-9]|5[0-5])|[1-9][0-9]|[1-9]))';
    }
    description
      "The type of the tunnel-interface.";
  }

  typedef vlan-id {
    type uint16 {
      range "1..4094";
    }
    description
      "Type definition representing a single-tagged VLAN ID";
  }

  grouping tunnel-interface-top {
    description
      "Top-level configuration and state for tunnel interfaces.";
    list tunnel-interface {
      if-feature "srl-feat:vxlan";
      key "name";
      srl_nokia-ext:first-released "21.3.1";
      description
        "In the case that the interface is logical tunnel
         interface, the parameters for the tunnel are
         specified within this subtree. Tunnel interfaces
         have only a single logical subinterface associated
         with them.";
      leaf name {
        type tunnel-interface-all;
        description
          "The name of the tunnel-interface.

           Valid options are:
           vxlan<N>, N=0..255";
      }
      uses vxlan-interface-top;
    }
  }

  grouping vxlan-interface-top {
    description
      "Vxlan-interface grouping.";
    list vxlan-interface {
      max-elements 16384;
      key "index";
      srl_nokia-ext:first-released "21.3.1";
      description
        "The list of vxlan-interfaces.";
      leaf index {
        type uint32 {
          range "0..99999999";
        }
        description
          "The index of the vxlan-tunnel.";
      }
      leaf type {
        mandatory true;
        type identityref {
          base srl_nokia-if:si-type;
        }
        description
          "The value of this leaf indicates the context in which the
           vxlan-interface will be used in.";
        must ".='srl_nokia-if:bridged' or .='srl_nokia-if:routed'" {
          error-message "unsupported type.";
        }
        must "not(.='srl_nokia-if:bridged')" {
          error-message "unsupported type.";
          srl_nokia-ext:if-feature "not srl_nokia-feat:evpn-vxlan-mac-vrf";
        }
        must "not(.='srl_nokia-if:routed')" {
          error-message "unsupported type.";
          srl_nokia-ext:if-feature "not srl_nokia-feat:evpn-vxlan-ifl";
        }
      }
      leaf oper-state {
        srl_nokia-ext:show-importance "high";
        config false;
        type enumeration {
          enum up;
          enum down;
        }
        description
          "The operational state of the vxlan-interface";
      }
      leaf oper-down-reason {
        srl_nokia-ext:show-importance "high";
        config false;
        type enumeration {
          enum mac-failed;
          enum ingress-hash-failed;
          enum egress-hash-failed;
          enum other;
        }
        description
          "The reason why the vxlan-interface is oper-down";
      }
      container ingress {
        leaf vni {
          type uint32 {
            range "1..16777215";
          }
          mandatory true;
          description
            "Ingress VXLAN Network Identifier of the VXLAN subinterface.

             The egress VNI is determined by the static egress-vni configured in the associated destination
             or by the dynamic egress-vni learned from the control plane.";
        }
        description
          "Enter the ingress context";
      }
      container egress {
        leaf source-ip {
          type union {
            type enumeration {
              enum use-system-ipv4-address {
                value 0;
              }
            }
          }
          default "use-system-ipv4-address";
          description
            "The ip-address that will be used as the source-ip for all vxlan traffic egressing this vxlan-interface.";
        }
        container inner-ethernet-header {
          description
            "Parameters of the inner VXLAN ethernet payload when the VXLAN tunnel is used in an ip-vrf.";
          presence "Configure the inner-ethernet-header";
          must "../../type != 'srl_nokia-if:bridged'" {
            error-message "Inner-ethernet-header not allowed with vxlan-interface type bridged.";
          }
          leaf source-mac {
            type union {
              type enumeration {
                enum use-system-mac {
                  value 0;
                }
              }
            }
            default "use-system-mac";
            description
              "VXLAN inner ethernet source mac-address. Present when the VXLAN tunnel is associated
               with a ip-vrf network-instance.";
          }
          leaf used-source-mac {
            config false;
            type srl_nokia-comm:mac-address;
            description
              "VXLAN inner ethernet source mac-address in use. Present when the VXLAN tunnel is associated
               with a ip-vrf network-instance.";
          }
        }
        description
          "Enter the egress context";
      }
      uses bridge-table-group-top;
    }
  }

  grouping bridge-table-group-top {
    container bridge-table {
      presence "Bridge table config and state on the vxlan-interface";
      must "../type = 'srl_nokia-if:bridged'" {
        error-message "bridge-table allowed only with vxlan-interface type bridged.";
      }
    }
  }

  uses tunnel-interface-top;
}
