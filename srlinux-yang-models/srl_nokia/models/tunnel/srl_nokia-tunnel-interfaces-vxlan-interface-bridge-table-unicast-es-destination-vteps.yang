module srl_nokia-tunnel-interfaces-vxlan-interface-bridge-table-unicast-es-destination-vteps {
  yang-version 1.1;

  // namespace

  namespace "urn:nokia.com:srlinux:vxlan:tunnel-interfaces-vxlan-interface-bridge-table-unicast-es-destination-vteps";
  prefix srl_nokia-tunnel-if-vxlan-if-bt-unicast-destinations-vteps;

  // import some basic types

  import srl_nokia-common {
    prefix srl_nokia-comm;
  }
  import srl_nokia-tunnel-interfaces {
    prefix srl_nokia-tunnel-if;
  }
  import srl_nokia-extensions {
    prefix srl_nokia-ext;
  }
  import srl_nokia-tunnel-interfaces-vxlan-interface-bridge-table-unicast-destinations {
    prefix srl_nokia-tunnel-if-vxlan-if-bt-unicast-destinations;
  }

  organization
    "Nokia";
  contact
    "Nokia SR Linux Support
     Web: <http://www.nokia.com>";
  description
    "Model for bridge-table unicast destinations on the vxlan-interface";

  revision 2020-10-31 {
    description
      "SRLinux 20.10.1";
  }

  grouping bridge-table-vxlan-interface-unicast-destinations-es-destination-vteps-top {
    list vtep {
      config false;
      key "address vni";
      leaf address {
        srl_nokia-ext:show-importance "high";
        type srl_nokia-comm:ip-address;
        description
          "The IP address that identifies the remote VXLAN Termination Endpoint (VTEP).";
      }
      leaf vni {
        type uint32 {
          range "1..16777215";
        }
        srl_nokia-ext:show-importance "high";
        description
          "VXLAN Network Identifier of the destination.";
      }
    }
  }

  augment "/srl_nokia-tunnel-if:tunnel-interface/srl_nokia-tunnel-if:vxlan-interface/srl_nokia-tunnel-if:bridge-table/srl_nokia-tunnel-if-vxlan-if-bt-unicast-destinations:unicast-destinations/srl_nokia-tunnel-if-vxlan-if-bt-unicast-destinations:es-destination" {
    uses bridge-table-vxlan-interface-unicast-destinations-es-destination-vteps-top;
  }
}
