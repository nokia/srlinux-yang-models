module srl_nokia-tunnel-interfaces-vxlan-interface-bridge-table-multicast-destinations {
  yang-version 1.1;
  namespace "urn:nokia.com:srlinux:mcid:tunnel-interfaces-vxlan-interface-bridge-table-multicast-destinations";
  prefix srl_nokia-tunnel-if-vxlan-if-bt-multicast-destinations;

  import srl_nokia-common {
    prefix srl_nokia-comm;
  }
  import srl_nokia-tunnel-interfaces {
    prefix srl_nokia-tunnel-if;
  }
  import srl_nokia-extensions {
    prefix srl_nokia-ext;
  }

  organization
    "Nokia";
  contact
    "Nokia SR Linux Support
     Web: <http://www.nokia.com>";
  description
    "Model for bridge-table multicast destinations on the vxlan-interface";

  revision 2026-07-31 {
    description
      "SRLinux 26.7.1";
  }
  revision 2025-07-31 {
    description
      "SRLinux 25.7.1";
  }
  revision 2023-10-31 {
    description
      "SRLinux 23.10.1";
  }
  revision 2021-03-31 {
    description
      "SRLinux 21.3.1";
  }

  grouping bridge-table-vxlan-interface-multicast-destinations-destination-top {
    list destination {
      key "vtep vni";
      leaf vtep {
        srl_nokia-ext:show-importance "high";
        type srl_nokia-comm:ip-address;
        description
          "IP address identifying the remote VXLAN Termination Endpoint (VTEP)";
      }
      leaf vni {
        type uint32 {
          range "1..16777215";
        }
        srl_nokia-ext:show-importance "high";
        description
          "VXLAN Network Identifier (VNI) of the destination";
      }
      leaf multicast-forwarding {
        srl_nokia-ext:show-importance "high";
        type srl_nokia-comm:multicast-type;
        description
          "Type of multicast data forwarded by this VXLAN destination";
      }
      leaf destination-index {
        type uint64;
        srl_nokia-ext:show-importance "high";
        description
          "System-wide unique identifier of this VXLAN destination object (system allocated)";
      }
      leaf not-programmed-reason {
        srl_nokia-ext:show-importance "high";
        type enumeration {
          enum no-destination-index;
          enum multicast-limit;
        }
        description
          "The reason why the destination is not programmed in the floodlist";
      }
    }
  }

  grouping bridge-table-vxlan-interface-multicast-destinations-limits-top {
    container multicast-limit {
      description
        "Enter the multicast-limit context

         Multicast limits per vxlan interface.";
      leaf maximum-entries {
        type int32;
        description
          "Maximum number of multicast vxlan-destinations allowed on a vxlan-interface.";
      }
      leaf current-usage {
        type int32;
        description
          "Maximum number of multicast vxlan-destinations in use on this vxlan-interface.";
      }
    }
  }

  grouping bridge-table-vxlan-interface-multicast-destinations-top {
    container multicast-destinations {
      config false;
      uses bridge-table-vxlan-interface-multicast-destinations-limits-top;
      uses bridge-table-vxlan-interface-multicast-destinations-destination-top;
      description
        "Enter the multicast-destinations context";
    }
  }

  augment "/srl_nokia-tunnel-if:tunnel-interface/srl_nokia-tunnel-if:vxlan-interface/srl_nokia-tunnel-if:bridge-table" {
    uses bridge-table-vxlan-interface-multicast-destinations-top;
  }
}
