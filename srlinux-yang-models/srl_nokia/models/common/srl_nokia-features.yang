module srl_nokia-features {
  yang-version 1.1;
  namespace "urn:nokia.com:srlinux:general:features";
  prefix srl_nokia-feat;

  organization
    "Nokia";
  contact
    "Nokia SR Linux Support
     Web: <http://www.nokia.com>";
  description
    "YANG module detailing SRLinux features";

  revision 2026-07-31 {
    description
      "SRLinux 26.7.1";
  }
  revision 2026-03-31 {
    description
      "SRLinux 26.3.1";
  }
  revision 2025-10-31 {
    description
      "SRLinux 25.10.1";
  }
  revision 2025-07-31 {
    description
      "SRLinux 25.7.1";
  }
  revision 2025-03-31 {
    description
      "SRLinux 25.3.1";
  }
  revision 2024-10-31 {
    description
      "SRLinux 24.10.1";
  }
  revision 2024-07-31 {
    description
      "SRLinux 24.7.1";
  }
  revision 2024-03-31 {
    description
      "SRLinux 24.3.1";
  }
  revision 2023-10-31 {
    description
      "SRLinux 23.10.1";
  }
  revision 2023-07-31 {
    description
      "SRLinux 23.7.1";
  }
  revision 2023-03-31 {
    description
      "SRLinux 23.3.1";
  }
  revision 2022-11-30 {
    description
      "SRLinux 22.11.1";
  }
  revision 2022-06-30 {
    description
      "SRLinux 22.6.1";
  }
  revision 2022-03-31 {
    description
      "SRLinux 22.3.1";
  }
  revision 2021-11-30 {
    description
      "SRLinux 21.11.1";
  }
  revision 2021-06-30 {
    description
      "SRLinux 21.6.1";
  }
  revision 2021-03-31 {
    description
      "SRLinux 21.3.1";
  }
  revision 2020-06-30 {
    description
      "SRLinux 20.6.1";
  }

  feature aaa-fqdn-for-radius-server-address {
    description
      "FQDN for RADIUS server address";
  }

  feature aaa-fqdn-for-tacacs-server-address {
    description
      "FQDN for TACACS+ server address";
  }

  feature aaa-remote-superuser {
    description
      "Support for superuser flag for remote users";
  }

  feature aaa-server-timeout {
    description
      "Support for configuration of a per-server timeout in a AAA server group";
  }

  feature aaa-servers-health-check {
    description
      "Health checks for RADIUS and TACACS+";
  }

  feature aaa-servers-tacacs-vsa {
    description
      "TACACS+ VSAs for user roles and RBAC";
  }

  feature aaa-spiffe-id {
    description
      "Support for authentication using spiffe-id";
  }

  feature aaa-ssh-connections-limit {
    description
      "Support for SSH connections limit";
  }

  feature aaa-superuser {
    description
      "Support for superuser flag for local users and roles";
  }

  feature ac5x;

  feature acl-action-accept-with-log {
    description
      "Support of entry action accept with log";
  }

  feature acl-cpm-filter-match-network-instance {
    description
      "Support for ACL CPM-filter network-istance match criterion";
  }

  feature acl-cpm-filter-type-mac {
    description
      "Support for ACL CPM-filter of type mac";
  }

  feature acl-filter-allowed-on-irb-interfaces {
    description
      "Support for ACL filters on irb interfaces";
  }

  feature acl-filter-allowed-on-l2-interfaces {
    description
      "Support for ACL filters on l2 interfaces";
  }

  feature acl-filter-embed-entries-bgp-fs {
    description
      "ACL support for embedding FlowSpec entries";
  }

  feature acl-filter-ip-allowed-on-l2-interfaces {
    description
      "Support for ACL filters with type IPv4 or Ipv6 on l2 interfaces";
  }

  feature acl-filter-mac {
    description
      "Support for ACL mac filter";
  }

  feature acl-filter-mac-allowed-on-l2-interfaces {
    description
      "Support for ACL filters with type MAC on l2 interfaces";
  }

  feature acl-filter-mac-allowed-on-l3-interfaces {
    description
      "Support for ACL filters with type MAC on l3 interfaces";
  }

  feature acl-filter-qos-forwarding-class {
    description
      "Support for ACL filter based assignment of forwarding QOS class";
  }

  feature acl-filter-qos-profile {
    description
      "Support for ACL filter based assignment of QOS profile";
  }

  feature acl-filter-redirect-to-next-hop {
    description
      "Support for ACL based redirection to next hop";
  }

  feature acl-filter-redirect-to-ni {
    description
      "Support for ACL based redirection with network-instance override";
  }

  feature acl-filter-reject {
    description
      "Support for ACL Reject action";
  }

  feature acl-group-based-policy-policer {
    description
      "Support for ACL Group Based Policy (GBP) policers";
  }

  feature acl-if-output-shared-mac-tcam-entries {
    description
      "Support sharing of entries on acl interface output";
  }

  feature acl-if-output-shared-tcam-entries {
    description
      "Support sharing of entries on acl interface output";
  }

  feature acl-ip-option-present {
    description
      "Support for ACL Match IP Option Present";
  }

  feature acl-ip-packet-length {
    description
      "Support for ACL IP Packet Length";
  }

  feature acl-ip-prefix-list {
    description
      "Support for ACL IP Prefix List";
  }

  feature acl-ip-prefix-list-apply-path-bgp-peers {
    description
      "Support for ACL Prefix List Apply-Path BGP peers";
  }

  feature acl-ip-prefix-list-apply-path-interfaces {
    description
      "Support for ACL Prefix List Apply-Path interfaces";
  }

  feature acl-l4-port-list {
    description
      "Support for ACL L4 Port List";
  }

  feature acl-logging {
    description
      "Support for ACL logging";
  }

  feature acl-logging-fpcx {
    description
      "Support for ACL logging for fpcx";
  }

  feature acl-policer {
    description
      "Support for ACL policers";
  }

  feature acl-policer-for-mac-filters {
    description
      "Support for ACL policers with acl-filter type 'mac'";
  }

  feature acl-pps-policer {
    description
      "Support for ACL PPS policers";
  }

  feature acl-pps-policer-committed-rate {
    description
      "Support for ACL PPS policers committed rate";
  }

  feature acl-qos-ip-prefix-list {
    description
      "Support for QOS IP Prefix List";
  }

  feature acl-subinterface-entry-statistics {
    description
      "Support for ACL subinterface entry statistics";
  }

  feature acl-ttl {
    description
      "Support for ACL Match TTL";
  }

  feature admin-user-roles {
    description
      "Support for configurable roles for the admin user";
  }

  feature alarm-hardware {
    description
      "Support for alarm hardware, ACO/LT button, alarm LEDs, alarm connector";
  }

  feature algorithmic-tcam {
    description
      "Support for algorithmic TCAM compression and related operational telemetry (for example requested TCAM entry count).";
  }

  feature anycast-gw {
    description
      "Support for bridged feature and anycast-gw configuration on interface";
  }

  feature application-hot-restart {
    description
      "Support for application hot restart";
  }

  feature arp-nd-datapath-programming {
    description
      "Support for datapath programming of arp-nd routes";
  }

  feature backplane-facing-capacity {
    description
      "Support for backplane facing capacity paths";
  }

  feature bfd {
    description
      "Support for BFD";
  }

  feature bgp-accumulated-igp-metric {
    description
      "Support for AIGP metric path attribute";
  }

  feature bgp-add-paths {
    description
      "Support for bgp add path.";
  }

  feature bgp-add-paths-evpn {
    description
      "Support for bgp add path on evpn afi-safi.";
  }

  feature bgp-add-paths-l3vpn {
    description
      "Support for bgp add path on afi-safis l3vpn-ipv4-unicast and l3vpn-ipv6-unicast.";
  }

  feature bgp-add-paths-labeled-unicast {
    description
      "Support for bgp add path on afi-safis ipv4-labeled-unicast and ipv6-labeled-unicast..";
  }

  feature bgp-add-paths-policy-control {
    description
      "Support for bgp add path policy control.";
  }

  feature bgp-afi-safi-default-policy-action {
    description
      "Support for a default import and export policy action per afi-safi";
  }

  feature bgp-afi-safi-policy {
    description
      "Support for import and export policy per afi-safi.";
  }

  feature bgp-auth-password {
    description
      "Provide a BGP TCP MD5 authentication password without defining a keychain";
  }

  feature bgp-auto-discovery-using-lldp {
    description
      "Using LLDP to initiate outbound dynamic BGP sessions";
  }

  feature bgp-auto-link-bandwidth {
    description
      "Auto-generation of Link BW extended community based on interface speed";
  }

  feature bgp-backup-path-frr-evpn {
    description
      "BGP support for backup paths using BGP-EVPN routes. Also known as Edge PIC";
  }

  feature bgp-backup-path-frr-ip {
    description
      "BGP support for backup paths using IP routes. Also known as Edge PIC";
  }

  feature bgp-backup-path-frr-label-ip {
    description
      "BGP support for backup paths using label-unicast routes. Also known as Edge PIC";
  }

  feature bgp-backup-path-frr-vpn {
    description
      "BGP support for backup paths using BGP VPN routes. Also known as Edge PIC";
  }

  feature bgp-bmp-support {
    description
      "Support for BGP Monitoring Protocol (BMP)";
  }

  feature bgp-cfg-afi-safi-list {
    description
      "Support for the AFI-SAFI list based configuration and state model in BGP for instances, groups and neighbors.";
  }

  feature bgp-domain-path {
    description
      "Support for the Domain Path Attribute (D-PATH) for BGP IPVPN and EVPN routes";
  }

  feature bgp-flowspec-v1 {
    description
      "Support for bgp afi-safis ipv4-flowspec-v1 and ipv6-flowspec-v1";
  }

  feature bgp-graceful-restart-err {
    description
      "Support for BGP extended route retention additions to GR";
  }

  feature bgp-graceful-restart-gaps {
    description
      "Add missing leafs for graceful-restart";
  }

  feature bgp-graceful-restart-state-additions {
    description
      "Add missing state leafs for graceful restart";
  }

  feature bgp-group-based-policy {
    description
      "Support for GBP in the context of received and advertised BGP routes";
  }

  feature bgp-import-export-policy-leaflist {
    description
      "Change bgp import-policy and export-policy to a leaf-list";
  }

  feature bgp-ip-vrf-evpn-mi-mpls-vxlan {
    description
      "Support multi-instance bgp-evpn having different encap-type in ip-vrf";
  }

  feature bgp-ipv6-next-hop-tunnel-resolution {
    description
      "Resolve BGP IPv6 next-hops over IPv6 tunnels";
  }

  feature bgp-ipvx-mvpn {
    description
      "Support for bgp afi-safis ipv4-mvpn and ipv6-mvpn";
  }

  feature bgp-labeled-unicast {
    description
      "Support for BGP-LU address families";
  }

  feature bgp-labeled-unicast-future {
    description
      "Future (post 24.3) features for BGP-LU address families";
  }

  feature bgp-labeled-unicast-over-sr-te {
    description
      "Support for BGP-LU next-hop resolving over SR-TE tunnel";
  }

  feature bgp-labeled-unicast-prefix-sid {
    description
      "Support for prefix SID attribute in the context of SR-MPLS";
  }

  feature bgp-labeled-unicast-prefix-sid-ilm-statistics {
    description
      "BGP-LU prefix-SID ILM ingress statistics";
  }

  feature bgp-labeled-unicast-rfc8950 {
    description
      "Improved support for advertising BGP-LUv4 routes to IPv6 transport peers";
  }

  feature bgp-labeled-unicast-selective-install {
    description
      "Support for BGP-LU selective tunnel installation based on service endpoints";
  }

  feature bgp-labeled-unicast-tunnel-statistics {
    description
      "BGP Labeled Prefix statistics";
  }

  feature bgp-local-as-container-iso-list {
    description
      "Change list local-as to container in bgp group and neighbor";
  }

  feature bgp-max-ecmp-hash-buckets {
    description
      "Configuration of maximum hash buckets for weighted ECMP of BGP routes";
  }

  feature bgp-mtu-discovery {
    description
      "Support for BGP path MTU discovery.";
  }

  feature bgp-multipath-maximum-paths {
    description
      "Support for maximum BGP ECMP next-hops configuration.";
  }

  feature bgp-multipath-maximum-paths-limit-128 {
    description
      "Support multipath maximum-paths upper limit 128 depending on platform and afi-safi";
  }

  feature bgp-multipath-maximum-paths-limit-256 {
    description
      "Support multipath maximum-paths upper limit 256 depending on platform and afi-safi";
  }

  feature bgp-next-hop-resolution-policy {
    description
      "Support for BGP next-hop resolution policies";
  }

  feature bgp-next-hop-resolution-tag {
    description
      "Support for BGP next-hop resolution based on tags";
  }

  feature bgp-peertype-maximum-paths {
    description
      "Support for seperate BGP ECMP configuration for each peer-type (EBGP/IBGP)";
  }

  feature bgp-prefix-limit {
    description
      "Support for Bgp Prefix Limit enhancements.";
  }

  feature bgp-prefix-limit-forever {
    description
      "Support for Bgp Prefix Limit Restart Timer forever.";
  }

  feature bgp-prefix-limit-last-exceeded {
    description
      "Support of prefix-limit timestamp";
  }

  feature bgp-prefix-limit-post-policy {
    description
      "Support of prefix-limit-accepted configuration";
  }

  feature bgp-prefix-limit-received {
    description
      "Renaming bgp containers prefix-limit to prefix-limit-received.";
  }

  feature bgp-restart-max-wait {
    description
      "Introduction of system-wide BGP configuration container at /system/protocols/bgp for BGP AWR timer.";
  }

  feature bgp-rib-afi-safi-list {
    description
      "Support for the AFI-SAFI list based model in BGP RIB representation inspired from OC.";
  }

  feature bgp-rib-afi-safi-list-for-evpn {
    description
      "Support for the AFI-SAFI list based model in BGP RIB evpn representation inspired from OC.";
  }

  feature bgp-rib-afi-safi-route {
    description
      "Use list route in stead of list routes in bgp-rib";
  }

  feature bgp-route-flap-damping {
    description
      "Support for BGP route flap damping";
  }

  feature bgp-rr-for-rtc {
    description
      "BGP can act as route reflector for afi-safi route-target";
  }

  feature bgp-rtc {
    description
      "Support for BGP route target constraint";
  }

  feature bgp-send-community-leaflist {
    description
      "Use leaf-list send-community-type iso container send-community";
  }

  feature bgp-single-hop-connected-check {
    description
      "Support for Bgp transport Single Hop Connected Check.";
  }

  feature bgp-srte-policy {
    description
      "Support for BGP SR-TE policy address families";
  }

  feature bgp-srte-policy-sbfd-return-label {
    description
      "Support for sBFD return label for BGP SR-TE policy";
  }

  feature bgp-unnumbered-peers {
    description
      "Support dynamic bgp unnumbered peers.";
  }

  feature bgp-vpn-allow-export {
    description
      "Support BGP VPN allow-export.";
  }

  feature bgp-weighted-ecmp {
    description
      "Support for BGP weighted ECMP using link-bandwidth";
  }

  feature breakout-ports-1 {
    description
      "Support for 1 breakout port";
  }

  feature breakout-ports-2 {
    description
      "Support for 2 breakout ports";
  }

  feature breakout-ports-3 {
    description
      "Support for 3 breakout ports";
  }

  feature breakout-ports-4 {
    description
      "Support for 4 breakout ports";
  }

  feature breakout-ports-8 {
    description
      "Support for 8 breakout ports";
  }

  feature breakout-speed-100G {
    description
      "Support for 100G breakout port speed";
  }

  feature breakout-speed-10G {
    description
      "Support for 10G breakout port speed";
  }

  feature breakout-speed-1G {
    description
      "Support for 1G breakout port speed";
  }

  feature breakout-speed-200G {
    description
      "Support for 200G breakout port speed";
  }

  feature breakout-speed-25G {
    description
      "Support for 25G breakout port speed";
  }

  feature breakout-speed-400G {
    description
      "Support for 400G breakout port speed";
  }

  feature breakout-speed-50G {
    description
      "Support for 50G breakout port speed";
  }

  feature breakout-speed-800G {
    description
      "Support for 800G breakout port speed";
  }

  feature bridged {
    description
      "Support for MAC-VRF services";
  }

  feature bt-split-horizon-groups {
    description
      "Support for Bridge-Table split horizon groups";
  }

  feature central-security-module {
    description
      "Support for central security module";
  }

  feature chassis {
    description
      "The platform is in a chassis configuration";
  }

  feature chassis-mode {
    description
      "Support chasis mode selection feature";
  }

  feature chassis-mode-mixed {
    description
      "Support mixed chassis mode usage";
  }

  feature chassis-vertical-orientation {
    description
      "The platform supports a configurable mount orientation";
  }

  feature cli-commit-discard-options {
    description
      "Commit and discard cli environment options";
  }

  feature cli-modeled-environment {
    description
      "Support for cli modeled environment";
  }

  feature cli-plugin-authorization {
    description
      "Support for cli plugin authorization";
  }

  feature combined-bgp-ecmp {
    description
      "Support for ECMP across different BGP owners in an IP-VRF network-instance";
  }

  feature combined-ecmp-redirect {
    description
      "Support for data path egress filtering using redirect ACLs for combined ECMP and gateway-IP load balancing";
  }

  feature config-l2-mtu-default {
    description
      "Support for system mtu default-l2-mtu config";
  }

  feature config-sub-if-l2-mtu {
    description
      "Support for subinterface l2-mtu config";
  }

  feature configurable-intf-mac-addr {
    description
      "Support for configurable interface mac address";
  }

  feature connection-point {
    description
      "Support for connection points on network-instances";
  }

  feature containerz-cgroup {
    description
      "Support for containerz cgroup resource management";
  }

  feature containerz-location {
    description
      "Support for containerz location feature to control where containers are allowed to run";
  }

  feature control-card-reboot {
    description
      "This platform supports reboots of control cards

       Usually only for platforms with discrete CPMs.";
  }

  feature cpiom-linecard-redundancy {
    description
      "This platform supports redundant cpiom line cards";
  }

  feature cpm-datapath-resources {
    description
      "Support for monitoring the utilization of XDP-CPM datapath resources";
  }

  feature cpm-warm-redundancy {
    description
      "Support for CPM Warm Redundancy";
  }

  feature crc-symbol-monitoring {
    description
      "Support for interface crc and symbol monitoring";
  }

  feature dac-link-training {
    description
      "Support for configurable interface dac-link-training";
  }

  feature datapath-resource-watermarks {
    description
      "Support for monitoring high-watermark level of datapath resources";
  }

  feature dco-cmis-4-dot-0-application-descriptors {
    description
      "Support for reporting of application descriptors based on CMIS 4.0 and direct setting of AppSel code";
  }

  feature dco-logical-channels {
    description
      "Support for logical channels for digital coherent optics modules";
  }

  feature dco-loopback {
    description
      "Support for loopbacks withing the digital coherent optics modules";
  }

  feature dco-stats-avg-min-max {
    description
      "Support for digital coherent optics average, minimum, maximum statistics";
  }

  feature dhcp-relay {
    description
      "Support DHCPv4/v6 relay for non-mixed-mode platforms only";
  }

  feature dhcp-relay-fqdn {
    description
      "Support for dhcp relay fqdn feature";
  }

  feature dhcp-relay-irb-l2-circuit-id {
    description
      "Support IRB L2 interface name and mac-vrf instance name in Option 82 or 18";
  }

  feature dhcp-server {
    description
      "Support DHCPv4/v6 server feature";
  }

  feature dhcp-server-guard {
    description
      "Support for fhs dhcp server guard";
  }

  feature dhcp-svr-boot-compute {
    description
      "Support for dhcp server support for boot compute. custom options. next server address";
  }

  feature dhcp-svr-option-121 {
    description
      "Support for dhcp server option 121, Classless Static Route feature";
  }

  feature dhcp-svr-option-26 {
    description
      "Support for dhcp server option 26, Interface Mtu feature";
  }

  feature dhcpv4-snooping {
    description
      "Support for DHCPv4 snooping";
  }

  feature dhcpv6-snooping {
    description
      "Support for DHCPv6 snooping";
  }

  feature digital-coherent-optics {
    description
      "Support for digital coherent optics modules";
  }

  feature disabled {
    description
      "Feature flag that is always disabled";
  }

  feature disk-encryption {
    description
      "Support for Disk Encryption";
  }

  feature dot1q-vlan-ranges {
    description
      "Support for configurable dot1q vlan-ranges";
  }

  feature dot1x-authenticator {
    description
      "Support for dot1x authenticator configuration";
  }

  feature dot1x-authenticator-lag {
    description
      "Support for dot1x authenticator configuration on lag interfaces";
  }

  feature dot1x-authenticator-mac-based-authentication {
    description
      "Support for dot1x authenticator mac based authentication";
  }

  feature dot1x-authenticator-mba-quiet-period {
    description
      "Support for quiet period for IEEE802.1X MBA hosts";
  }

  feature dot1x-authenticator-multi-host-auth {
    description
      "Support for IEEE 802.1X authenticator multi-host host-mode";
  }

  feature dot1x-authenticator-multi-host-auth-tcam-res-mgmt {
    description
      "Support for dot1x tcam resource guard";
  }

  feature dot1x-interface-stats {
    description
      "Support for dot1x stats per interface";
  }

  feature dot1x-supplicant {
    description
      "Support for IEEE802.1X supplicant";
  }

  feature dot1x-tunnel {
    description
      "Support for dot1x tunneling";
  }

  feature dot1x-tunnel-detail {
    description
      "Support for specific dot1x tunneling

       Some platforms can tunnel with finer granularity of untagged, single-tagged, double-tagged.";
  }

  feature dot1x-tunnel-system-stats {
    description
      "Support for tunneling IEEE 802.1X statistics in the system context";
  }

  feature dot1x-tunnel-tunnel-all {
    description
      "Support for dot1x tunneling tunnel-all

       Some platforms can tunnel, but not with fine (untagged, signle-tagged, double-tagged) granularity.";
  }

  feature dynamic-load-balancing {
    description
      "Support for dynamic-load-balancing";
  }

  feature dynamic-subinterfaces {
    description
      "Support for dynamic subinterfaces";
  }

  feature dynamic-tcam {
    description
      "Support for Dynamic TCAM";
  }

  feature egress-mac-filter-restriction {
    description
      "Platform requires explicit egress-mac-filter enabling";
  }

  feature egress-subif-policing {
    description
      "Support for egress subinterface policing based on policer-templates";
  }

  feature entropy-bgp-sr {
    description
      "Support for Entropy label with BGP and SR-ISIS";
  }

  feature ethcfm {
    description
      "Support for Ethernet CFM";
  }

  feature ethcfm-ingress-squelching {
    description
      "Support for Ethernet CFM ingress squelching";
  }

  feature ethcfm-mp-custom-mac-address {
    description
      "Support for Ethernet CFM Management Point custom MAC address configuration";
  }

  feature ethcfm-mp-mac-address-allocation {
    description
      "Support selectable Ethernet CFM Management Point MAC allocation scheme";
  }

  feature ethcfm-nsr {
    description
      "Support for Ethernet CFM non-stop-routing";
  }

  feature ethcfm-opcode-stats {
    description
      "Support for Ethernet CFM per operational code statistics";
  }

  feature ethcfm-sender-id-tx {
    description
      "Support for Ethernet CFM transmission of sedner id tlv";
  }

  feature ethcfm-subinterface {
    description
      "Support for Ethernet CFM configuration on subinterface";
  }

  feature event-handler {
    description
      "Support for the MicroPython-based event handler";
  }

  feature event-handler-cron {
    description
      "Support for cron-like scheduling of event handler script";
  }

  feature evpn {
    description
      "Support for EVPN";
  }

  feature evpn-anycast-l3-subnet {
    description
      "Support for EVPN Anycast for multi-homing L3 subnets for zero ESI";
  }

  feature evpn-iff {
    description
      "Support for EVPN Interface-ful model for IP Prefix routes, as in RFC9136 sections 4.4.2 and 4.4.3";
  }

  feature evpn-iff-unnumbered {
    description
      "Support for EVPN Interface-ful unnumbered model for IP Prefix routes, as in RFC9136 sections 4.4.2 and 4.4.3";
  }

  feature evpn-ifl-gw-ip {
    description
      "Support for non-zero GW-IP (Gateway IP) advertisement and resolution for EVPN IFL routes as per RFC9135 section 9.2";
  }

  feature evpn-ifl-host {
    description
      "Support for the advertisement of EVPN-IFL host routes or MAC/IP Advertisement routes with layer-2/layer-3 labels/VNIs and route targets";
  }

  feature evpn-ifl-host-ip-aliasing {
    description
      "Support for the advertisement of IP AD per EVI/ES routes for EVPN-IFL host routes as per draft-ietf-bess-evpn-ip-aliasing";
  }

  feature evpn-ifl-unequal-ecmp {
    description
      "Support for EVPN unequal ECMP for RT5 IFL routes";
  }

  feature evpn-iml-label-block {
    description
      "Support for allocation of labels for EVPN IML routes from a seperate label block.";
  }

  feature evpn-layer-2-ecmp {
    description
      "Support for the layer-2 ecmp on BGP EVPN services";
  }

  feature evpn-mh {
    description
      "Support for EVPN Multi-Homing";
  }

  feature evpn-mh-anycast {
    description
      "Support for EVPN Anycast Multi-Homing on Ethernet Segments";
  }

  feature evpn-mh-ip-aliasing {
    description
      "Support for EVPN Multi-Homing IP Aliasing Ethernet Segments";
  }

  feature evpn-mh-multicast-non-df-tcam-resource {
    description
      "Report TCAM entries used by egress filtering of IP multicast traffic to non-Designated Forwarder subinterfaces";
  }

  feature evpn-mh-no-esi-label {
    description
      "Support for EVPN Multi-Homing without ESI label";
  }

  feature evpn-mh-non-system-ipv4-address {
    description
      "Support for non-system ipv4 address as the next-hop and originating ip of EVPN Multi-Homing routes";
  }

  feature evpn-mh-virtual-es {
    description
      "Support for virtual ethernet-segments";
  }

  feature evpn-mpls {
    description
      "Support for EVPN MPLS";
  }

  feature evpn-mpls-control-word {
    description
      "Support for control-word in evpn-mpls";
  }

  feature evpn-mpls-shg {
    description
      "Support for EVPN MPLS Split-Horizon-Groups";
  }

  feature evpn-neighbor-synchronization {
    description
      "Support for EVPN Neighbor Synchronization on layer-3 interfaces";
  }

  feature evpn-route-internal-tags {
    description
      "Support for internal tags associated to evpn routes";
  }

  feature evpn-rt2-proxy-irb {
    description
      "Support for EVPN RT2 Proxy functionality on IRB subinterfaces";
  }

  feature evpn-rt2-proxy-mac-vrf {
    description
      "EVPN multihoming RT-2 proxy (draft-evpn-ip-mac-proxy) on MAC-VRF network-instance";
  }

  feature evpn-vxlan-ifl {
    description
      "Support for EVPN-VXLAN on ip-vrf network-instances";
  }

  feature evpn-vxlan-mac-vrf {
    description
      "Support for EVPN-VXLAN on mac-vrf network-instances";
  }

  feature evpn-vxlan-oism {
    description
      "Support for OISM on EVPN VXLAN, as per RFC9625";
  }

  feature evpn-vxlan-oism-peg {
    description
      "Support for OISM PIM to EVPN Gateway functionality on EVPN VXLAN, as per RFC9625";
  }

  feature exponential-port-dampening {
    description
      "Support for exponential port dampening";
  }

  feature facility-alarm-mgr {
    description
      "Support for facility alarm manager to track and display the basic status of the equipment facilities";
  }

  feature factory-reset {
    description
      "Support for gNOI Factory Reset";
  }

  feature fan-avg-speed-show-report {
    description
      "Update fan show command to display average fan speed field";
  }

  feature fib-ilm-programming {
    description
      "Support for ILM FIB programming state";
  }

  feature fib-programming-progress {
    description
      "Support for FIB programming progress per forwarding complex";
  }

  feature fib-tunnel-programming {
    description
      "Support for tunnel FIB programming state";
  }

  feature first-hop-security {
    description
      "Support for First Hop Security.";
  }

  feature fixed {
    description
      "The platform is in a fixed configuration, i.e. non-chassis platforms";
  }

  feature fixed-mgmt-port-names {
    description
      "The platform supports mgmtA and mgmtB interfaces";
  }

  feature flex-algo-common {
    description
      "Support for Common Flexible Algorithm Definition (FAD) and Attributes";
  }

  feature flex-algo-nhg {
    description
      "Support for Flexible Algorithm tunnel resolution support with next hop groups";
  }

  feature flex-algo-te-metric {
    description
      "Support for Flexible Algorithm specific te-metric";
  }

  feature flow-aware-transport-label {
    description
      "Support for Flow-Aware Transport (FAT) label";
  }

  feature flow-aware-transport-label-evpn-mpls-vpws {
    description
      "Support for BGP-EVPN mpls flow aware transport (FAT) label in VPWS network-instances";
  }

  feature forward-error-correction-ethernet {
    description
      "Support for configuring fec in the ethernet context";
  }

  feature forwarding-complex-1 {
    description
      "Support for forwarding-complex 1";
  }

  feature forwarding-complex-pipeline-counters {
    description
      "Support for forwarding-complex drop counters and aggregate CPU extration statistics";
  }

  feature fpcx {
    description
      "FPcx based platforms";
  }

  feature future-0-0 {
    description
      "Only true in 0.0 stream, false in other streams. The feature is for an unknown future release.";
  }

  feature glome-authentication {
    description
      "GLOME user authentication for linux users (console and non-console)";
  }

  feature gnmi-extensions {
    description
      "Nokia gNMI extensions";
  }

  feature gnmi-services {
    description
      "gNMI services";
  }

  feature gnoi-bgp {
    description
      "gNOI Bgp service";
  }

  feature gnoi-bootconfig {
    description
      "gNOI BootConfig service";
  }

  feature gnoi-containerz {
    description
      "gNOI containerz service";
  }

  feature gnoi-export-protos {
    description
      "OpenConfig protos";
  }

  feature gnoi-healthz {
    description
      "gNOI Healthz service";
  }

  feature gnoi-healthz-forwarding-complex {
    description
      "gNOI Healthz service support for forwarding-complex";
  }

  feature gnoi-yang-action {
    description
      "gNOI YANG action service";
  }

  feature gnpsi {
    description
      "gnPSI gRPC Network Packet Sampling Interface";
  }

  feature gnsi-accounting {
    description
      "gNSI Accounting service";
  }

  feature gnsi-authz {
    description
      "gNSI Authz service";
  }

  feature gnsi-certz {
    description
      "gNSI Certz service";
  }

  feature gnsi-credentialz {
    description
      "gNSI Credentialz service";
  }

  feature gnsi-pathz {
    description
      "gNSI Pathz service";
  }

  feature gribi-host-prefix-ip-tunnel-statistics {
    description
      "gRIBI host prefix IP tunnel statistics";
  }

  feature group-based-policy {
    description
      "Micro Segmentation Group Based Policy";
  }

  feature group-based-policy-ip-vrf {
    description
      "Micro Segmentation Group Based Policy on IP-VRF network-instances";
  }

  feature grpc-server {
    description
      "Support for gRPC server";
  }

  feature grpc-server-max-concurrent-streams {
    description
      "Configurable gRPC max concurrent streams parameter";
  }

  feature grpc-tunnel {
    description
      "Support for gRPC Tunnel";
  }

  feature grub-password {
    description
      "Support for grub password";
  }

  feature host-network-instance {
    description
      "Support for host network-instance type";
  }

  feature icmp-rate-control {
    description
      "System-wide control of ICMP message generation rates";
  }

  feature igmp {
    description
      "Support for IGMP";
  }

  feature igmp-ipvrf {
    description
      "Support for IGMP on ipvrf";
  }

  feature igmp-snooping {
    description
      "Support for IGMP snooping";
  }

  feature igp-overload-on-fib-failure {
    description
      "IGP overload handling after FIB failures";
  }

  feature individual-fan-state {
    description
      "Support for the reporting of individual fan speed state within a fan tray";
  }

  feature ingress-subif-policing {
    description
      "Support for ingress subinterface policing based on policer-templates";
  }

  feature inter-as-nhsrr-ipvpn {
    description
      "Support for inter-as model B and next hop self route reflector functionality for ipvpn";
  }

  feature interface-evpn-internal-tags {
    description
      "Support for internal tags associated to arp/nd routes advertised in evpn";
  }

  feature interface-references {
    description
      "Support for interface-ref containers under network-instance.";
  }

  feature internal-tags {
    description
      "Support for internal tags associated to routes or tunnels";
  }

  feature intf-eth-in-undersize-frames {
    description
      "Support for interface ethernet statistic in-undersize-frames";
  }

  feature ip-acl-dscp-set {
    description
      "Support for IP ACL matching on DSCP sets";
  }

  feature ip-mac-binding {
    description
      "Support for fhs ip_mac binding";
  }

  feature ip-qos-multifield {
    description
      "Support for ingress QoS classification based on multifield classifier policies";
  }

  feature ip-qos-multifield-on-bridged-subifs {
    description
      "Support for ingress QoS classification based on multifield classifier policies on subinterfaces type bridged";
  }

  feature ip-tunnel-decap-groups {
    description
      "Support for IP tunnel decapsulation groups";
  }

  feature ip-tunnel-encap-stats {
    description
      "Support for IP tunnel encapsulation statistics";
  }

  feature ipfix {
    description
      "Support of Flow Sampling feature";
  }

  feature ipsec-inline-fastpath {
    description
      "Support IPsec with inline fastpath";
  }

  feature ipv4-ipv6-routes-lem-optimization-resources {
    description
      "Support for resources for IPv4/IPv6 FIB expansion into LEM and compression of entries";
  }

  feature ipv4-routes-lem-optimization {
    description
      "Support for IPv4 FIB expansion into LEM and compression of entries";
  }

  feature ipv4-unnumbered {
    description
      "Support for IPv4 unnumbered interfaces";
  }

  feature ipvpn {
    description
      "Support for bgp-ipvpn";
  }

  feature ipvpn-route-internal-tags {
    description
      "Support for internal tags associated to ipvpn routes";
  }

  feature isis-adjsid-holdtime {
    description
      "Support for isis adjacency sid holdtime";
  }

  feature isis-advertise-passive-only {
    description
      "Support for isis advertise-passive-only";
  }

  feature isis-app-hot-restart {
    description
      "Support for isis non-stop-routing";
  }

  feature isis-delay-normalization {
    description
      "Support for isis delay normalization";
  }

  feature isis-dyn-delay {
    description
      "Support for isis dynamic delay advertisement";
  }

  feature isis-flex-algo {
    description
      "Support for ISIS flexible algorithms";
  }

  feature isis-interface-afi-safi-enable {
    description
      "Enable Placeholder leaf for OC mapping of interface context IPv4 or IPv6 enable flag";
  }

  feature isis-level-passive {
    description
      "Support for isis per level passive configuration";
  }

  feature isis-lfa {
    description
      "Support for ISIS loop-free alternates";
  }

  feature isis-loopfree-alternate-flex-algo {
    description
      "Support for isis micro-loop avoidance";
  }

  feature isis-lsdb {
    description
      "Support for isis link-state-database";
  }

  feature isis-lsdb-te-extensions {
    description
      "Support for isis link-state-database TE extensions";
  }

  feature isis-maint-mode {
    description
      "Support for isis maintainance mode";
  }

  feature isis-mi {
    description
      "Support for isis multi-instance";
  }

  feature isis-micro-loop-avoidance {
    description
      "Support for isis micro-loop avoidance";
  }

  feature isis-micro-loop-avoidance-flex-algo {
    description
      "Support for isis micro-loop avoidance";
  }

  feature isis-mt {
    description
      "Support for isis multi-topology";
  }

  feature isis-multi-part-tlv {
    description
      "Support for isis multi-part tlv's";
  }

  feature isis-nsf {
    description
      "Support for isis non-stop-forwarding";
  }

  feature isis-rtr-capability {
    description
      "Support for configurable advertise-router-capability";
  }

  feature isis-srv6 {
    description
      "Support for ISIS Segment Routing with SRv6 dataplane";
  }

  feature isis-topology-state {
    description
      "Support for ISIS Topology State for Standard SPF";
  }

  feature isis-ucmp {
    description
      "Support for isis weighted ecmp";
  }

  feature ixr-dnx;

  feature ixr-dnx-gen2;

  feature ixr-dnx-gen2cp;

  feature ixr-dnx-gen2cp-gen3-mixed-system {
    description
      "7250 IXR Gen 2cp and Gen 3 mixed card in a chassis grouping. This list consists of 7250 IXR-6e and IXR-10e with Jericho-2cp and Jericho-3 cards in the same chassis. Last updated on Jul, 2025";
  }

  feature ixr-dnx-gen2cp-only-system {
    description
      "7250 IXR Gen 2cp platform grouping. This list consists of 7250 IXR-X1b, IXR-X3b and IXR-6e, IXR-10e with Jericho-2cp cards as of Jul, 2025";
  }

  feature ixr-dnx-gen3;

  feature ixr-dnx-gen3-only-system {
    description
      "7250 IXR Gen 3 platform grouping. This list consists of 7250 IXR-6e, IXR-10e and IXR-18e with Jericho-3 cards as of Jul, 2025";
  }

  feature ixr-xgs;

  feature jericho2;

  feature jericho2cp;

  feature jericho3;

  feature keychain {
    description
      "Support for protocol authentication keychains with multiple keys";
  }

  feature l2-proxy-arp {
    description
      "Support for Bridge Table proxy ARP functionality";
  }

  feature l2-proxy-arp-nd-control-flood-on-evpn {
    description
      "Support for controlling snooped arp/nd frames on evpn in mac-vrf network-instances";
  }

  feature l2-proxy-arp-nd-route-internal-tags {
    description
      "Support for internal tags associated to proxy arp/nd evpn routes";
  }

  feature l2-proxy-nd {
    description
      "Support for Bridge Table proxy ND functionality";
  }

  feature l2cp-transparency {
    description
      "Support for Layer-2 Control Protocol transparency or tunneling";
  }

  feature l2cp-transparency-efm-oam {
    description
      "Support for Layer-2 Control Protocol transparency or tunneling for efm-oam frames";
  }

  feature l2cp-transparency-elmi {
    description
      "Support for Layer-2 Control Protocol transparency or tunneling for elmi frames";
  }

  feature l2cp-transparency-esmc {
    description
      "Support for Layer-2 Control Protocol transparency or tunneling for esmc frames";
  }

  feature l2cp-transparency-stats {
    description
      "Support for Layer-2 Control Protocol transparency or tunneling system level statistics";
  }

  feature l2cp-transparency-xstp {
    description
      "Support for Layer-2 Control Protocol transparency or tunneling for xstp frames";
  }

  feature l3-multicast-vpn {
    description
      "Support for l3-multicast-vpn";
  }

  feature l3-multicast-vpn-policy {
    description
      "Support for l3-multicast-vpn";
  }

  feature l3-multicast-vpn-spmsi {
    description
      "Support for l3-multicast-vpn-spmsi";
  }

  feature l3-proxy-arp {
    description
      "Support for layer-3 sub-interface proxy ARP functionality";
  }

  feature l3-proxy-arp-irb {
    description
      "Support for layer-3 sub-interface proxy ARP functionality on IRB interfaces";
  }

  feature l3-proxy-nd {
    description
      "Support for layer-3 sub-interface proxy ND functionality";
  }

  feature l3-proxy-nd-irb {
    description
      "Support for layer-3 sub-interface proxy ND functionality on IRB interfaces";
  }

  feature label-management {
    description
      "Support for mpls label management";
  }

  feature label-range-user-owner {
    description
      "Use 'owner' instead of 'protocol' to refer to the user of an MPLS label-range.";
  }

  feature labeled-tunnel-statistics {
    description
      "Labeled tunnel statistics resources usage tracker";
  }

  feature lacp-fallback {
    description
      "Support for link aggregation control protocol fallback";
  }

  feature lacp-fallback-individual-mode {
    description
      "Support for link aggregation control protocol fallback individual mode";
  }

  feature lag {
    description
      "Support for link aggregation groups";
  }

  feature lag-forwarding-viable {
    description
      "Support for lag member forwarding-viable option";
  }

  feature lag-member-speed-2-5G {
    description
      "Support for 2.5G ethernet LAG member-links speed";
  }

  feature lag-member-speed-5G {
    description
      "Support for 5G ethernet LAG member-links speed";
  }

  feature lawful-intercept {
    description
      "Support for lawful intercept";
  }

  feature ldp {
    description
      "Support for label distribution protocol";
  }

  feature ldp-bfd {
    description
      "Support for BFD in LDP";
  }

  feature ldp-entropy-label {
    description
      "Support for entropy label with LDP LSPs";
  }

  feature ldp-implicit-null-label {
    description
      "Support for pushing implicit null label (e.g. no label) under LDP global context";
  }

  feature ldp-ipv4-auto-rx-tx-targeted {
    description
      "Support for IPv4 auto-rx and auto-tx T-LDP";
  }

  feature ldp-ipv6 {
    description
      "Support for LDP IPv6 extensions";
  }

  feature ldp-label-wdraw-delay {
    description
      "Support for configuring the LDP label withdrawal delay";
  }

  feature ldp-lfa {
    description
      "Support for LFA in LDP";
  }

  feature ldp-lfa-ospf {
    description
      "Support for LFA in LDP with OSPFv2 as IGP";
  }

  feature ldp-local-lsr-id {
    description
      "Support for local LSR ID in LDP";
  }

  feature ldp-mcast-generic {
    description
      "Support for multicast LDP for generic FECs";
  }

  feature ldp-mcast-generic-dnx {
    description
      "Support for multicast LDP for generic FECs on DNX";
  }

  feature ldp-mcast-generic-fpcx {
    description
      "Support for multicast LDP for generic FECs on FPcx";
  }

  feature ldp-mcast-oam {
    description
      "Support for OAM for multicast LDP";
  }

  feature ldp-prefix-policies {
    description
      "Support for LDP prefix policies";
  }

  feature ldp-remote-lfa-ospf {
    description
      "Support for remote LFA in LDP with OSPFv2 as IGP";
  }

  feature ldp-rlfa {
    description
      "Support for remote LFA using LDP";
  }

  feature ldp-static-fec-pop {
    description
      "Static FEC origination";
  }

  feature ldp-targeted {
    description
      "Support for targeted label distribution protocol";
  }

  feature ldp-targeted-dnx {
    description
      "Support for targeted label distribution protocol on DNX";
  }

  feature ldp-targeted-fpcx {
    description
      "Support for targeted label distribution protocol on FPcx";
  }

  feature ldp-targeted-static-ipv6 {
    description
      "Support for static IPv6 targeted LDP";
  }

  feature ldp-targeted-static-ipv6-dnx {
    description
      "Support for static IPv6 targeted LDP on DNX";
  }

  feature ldp-targeted-static-ipv6-fpcx {
    description
      "Support for static IPv6 targeted LDP on FPcx";
  }

  feature ldp-tunnel-down-damp-time {
    description
      "Support for LDP tunnel damp time";
  }

  feature license {
    description
      "Support for licenses";
  }

  feature license-hw {
    description
      "Support for licenses on hardware platforms";
  }

  feature linecard-locator {
    description
      "The this platform line cards support locator function

       Usually only for platforms with discrete IMM.";
  }

  feature linecard-reboot {
    description
      "This platform supports reboots of line cards

       Usually only for platforms with discrete IMM.";
  }

  feature link-loss-forwarding {
    description
      "Support for link-loss-forwarding";
  }

  feature link-measurement {
    description
      "Support for dynamic link neasurement";
  }

  feature link-measurement-lag-micro-sessions {
    description
      "Support for dynamic link neasurement";
  }

  feature lldp-component {
    description
      "Support for LLDP Org Specific TLV type 127 OUI 00:12:0F subtype 04 and OUI 00:80:C2 subtype 07";
  }

  feature lldp-med {
    description
      "Support for LLDP for Media Endpoint Devices";
  }

  feature lldp-suppress-tlv {
    description
      "Support for suppress-tlv-advertisement";
  }

  feature lldp-ue-link-negotiation {
    description
      "Support for a component of LLDP Ultra Ethernet Link negotiation TLV";
  }

  feature lldp-vlan {
    description
      "Support for Orgainizationally Specific LLDP TLVs for the transmission of VLAN information";
  }

  feature load-balancing {
    description
      "Support for load-balancing related configuration";
  }

  feature location-coordinates {
    description
      "Support for location coordinates";
  }

  feature log-filter-for-negation {
    description
      "Options for filter negation of prefix, contains and regex at rsyslog";
  }

  feature log-tls {
    description
      "TLS encryption support for rsyslog";
  }

  feature longest-prefix-match {
    description
      "Support show route table for the longest prefix match";
  }

  feature loopback-mode-facility {
    description
      "Support facility option for loopback-mode";
  }

  feature loopback-mode-terminal {
    description
      "Support terminal option for loopback-mode";
  }

  feature macsec {
    description
      "Support for macsec";
  }

  feature macsec-fallback-keychain {
    description
      "Support for fallback keychain for macsec";
  }

  feature macsec-lag-subinterface {
    description
      "Support for macsec on a LAG subinterface";
  }

  feature macsec-subinterface {
    description
      "Support for macsec on a subinterface";
  }

  feature maintenance-mode-improvements {
    description
      "Improvements for maintenance mode";
  }

  feature mcac {
    description
      "Support for Multicast Access Control";
  }

  feature mcast-route-policy {
    description
      "Support for multicast handling in route policy";
  }

  feature mda {
    description
      "The platform uses discrete MDA components";
  }

  feature measured-boot {
    description
      "Support for Measured Boot";
  }

  feature mirror-dest-local {
    description
      "Support for local mirror-destination";
  }

  feature mirror-dest-pcap-internal-capture-if {
    description
      "Support for mirroring based tools traffic-monitor capture";
  }

  feature mirror-dest-remote {
    description
      "Support for remote mirror-destination";
  }

  feature mirror-dest-remote-tunnel-encap-l2ogre {
    description
      "Support for remote mirror-destination encap l2overgre";
  }

  feature mirror-dest-remote-tunnel-encap-l3ogre {
    description
      "Support for remote mirror-destination encap l3overgre";
  }

  feature mirror-dest-remote-tunnel-encap-mplsogre {
    description
      "Support for remote mirror-destination encap mplsovergre";
  }

  feature mirror-dest-remote-tunnel-mpls {
    description
      "Support for remote mirror-destination over supported mpls tunnel";
  }

  feature mirror-dest-slicing {
    description
      "Support for mirror-destination packet slicing";
  }

  feature mirror-dest-statistics {
    description
      "Support for mirror-destination statistics";
  }

  feature mirror-dest-statistics-egress-pkts {
    description
      "Support for mirror-destination statistics for egress packets count";
  }

  feature mirror-dest-statistics-octets {
    description
      "Support for mirror-destination statistics for total octets";
  }

  feature mirror-source-acl {
    description
      "Support for acl based mirror-source";
  }

  feature mirror-source-intf {
    description
      "Support for interface based mirror-source";
  }

  feature mirror-source-subintf {
    description
      "Support for subinterface based mirror-source";
  }

  feature mirror-source-subintf-bridged {
    description
      "Support for layer-2 subinterface based mirror-source";
  }

  feature mirroring {
    description
      "Support for mirroring (SPAN/ERSPAN)";
  }

  feature mirroring-intf-stats {
    description
      "Support for mirroring interface stats";
  }

  feature mirroring-tools-mirror-dest-statistics {
    description
      "Support for tools mirror-dest-statistics";
  }

  feature mld {
    description
      "Support for MLD";
  }

  feature mld-ipvrf {
    description
      "Support for MLD on ipvrf";
  }

  feature mld-snooping {
    description
      "Support for MLD snooping";
  }

  feature mpls {
    description
      "Support for MPLS";
  }

  feature mpls-ndk {
    description
      "Support for NDK static MPLS";
  }

  feature mpls-oam {
    description
      "Support for MPLS OAM, includes LSP ping and trace operations";
  }

  feature mpls-oam-colored-te-policy {
    description
      "Support for lsp-ping and lsp-trace over SR MPLS colored TE-Policy";
  }

  feature mpls-oam-p2mp-ldp {
    description
      "Support for mpls oam p2mp ldp lsp-ping";
  }

  feature mpls-oam-uncolored-tepolicy {
    description
      "Support for lsp-ping and lsp-trace over SR MPLS uncolored TE-Policy";
  }

  feature mpls-over-ip-dscp-marking-enhancements {
    description
      "Support for in-profile vs out-profile DSCP marking when encapsulating MPLS inside IP tunnels";
  }

  feature mpls-static-lsp {
    description
      "Support for static MPLS LSPs";
  }

  feature msdp {
    description
      "Support for MSDP";
  }

  feature named-queues-and-named-fcs {
    description
      "Support for named queues and forwarding classes";
  }

  feature ndk-admin-state {
    description
      "Support in YANG to admin-state enable/disable NDK mgr";
  }

  feature ndk-auto-telemetry-state {
    description
      "Support for option to auto update config state for NDK apps";
  }

  feature ndk-disable-caching {
    description
      "Support for disabling caching in NDK mgr";
  }

  feature net-inst-mgr-app-hot-restart {
    description
      "Support for net_inst_mgr hot restart";
  }

  feature netconf {
    description
      "Support for NETCONF";
  }

  feature netconf-unix-socket {
    description
      "Support for NETCONF over unix socket";
  }

  feature network-instance-leaked-route-readvertisement {
    description
      "Support for leaked route re-advertisement";
  }

  feature network-instance-mpls {
    description
      "Support for MPLS Services";
  }

  feature network-instance-multi-label-block-mpls {
    description
      "Support for multiple label blocks for MPLS Services in network-instances";
  }

  feature network-instance-protocol-instance-names {
    description
      "Support for naming BGP, static and aggregate protocol instances";
  }

  feature network-instance-route-limits {
    description
      "Support for a configurable per-family route limit for a network-instance";
  }

  feature network-instance-single-dynamic-label-block-mpls {
    description
      "Support for single dynamic label block for MPLS Services in network-instances";
  }

  feature network-instance-static-mpls {
    description
      "Support for MPLS Services with static labels";
  }

  feature nhsrr-evpn {
    description
      "Support for next hop self route reflector functionality for evpn";
  }

  feature ntp-server {
    description
      "Support for NTP server instances";
  }

  feature ntp-tls {
    description
      "TLS encryption support for NTP";
  }

  feature num-physical-channels {
    description
      "Support for configuring the number of physical channels for interfaces";
  }

  feature num-physical-channels-breakout {
    description
      "Support for configuring the number of physical channels for breakouts";
  }

  feature oam {
    description
      "Support for OAM";
  }

  feature oam-csig {
    description
      "Support for OAM Congestion Signalling";
  }

  feature oam-pm {
    description
      "Support for OAM Performance Monitoring";
  }

  feature oam-pm-ethcfm {
    description
      "Support for OAM Performance Monitoring Ethernet CFM";
  }

  feature oam-pm-ethcfm-dmm {
    description
      "Support for OAM Performance Monitoring Ethernet CFM DMM protocol";
  }

  feature oam-pm-ethcfm-slm {
    description
      "Support for OAM Performance Monitoring Ethernet CFM SLM protocol";
  }

  feature oam-pm-ip {
    description
      "Support for OAM Performance Monitoring IP";
  }

  feature oc-extracted-cpm-traffic-stats {
    description
      "Support for OpenConfig extracted CPM traffic statistics";
  }

  feature openconfig {
    description
      "Support for OpenConfig";
  }

  feature operational-fan-speed {
    description
      "Support for displaying the operational fan speed";
  }

  feature optical-line-system {
    description
      "Support for QFSP-DD-LS Amplifier";
  }

  feature ospf-mgr-app-hot-restart {
    description
      "Support for ospf hot restart";
  }

  feature ospf-vprn-dn-bit {
    description
      "Support for OSPF DN-bit control (ignore-dn-bit / suppress-dn-bit) in ip-vrf (VPRN) network-instances";
  }

  feature p4rt {
    description
      "Support for P4Runtime";
  }

  feature packet-link-qualification {
    description
      "Support for gNOI Packet Link Qualification";
  }

  feature packet-tracer {
    description
      "Support for oam packet-trace";
  }

  feature password-complexity-repeated-characters {
    description
      "Max occurrence of the same character consecutively";
  }

  feature password-complexity-sequence {
    description
      "Disallow sequence keys in password";
  }

  feature pcep-pcc {
    description
      "Path Computation Element client functionality";
  }

  feature pcep-pcc-pce-association {
    description
      "Path Computation Element client functionality for pce associations";
  }

  feature pcep-pcc-pce-init {
    description
      "PCE init SL, te-policy template";
  }

  feature pcep-pcc-tls {
    description
      "Path Computation Element client functionality to support TLS";
  }

  feature per-port-hash-seed {
    description
      "Support for per port ECMP hash seed on selected interfaces";
  }

  feature pim {
    description
      "Support for PIM";
  }

  feature pim-ipvrf {
    description
      "Support for PIM IP VRF";
  }

  feature pim-snooping {
    description
      "Support for PIM snooping";
  }

  feature pim-spt-switchover {
    description
      "Support for PIM SPT switchover";
  }

  feature platform-7215-a1;

  feature platform-7220-d1;

  feature platform-7220-d2;

  feature platform-7220-d3;

  feature platform-7220-d4;

  feature platform-7220-d5;

  feature platform-7220-h2;

  feature platform-7220-h3;

  feature platform-7220-h4;

  feature platform-7220-h4-32d;

  feature platform-7220-h5-32d;

  feature platform-7220-h5-64d;

  feature platform-7220-h5-64o;

  feature platform-7220-h5-64o-512;

  feature platform-7220-h6-64;

  feature platform-7250-ixr;

  feature platform-7250-ixr-18e-gen3;

  feature platform-7250-ixr-18e-unified;

  feature platform-7250-ixr-e-gen2cp;

  feature platform-7250-ixr-e-gen2cp-3;

  feature platform-7250-ixr-e-gen3;

  feature platform-7250-ixr-e-unified;

  feature platform-7250-ixr-x1b;

  feature platform-7250-ixr-x3b;

  feature platform-7250-ixr-x4;

  feature platform-7250-ixr-x4-osfp;

  feature platform-7250-j2;

  feature platform-7730-sxr-1-32d;

  feature platform-7730-sxr-1d-32d;

  feature platform-7730-sxr-1x-44s;

  feature platform-counter-bank-allocation {
    description
      "Support for managing the allocation of hardware counter banks";
  }

  feature platform-counter-bank-allocation-ip-tunnel-encap {
    description
      "Support for managing the allocation of hardware counter banks for originated GUE, MPLSoGRE, and MPLSoUDP tunnels";
  }

  feature platform-counter-bank-allocation-mep-opcode {
    description
      "Support for managing the allocation of hardware counter banks on per MEP OpCode basis";
  }

  feature platform-counter-bank-allocation-subintf-fc-policers-and-stats {
    description
      "Support for managing the allocation of hardware counter banks for fc policers on per subinterface basis and its associated stats";
  }

  feature platform-counter-bank-allocation-subintf-parent-policers-and-stats {
    description
      "Support for managing the allocation of hardware counter banks for parent policers on per subinterface basis and its associated stats";
  }

  feature platform-crimson;

  feature platform-dnx-lag-pool-management {
    description
      "Support for managing the allocation of hardware LAG pool resources for LAG IDs and member links reservation on DNX platforms";
  }

  feature platform-dynamic-subinterfaces {
    description
      "Support for managing the allocation of hardware resources for dynamic subinterfaces";
  }

  feature platform-group-based-policy {
    description
      "Support for platform group-based policy on MAC-VRF and IP-VRF network-instances";
  }

  feature platform-group-based-policy-ip-vrf {
    description
      "Support for platform group-based policy on IP-VRF network-instances";
  }

  feature platform-hash-polynomial-visibility {
    description
      "Support for state showing the hash polynomial used by each hash user";
  }

  feature platform-imgmt;

  feature platform-mdb-profile {
    description
      "Support for managing the allocation of hardware resources according to a Broadcom MDB profile";
  }

  feature platform-mdb-profile-3 {
    description
      "Support for managing the allocation of hardware resources according to MDB profile-3 on 7250 IXR Gen 2cp platforms. FID 10477.1";
  }

  feature platform-mdb-profile-4 {
    description
      "Support for managing the allocation of hardware resources according to MDB profile-4 on 7250 IXR Gen 3 platforms. FID 10477";
  }

  feature platform-sse-t81-64;

  feature platform-vsrl {
    description
      "VSRL platforms";
  }

  feature poe {
    description
      "Support for Power over Ethernet (PoE)";
  }

  feature policy-based-forwarding-decap-actions {
    description
      "Support for policy-based forwarding decap actions";
  }

  feature policy-based-forwarding-decapsulate-gre {
    description
      "Support for policy-based forwarding action: decapsulate GRE";
  }

  feature policy-based-forwarding-decapsulate-gre-ipv4-prefix-list {
    description
      "Support for policy-based forwarding action: encapsulate GRE with ipv4-prefix-list support";
  }

  feature policy-based-forwarding-decapsulate-gre-ipv6-prefix-list {
    description
      "Support for policy-based forwarding action: encapsulate GRE with ipv6-prefix-list support";
  }

  feature policy-based-forwarding-decapsulate-gue {
    description
      "Support for policy-based forwarding action: decapsulate GUE";
  }

  feature policy-based-forwarding-decapsulate-gue-ipv6 {
    description
      "Support for policy-based forwarding action: decapsulate GUE with ipv6 match support";
  }

  feature policy-based-forwarding-decapsulate-gue-ipv6-prefix-list {
    description
      "Support for policy-based forwarding action: decapsulate GUE with ipv6-prefix-list support";
  }

  feature policy-based-forwarding-decapsulate-ip-in-ip {
    description
      "Support for policy-based forwarding action: decapsulate IP-in-IP";
  }

  feature policy-based-forwarding-decapsulate-mpls-udp {
    description
      "Support for policy-based forwarding action: decapsulate MPLS in UDP";
  }

  feature policy-based-forwarding-decapsulate-mpls-udp-ipv6-prefix-list {
    description
      "Support for policy-based forwarding action: decapsulate MPLS in UDP with ipv6-prefix-list support";
  }

  feature policy-based-forwarding-down-override {
    description
      "Support for overriding the the PF's effective action when the target is down.";
  }

  feature policy-based-forwarding-down-override-action-nh {
    description
      "Support for overriding the the PF's effective action for action NH when the target is down.";
  }

  feature policy-based-forwarding-down-override-action-nhg {
    description
      "Support for overriding the the PF's effective action for action NHG when the target is down.";
  }

  feature policy-based-forwarding-dscp-ip-protocol {
    description
      "Support for policy-based forwarding based on DSCP and/or IP protocol";
  }

  feature policy-based-forwarding-encapsulate-gre {
    description
      "Support for policy-based forwarding action: encapsulate GRE";
  }

  feature policy-based-forwarding-match-action-type {
    description
      "PBF policy type that provides a superset of ACL, QoS and PBR actions";
  }

  feature policy-based-forwarding-match-address-family {
    description
      "Support for address-family selector in policy-forwarding match conditions";
  }

  feature policy-based-forwarding-match-ipv4-prefix-list {
    description
      "Support for policy-based forwarding match IPv4 prefix list";
  }

  feature policy-based-forwarding-match-ipv6-conditions {
    description
      "Support for policy-based forwarding match IPv6 conditions";
  }

  feature policy-based-forwarding-match-ipv6-prefix-list {
    description
      "Support for policy-based forwarding match IPv6 prefix list";
  }

  feature policy-based-forwarding-nh-transport {
    description
      "Support for policy-forwarding to next-hop and network-instance";
  }

  feature policy-based-forwarding-nhg {
    description
      "Support for policy-forwarding to next-hop-group";
  }

  feature port-breakout {
    description
      "Support for ethernet port breakout (port connector)";
  }

  feature port-capacity {
    description
      "Support for ingress and egress port capacity bps info";
  }

  feature port-fec-clause74 {
    description
      "Support for legacy base-r FEC";
  }

  feature port-groups {
    description
      "Support for port groups";
  }

  feature port-host-if-fec-enhanced-stats-router {
    description
      "Support for host interface FEC enhanced statistics from the router side";
  }

  feature port-host-if-fec-histogram-router {
    description
      "Support for host interface FEC histogram from the router side";
  }

  feature port-host-if-fec-stats-router {
    description
      "Support for host interface FEC statistics from the router side";
  }

  feature port-host-if-fec-stats-transceiver {
    description
      "Support for host interface FEC statistics from the transceiver side";
  }

  feature port-speed-1-6T {
    description
      "Support for 1.6T port speed";
  }

  feature port-speed-100G {
    description
      "Support for 100G ethernet port speed";
  }

  feature port-speed-100M {
    description
      "Support for 100M ethernet port speed";
  }

  feature port-speed-10G {
    description
      "Support for 10G ethernet port speed";
  }

  feature port-speed-10M {
    description
      "Support for 10M ethernet port speed";
  }

  feature port-speed-1G {
    description
      "Support for 1G ethernet port speed";
  }

  feature port-speed-1T {
    description
      "Support for 1T port speed";
  }

  feature port-speed-2-5G {
    description
      "Support for 2.5G ethernet port speed";
  }

  feature port-speed-200G {
    description
      "Support for 200G ethernet port speed";
  }

  feature port-speed-25G {
    description
      "Support for 25G ethernet port speed";
  }

  feature port-speed-400G {
    description
      "Support for 400G ethernet port speed";
  }

  feature port-speed-40G {
    description
      "Support for 40G ethernet port speed";
  }

  feature port-speed-50G {
    description
      "Support for 50G ethernet port speed";
  }

  feature port-speed-5G {
    description
      "Support for 5G ethernet port speed";
  }

  feature port-speed-800G {
    description
      "Support for 800G ethernet port speed";
  }

  feature power-management {
    description
      "Support for chassis power management";
  }

  feature pqc-support-ssh-crypt-functions {
    description
      "Support for PQC and configurable SSH cryptography functions";
  }

  feature protection-policies {
    description
      "Support for protection policies";
  }

  feature pseudowire {
    description
      "Support for pseudowires";
  }

  feature pseudowire-in-vpws {
    description
      "Support for pseudowires in vpws network-instances";
  }

  feature pseudowire-redundancy {
    description
      "Support for redundant pseudowires in network-instances";
  }

  feature qinq {
    description
      "Support for qinq subinterfaces";
  }

  feature qos {
    description
      "Support for qos";
  }

  feature qos-bank-stats-mode-ecn {
    description
      "Support for ecn in bank-stats-mode";
  }

  feature qos-classify-profile {
    description
      "Support for qos";
  }

  feature qos-committed-burst-size-table {
    description
      "Support for qos committed burst size";
  }

  feature qos-dcbx {
    description
      "Support for DCBX";
  }

  feature qos-dcbx-ets {
    description
      "support for DCBX ETS TLV";
  }

  feature qos-de-out-profile {
    description
      "Support for qos de out profile";
  }

  feature qos-discard-all-high-drop-probability {
    description
      "Support for the system-wide discard-all-high-drop-probability configuration";
  }

  feature qos-dot1p-classifier-policy {
    description
      "Support for qos dot1p classifier policy";
  }

  feature qos-dot1p-rewrite-policy {
    description
      "Support for qos dot1p rewrite policy";
  }

  feature qos-drop-probability {
    description
      "Support for qos drop probability";
  }

  feature qos-drop-zones {
    description
      "Support for qos drop zones";
  }

  feature qos-dscp-classifier-policy {
    description
      "Support for qos dscp classifier policy";
  }

  feature qos-dscp-reclassifier-policy {
    description
      "Support for qos dscp reclassifier policy";
  }

  feature qos-dscp-rewrite-policy {
    description
      "Support for qosdscp rewrite policy";
  }

  feature qos-ecn {
    description
      "Support for qos ecn";
  }

  feature qos-ecn-dscp-policy {
    description
      "Support for qos dscp policy";
  }

  feature qos-forwarding-class-index {
    description
      "Support for qos forwarding class index";
  }

  feature qos-forwarding-class-resource-priority {
    description
      "Support for qos forwarding class resource priority";
  }

  feature qos-forwarding-complexes {
    description
      "Support for qos forwarding complexes";
  }

  feature qos-fp-pool-policy {
    description
      "Support for qos forwarding class";
  }

  feature qos-global-policers {
    description
      "Support for qos global policers";
  }

  feature qos-input-class-map {
    description
      "Support for qos input class map";
  }

  feature qos-interface-pool-policy {
    description
      "Support for qos interface pool policy";
  }

  feature qos-ip-rewrite-policy {
    description
      "Support for qos ip rewrite policy";
  }

  feature qos-ipv4-dscp-classifier-policy {
    description
      "Support for qos ipv4 dscp classifier policy";
  }

  feature qos-ipv4-dscp-rewrite-policy {
    description
      "Support for qos ipv4 dscp rewrite policy";
  }

  feature qos-ipv6-dscp-classifier-policy {
    description
      "Support for qos ipv6 dscp classifier policy";
  }

  feature qos-ipv6-dscp-rewrite-policy {
    description
      "Support for qos ipv6 dscp rewrite policy";
  }

  feature qos-irb-subinterface {
    description
      "Support for qos on irb subinterface";
  }

  feature qos-lag-subinterface-queuing {
    description
      "Support for subinterface queuing on LAG";
  }

  feature qos-ler-use-dscp {
    description
      "Support for qos ler use dscp";
  }

  feature qos-management-protocols-dscp {
    description
      "Support for qos management protocols dscp";
  }

  feature qos-match-qinq-dot1p {
    description
      "Support for qos match qinq dot1p";
  }

  feature qos-mpls-classifier-policy {
    description
      "Support for qos mpls classifier policy";
  }

  feature qos-mpls-rewrite-policy {
    description
      "Support for qos mpls rewrite policy";
  }

  feature qos-multi-traffic-queue {
    description
      "Support for qos multi traffic queue";
  }

  feature qos-multicast-queue {
    description
      "Support for qos multicast queue";
  }

  feature qos-output-class-map {
    description
      "Support for qos output class map";
  }

  feature qos-packet-trimming {
    description
      "Support for qos packet trimming";
  }

  feature qos-packet-trimming-queue {
    description
      "Support for qos packet trimming on queue";
  }

  feature qos-pfc {
    description
      "Priority-based Flow Control (PFC) support";
  }

  feature qos-pfc-dnx {
    description
      "Priority-based Flow Control (PFC) support on DNX platforms, 7250 IXR-6e/10e and 7250 IXR-x1b/x3b  variants";
  }

  feature qos-pfc-headroom-buffer {
    description
      "Support of PFC Headroom buffer";
  }

  feature qos-pfc-peak-buffer {
    description
      "Peak pfc buffer usage on DNX platforms";
  }

  feature qos-pfc-received-traffic-mapping {
    description
      "Pfc received traffic mapping capability";
  }

  feature qos-pfc-threshold {
    description
      "Support of PFC Threshold";
  }

  feature qos-pfc-xgs {
    description
      "Priority-based Flow Control (PFC) support on XGS platforms, 7220 D5/D4 and 7220 H4 variants";
  }

  feature qos-policer-policies {
    description
      "Support for qos policer policies";
  }

  feature qos-policers-subtree {
    description
      "Support for the qos policers subtree";
  }

  feature qos-pre-classifier {
    description
      "Support for pre-classfication table";
  }

  feature qos-preserve-dscp {
    description
      "Support for qos preserve dscp";
  }

  feature qos-queue-block-size {
    description
      "Support for queue-block-size";
  }

  feature qos-queue-burst-delay {
    description
      "Support for qos queue burst to be expressed as a delay time";
  }

  feature qos-queue-cbs-adaptation-rule {
    description
      "Support for qos cbs adaptation rule";
  }

  feature qos-queue-committed-burst-size {
    description
      "Support for qos queue committed burst size";
  }

  feature qos-queue-depth-sampling {
    description
      "Support for qos queue depth sampling";
  }

  feature qos-queue-ecn-stats {
    description
      "Support for per-forwarding-class per port ECN statistics";
  }

  feature qos-queue-high-threshold {
    description
      "Support for qos queue high threshold";
  }

  feature qos-queue-management-profile {
    description
      "Support for qos queue management profile";
  }

  feature qos-queue-mbs-adaptation-rule {
    description
      "Support for qos queue mbs adaptation rule ";
  }

  feature qos-queue-profile-stats {
    description
      "Support for qos queue profile stats";
  }

  feature qos-queue-scheduling-class {
    description
      "Support for qos queue scheduling class";
  }

  feature qos-queue-scheduling-policy {
    description
      "Support for qos queue scheduling policy";
  }

  feature qos-resource-management {
    description
      "Support for qos resource management";
  }

  feature qos-resource-utilization-thresholds {
    description
      "Support for qos resource utilization thresholds";
  }

  feature qos-rewrite-dot1p {
    description
      "Support for qos rewrite dot1p";
  }

  feature qos-rewrite-inner-de {
    description
      "Support for qos rewrite  inner de";
  }

  feature qos-rewrite-inner-dot1p {
    description
      "Support for qos rewrite inner dot1p";
  }

  feature qos-rewrite-outer-de {
    description
      "Support for qos rewrite outer de";
  }

  feature qos-rewrite-outer-dot1p {
    description
      "Support for qos rewrite outer dot1p";
  }

  feature qos-rewrite-profile {
    description
      "Support for qos rewrite profile";
  }

  feature qos-sched-class-scheduling-policy {
    description
      "Support for qos sched class scheduling policy";
  }

  feature qos-scheduler-output-weight {
    description
      "Support for qos scheduler output weight";
  }

  feature qos-scheduler-policies {
    description
      "Support for scheduler policies";
  }

  feature qos-scheduling-priority-mapping {
    description
      "Support for qos scheduling priority mapping";
  }

  feature qos-show-interfaces-mismatch {
    description
      "Support for show qos interfaces mismatch";
  }

  feature qos-slope-policy {
    description
      "Support for qos slope policy";
  }

  feature qos-subinterface-dot1p-rewrite {
    description
      "Support for qos subinterface dot1p rewrite";
  }

  feature qos-subinterface-dscp-rewrite {
    description
      "Support for qos subinterface dscp rewrite";
  }

  feature qos-subinterface-members {
    description
      "Support for per subinterface member instance state";
  }

  feature qos-subinterface-policing {
    description
      "Support for subinterface policing";
  }

  feature qos-subinterface-queue-type {
    description
      "Support for qos subinterface queue type";
  }

  feature qos-subinterface-queuing {
    description
      "Support for subinterface queuing";
  }

  feature qos-system-generated-traffic-map {
    description
      "Support for qos system generated traffic map";
  }

  feature qos-tos-rewrite {
    description
      "Support for qos tos rewrite";
  }

  feature qos-traffic-management-mode {
    description
      "Support for traffic-management-mode";
  }

  feature qos-triggered-queue-depth-sampling {
    description
      "Support for high-threshold triggered queue-depth sampling";
  }

  feature qos-trunk-pool-policy {
    description
      "Support for qos buffer-management trunk-pool-policy";
  }

  feature qos-unicast-queue {
    description
      "Support for qos unicast queue";
  }

  feature qos-virtual-interface {
    description
      "Support for egress virtual interface";
  }

  feature qos-virtual-output-queue {
    description
      "Support for qos virtual output queue";
  }

  feature qos-voq-stats-enable {
    description
      "Support for qos virtual output queue stats enable";
  }

  feature qos-vxlan-classifier-policy {
    description
      "Support for qos vxlan classifier policy";
  }

  feature qos-vxlan-outer-header-rewrite {
    description
      "Support for qos vxlan outer header rewrite";
  }

  feature qos-wred-traffic-type-tcp {
    description
      "Support for qos wred traffic type tcp/non-tcp";
  }

  feature qumran2cp;

  feature qumran3d;

  feature ra-guard {
    description
      "Support for ra guard";
  }

  feature radius-source-address {
    description
      "Support for configurable source address for radius servers";
  }

  feature radius-tls {
    description
      "Support for exchanging RADIUS messages over a TLS connection";
  }

  feature redundant-cpms {
    description
      "Support for any platform with redundant CPMs";
  }

  feature reload-delay {
    description
      "Support for interface reload-delay timers";
  }

  feature restore-sdcard {
    description
      "Support operational commands related to restoration of a SD card";
  }

  feature route-leaking {
    description
      "Support for inter network-instance route leaking";
  }

  feature route-table-show-report-improvements {
    description
      "Support for route table show report improvements";
  }

  feature router-advertisement-rdnss-option {
    description
      "Support for router advertisement rdnss option";
  }

  feature routing-policy-bgp-disable-fib {
    description
      "Support for disabling FIB download for BGP routes matched by import policy as a route policy action";
  }

  feature routing-policy-bgp-flex-algo-next-hop-resolution-action {
    description
      "support for set-flex-algo action in route-policy";
  }

  feature routing-policy-bgp-local-pref-add-subtract {
    description
      "Support for incrementing or decrementing the BGP local pref using new route policy model";
  }

  feature routing-policy-bgp-local-pref-set {
    description
      "Support for setting BGP local pref using new route policy model";
  }

  feature routing-policy-bgp-med {
    description
      "Support for MED in BGP and routing policy actions";
  }

  feature routing-policy-bgp-next-hop-resolution-action {
    description
      "Support for modifying the BGP next-hop resolution constraints as a route policy action";
  }

  feature routing-policy-bgp-next-hop-self-action {
    description
      "Support for next-hop self as a policy action";
  }

  feature routing-policy-bgp-next-hop-set-action {
    description
      "Support for modifying the BGP next-hop address as a route policy action";
  }

  feature routing-policy-bgp-srte-policy {
    description
      "Support for match and action specific to BGP SR policy routes";
  }

  feature routing-policy-community-match-set-options {
    description
      "Support for community-set match-set-options: any, all and invert";
  }

  feature routing-policy-conditional-statements {
    description
      "Support for routing policy conditional statements";
  }

  feature routing-policy-enhanced-as-path-set {
    description
      "Support for as-path-member-set-member, character-mode regex and complete match-set-options";
  }

  feature routing-policy-extended-community-actions {
    description
      "Support for extended community actions aligned with OC";
  }

  feature routing-policy-extended-community-sets {
    description
      "Support for extended-community-set construct";
  }

  feature routing-policy-gribi-route-type {
    description
      "gRIBI as a protocol match in table-connection and other routing-policy types";
  }

  feature routing-policy-isis-actions {
    description
      "Support for ISIS policy actions";
  }

  feature routing-policy-match-protocol-redefine {
    description
      "Redefine supported match protocols in routing policy";
  }

  feature routing-policy-named-statements {
    description
      "Support for named statements in routing policy";
  }

  feature routing-policy-next-policy {
    description
      "Support for next-policy as a route policy action";
  }

  feature routing-policy-next-statement {
    description
      "Support for next-statement as a route policy action";
  }

  feature routing-policy-ospf-actions {
    description
      "Support for OSPF route policy actions";
  }

  feature routing-policy-preference-action {
    description
      "Support for route policy action to set preference";
  }

  feature routing-policy-prefix-set-match-options-any {
    description
      "Support for match-set-options any with prefix-set";
  }

  feature routing-policy-prefix-set-match-options-invert {
    description
      "Support for match-set-options invert with prefix-set";
  }

  feature routing-policy-resilient-hash-action {
    description
      "Support for enabling or disabling resilient hashing as an explicit policy action";
  }

  feature routing-policy-standard-community-actions {
    description
      "Support for standard community actions aligned with OC";
  }

  feature routing-policy-standard-community-sets {
    description
      "Support for standard-community-set construct";
  }

  feature routing-policy-subroutines {
    description
      "Support for route policy subroutines";
  }

  feature routing-policy-table-connections {
    description
      "Support for network-instance table connections for route redistribution";
  }

  feature routing-policy-tag-set-match-options {
    description
      "Support for match-set-options with tag-sets";
  }

  feature rsvp {
    description
      "Support for base RSVP protocol and RSVP-TE LSPs";
  }

  feature sbfd-return-label {
    description
      "Support for Seamless BFD, controlled (a.k.a. labeled) return";
  }

  feature seamless-bfd {
    description
      "Support Seamless BFD for SR segment lists";
  }

  feature secure-boot {
    description
      "Support for Secure Boot";
  }

  feature segment-routing {
    description
      "Support for segment routing using the MPLS dataplane";
  }

  feature segment-routing-adjacency-sid {
    description
      "Support for segment routing adjacency sid";
  }

  feature segment-routing-colored-te-policies {
    description
      "Support for colored segment routing TE policies";
  }

  feature segment-routing-isis-lsp-stats {
    description
      "Support for segment routing LSP stats in ISIS";
  }

  feature segment-routing-shared-sid {
    description
      "Support for segment routing shared sid";
  }

  feature segment-routing-shared-sid-lsp-stats {
    description
      "Support for segment routing shared sid lsp stats";
  }

  feature service-activation-testhead {
    description
      "Support of Service Activation TestHead (SAT) / Y.1564 feature";
  }

  feature sflow {
    description
      "Support for Sflow";
  }

  feature sflow-collector-dscp {
    description
      "Support for configuring DSCP per Sflow collector";
  }

  feature sflow-gnpsi-interface {
    description
      "gNPSI export for sFlow";
  }

  feature sflow-gue-packets {
    description
      "sFlow sampling for GUE packets (post encap, pre decap)";
  }

  feature sflow-interface-sampling {
    description
      "Support for Sflow Egress and Ingress sampling on interface level";
  }

  feature sflow-ipv6-udp-cksum-knob {
    description
      "Support for config knob to set checksum to 0x0 or 0xFFFF in Sflow IPv6 UDP packets";
  }

  feature sflow-lag {
    description
      "Support Sflow for LAG/aggregate type of interfaces";
  }

  feature sflow-system-egress-sample-rate {
    description
      "Support System Sflow Egress sample rate on Hx platforms";
  }

  feature show-acl-aclfilter {
    description
      "Support for new show acl acl-filter reports";
  }

  feature snmp {
    description
      "Support for SNMP";
  }

  feature snmp-counters {
    description
      "Support for SNMP packet counters";
  }

  feature snmp-over-tcp {
    description
      "Support for SNMP over TCP";
  }

  feature snmp-tools-trap {
    description
      "Support for sending SNMP Traps with a tools command";
  }

  feature snmp-traps {
    description
      "Support for SNMP traps";
  }

  feature snmp-v3 {
    description
      "Support for SNMPv3";
  }

  feature special-ptp-ip-timestamping {
    description
      "Support disabling of L3 timestamping";
  }

  feature srv6 {
    description
      "Support for Segment Routing with SRv6 dataplane";
  }

  feature srv6-dt2 {
    description
      "Support for SRv6 DT2U and DT2M services";
  }

  feature srv6-usid-basic {
    description
      "Support for basic SRv6 micro sid support";
  }

  feature ssh-rekey-threshold {
    description
      "Support for SSH rekey threshold configuration";
  }

  feature stamp {
    description
      "Support for Simple Two-way Active Measurement Protocol STAMP";
  }

  feature stamp-ipv6-mpls-dnx {
    description
      "Support on DNX for timestamping IPv6 o MPLS packets";
  }

  feature stat-interface-link-transitions {
    description
      "Support for interface and link transitions interface statistics";
  }

  feature static-next-hop-cpe {
    description
      "Support for CPE checks on static next-hops";
  }

  feature static-next-hop-group-backup {
    description
      "Support for floating static routes based on backup NHG";
  }

  feature static-next-hop-group-gre-tunnel {
    description
      "Support GRE tunnel next-hops in static NHGs";
  }

  feature static-next-hop-mpls-over-gre {
    description
      "Support for MPLS over GRE encapsiulation in static NHs";
  }

  feature static-next-hop-unnumbered-interface {
    description
      "Support for IP-unnumbered interfaces as next-hops in static NHGs";
  }

  feature static-next-hop-unnumbered-mpls {
    description
      "Support for MPLS with IP-unnumbered next-hops in static NHGs";
  }

  feature static-nhg-nh-reference {
    description
      "Support for static NHGs with reusable next-hop references";
  }

  feature static-nhg-udp-tunnel {
    description
      "Support for UDPv4 tunnel encap in static next-hops";
  }

  feature static-route-group-based-policy {
    description
      "Support for association of a static route with a group-based-policy tag";
  }

  feature static-route-tag-set {
    description
      "Support for association of a static route with a configured tag-set";
  }

  feature static-route-tag-value {
    description
      "Support for association of a static route with a configured tag value";
  }

  feature storm-control {
    description
      "Support for storm control";
  }

  feature storm-control-action {
    description
      "Support for storm control threshold action";
  }

  feature stp {
    description
      "Support for xSTP";
  }

  feature strict-request-path-verification {
    description
      "Support for strict request path verification";
  }

  feature subif-acl-policer {
    description
      "Support for ACL rate-limit action for sub interfaces";
  }

  feature subif-detailed-stats-config {
    description
      "Support for configuring subinterface detailed stats";
  }

  feature subif-ip-tags {
    description
      "Support for assignment of admin tags to IP subnets";
  }

  feature subif-policer {
    description
      "Support for sub interface policer";
  }

  feature subif-stats-per-ipv4-ipv6-container {
    description
      "Support for sub interface stats in ipv4 and ipv6 containers";
  }

  feature submgmt-fpcx {
    description
      "Subscriber management on fpcx";
  }

  feature subscriber-management {
    description
      "Support for subscriber management";
  }

  feature sync {
    description
      "Support for PTP, SyncE, BITS, ToD, 1PPSTEST";
  }

  feature sync-gnss {
    description
      "Support for GNSS receiver module";
  }

  feature sync-gnss-faster-start {
    description
      "Support for capability for faster start-up and restart-up time for the GNSS receiver";
  }

  feature sync-gnss-redundant {
    description
      "Support for GNSS redundant receivers";
  }

  feature sync-gnss-within-holdover {
    description
      "Configuration time duration for clock class 7 and 135 when entering holdover";
  }

  feature sync-one-pps {
    description
      "Support for 1PPS timing port";
  }

  feature sync-ptp-apts {
    description
      "Support for PTP APTS";
  }

  feature sync-ptp-freq {
    description
      "Support for recovery of frequency from the PTP messages.  Profiles G.8275.2 and G.8265.1";
  }

  feature sync-ptp-ip-peers {
    description
      "Support for PTP peers using IP transport and unicast negotitation";
  }

  feature sync-ptp-ip-peers-ipv6 {
    description
      "Support for PTP peers using IPv6 transport and unicast negotitation";
  }

  feature sync-ptp-ip-port-tracking {
    description
      "Support for tracking of rx/tx ports for ptp over ip";
  }

  feature sync-ptp-max-steps-removed {
    description
      "Support configuration of max-steps-removed";
  }

  feature sync-ptp-reset {
    description
      "Clear the current state of the ptp time recovery engine and the ptp frequency recovery engine";
  }

  feature sync0-port {
    description
      "Platform includes a dedicated sync0 port for synce and ptp";
  }

  feature system-fallback-routing {
    description
      "Support for fallback routing by doing a secondary FIB lookup in default";
  }

  feature system-filter {
    description
      "Support for system filters";
  }

  feature system-fips-mode {
    description
      "Support for fips mode";
  }

  feature system-forwarding-mode {
    description
      "Support for configurable switching mode";
  }

  feature system-hash-l3-parser-seed-and-ethernet {
    description
      "Support for new hash options that can improve hashing performance";
  }

  feature system-hash-profile {
    description
      "Support for user-configurable hash profiles that can be applied to selected interfaces";
  }

  feature system-hash-seed-from-mac {
    description
      "Support for auto-generating a hash-seed from the base chassis MAC address";
  }

  feature system-resource-acl-ip-filter-instances-general {
    description
      "Support for general acl ip system utilization resources";
  }

  feature system-resource-acl-ip-filter-instances-routed-bridged {
    description
      "Support for routed/bridged acl ip system utilization resources";
  }

  feature system-resource-acl-ipv4-ipv6-filter-instances {
    description
      "Support for acl ip system utilization resources";
  }

  feature system-resource-acl-mac-filter-instances {
    description
      "Support for acl mac system utilization resources";
  }

  feature system-resource-ip-gre-tunnels {
    description
      "Support for system resource ip-gre-tunnels";
  }

  feature system-resource-ip-in-ip-tunnels {
    description
      "Support for system resource ip-in-ip-tunnels";
  }

  feature system-resource-mcast-rpf-indices {
    description
      "Support for P2MP Reverse Path Forwarding";
  }

  feature system-resource-mpls-next-hops {
    description
      "Support for system resource mpls-next-hops";
  }

  feature system-resource-multicast-ppmc-indices {
    description
      "Support for system resource multicast-ppmc-indices";
  }

  feature system-resource-pg-groups {
    description
      "Support for system resource pg-groups";
  }

  feature system-resource-tunnels {
    description
      "Support for system resource tunnels";
  }

  feature system-resource-utilization {
    description
      "Support for system resource utilization";
  }

  feature system-resource-utilization-acl {
    description
      "Support for system resource utilization acl";
  }

  feature system-resource-utilization-qos {
    description
      "Support for system resource utilization qos";
  }

  feature system-resource-vp-lag-groups {
    description
      "Support for system resource vp-lag-groups";
  }

  feature system-resource-vxlan-tunnels {
    description
      "Support for system resource vxlan-tunnels";
  }

  feature tacacs-source-address {
    description
      "Support for configurable source address for tacacs servers";
  }

  feature te-policies {
    description
      "Support for SR-TE and segment routing policies using the MPLS dataplane";
  }

  feature te-policies-admin-groups {
    description
      "Support for admin group for TE-Policy sr-mpls uncolored and FRR";
  }

  feature te-policies-entropy-label {
    description
      "Support for entropy label with SR-TE and segment routing policies";
  }

  feature te-policies-increased-label-stack-fpcx {
    description
      "Support for increased label stack with SR-TE and segment routing policies on 7730 SXR";
  }

  feature te-policies-tag-set {
    description
      "Support for tag-set with SR-TE and segment routing policies";
  }

  feature te-policy-colored-statistics {
    description
      "Support for Colored TE-Policy segment-list statistics";
  }

  feature te-policy-delay-metric-limit {
    description
      "Support for delay metric limit under TE-Policy";
  }

  feature te-policy-exclude-srlg {
    description
      "Support for exclude-srlg under TE-Policy";
  }

  feature te-policy-local-cspf-fallback {
    description
      "Support for local CSPF fallback under TE-Policy";
  }

  feature te-policy-pcep-delay-metric-limit {
    description
      "Support for PCEP delay metric limit under TE-Policy";
  }

  feature te-policy-statistics {
    description
      "Support for TE-Policy statistics";
  }

  feature tftp {
    description
      "Support for TFTP";
  }

  feature tls-cert-expiry {
    description
      "Add yang state and events for certificate expiration";
  }

  feature tls-server-profile-rename {
    description
      "Rename node .system.tls.server-profile to .system.tls.profile";
  }

  feature tomahawk3;

  feature tomahawk4;

  feature tomahawk5;

  feature tomahawk6;

  feature tools-as-modeled-actions-different-output {
    description
      "Support for tools migrated to modeled actions. Specific for models with a different output as before the migration.";
  }

  feature tools-as-modeled-actions-same-output {
    description
      "Support for tools migrated to modeled actions. Specific for models with the same output as before the migration or no output.";
  }

  feature tools-force-pwd-change {
    description
      "Support for tools commands to force users to change password";
  }

  feature tpm-1-2 {
    description
      "The platform may contain a TPM1.2 device";
  }

  feature tpm-2-0 {
    description
      "The platform may contain a TPM2.0 device";
  }

  feature tpm-attestz {
    description
      "Support for TPM Attestz";
  }

  feature tpm-enrollz {
    description
      "Support for TPM Enrollz";
  }

  feature tpm-idevid {
    description
      "Support for TPM IDevID";
  }

  feature tpm-oidevid {
    description
      "Support for TPM OIDevID certificate in tls profile";
  }

  feature traffic-engineering {
    description
      "Support for TE advertisement by ISIS";
  }

  feature traffic-engineering-bgpls {
    description
      "Support for BGP-LS advertisement of IGP link-state data";
  }

  feature traffic-engineering-bgpls-directly-connected {
    description
      "Support for BGP-LS advertisement of directly connected link-state data";
  }

  feature traffic-engineering-isis-tedb-install {
    description
      "Support for TE DB by ISIS";
  }

  feature traffic-engineering-ospf {
    description
      "Support for TE DB, BGP-LS and TE advertisement by OSPF";
  }

  feature transceiver-cdb-capabilities {
    description
      "Support for reporting transceiver CDB capabilities";
  }

  feature transceiver-firmware-upgrade {
    description
      "Support for transceiver firmware upgrade";
  }

  feature transceiver-firmware-upgrade-oif {
    description
      "Support for transceiver firmware upgrade based on OIF 2025 package mechanism";
  }

  feature transceiver-firmware-version {
    description
      "Support for transceiver firmware version";
  }

  feature transceiver-link-length-info {
    description
      "Support for transceiver link length info";
  }

  feature transceiver-removal {
    description
      "Support for simulated transceiver removal";
  }

  feature transceiver-reset {
    description
      "Support for transceiver reset";
  }

  feature trident3;

  feature trident4;

  feature twamp {
    description
      "Support for TWAMP";
  }

  feature tx-flow-control {
    description
      "Support for transmitting Ethernet flow control (PAUSE) frames";
  }

  feature udp-tunnel {
    description
      "Support for UDP tunnel";
  }

  feature unequal-ecmp {
    description
      "Support for unequal Equal Cost Multi Path";
  }

  feature unicast-rpf-check {
    description
      "Support for source address validation using unicast RPF check";
  }

  feature unified-forwarding-tables {
    description
      "Support for UFT resources";
  }

  feature unified-forwarding-tables-mode {
    description
      "Support for UFT resources mode field";
  }

  feature unified-forwarding-tables-mode-2 {
    description
      "Support for UFT resources mode enum 2";
  }

  feature virtual-ip-discovery {
    description
      "Support for arp/nd virtual ip discovery";
  }

  feature vlan-id-any {
    description
      "Support for configurable vlan-id any";
  }

  feature vlan-id-optional {
    description
      "Support for configurable vlan-id optional";
  }

  feature vlan-loopback {
    description
      "Support for configurable vlan loopback with optional mac swap";
  }

  feature vlan-manipulation {
    description
      "Support for configurable vlan manipulation";
  }

  feature vlan-tpid {
    description
      "Support for configurable VLAN Tagging TPID";
  }

  feature vpws {
    description
      "Support for VPWS Services";
  }

  feature vrrp {
    description
      "Support for VRRP";
  }

  feature vsrl {
    description
      "VSRL common features";
  }

  feature vsrl-generic-hw {
    description
      "VSRL gen1 specific features";
  }

  feature vxlan {
    description
      "Support for VXLAN";
  }

  feature vxlan-stats {
    description
      "Support for VXLAN statistics";
  }

  feature vxlan-v6 {
    description
      "Support for IPV6 VXLAN";
  }

  feature warm-reboot {
    description
      "Support for warm reboot";
  }

  feature xdp-restart-unsupported {
    description
      "Restart of xdp application not supported, unified-forwarding-tables changes require chassis reboot";
  }

  feature ztp-boot-mode {
    description
      "Support for ztp-boot mode";
  }

}
