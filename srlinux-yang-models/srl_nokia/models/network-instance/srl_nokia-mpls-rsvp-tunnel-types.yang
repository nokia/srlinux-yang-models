module srl_nokia-mpls-rsvp-tunnel-types {
  yang-version 1.1;
  namespace "urn:nokia.com:srlinux:mpls:mpls-rsvp-tunnel-types";
  prefix srl_nokia-mpls-rsvp-tunnel-types;

  import srl_nokia-common {
    prefix srl_nokia-comm;
  }

  organization
    "Nokia";
  contact
    "Nokia SR Linux Support
     Web: <http://www.nokia.com>";
  description
    "This YANG module defines the common data types used by the Resource reSerVation Protocol (RSVP).";

  revision 2026-07-31 {
    description
      "SRLinux 26.7.1";
  }

  typedef tunnel-name {
    type srl_nokia-comm:name {
      length "1..64";
    }
    description
      "TE Tunnel name.";
  }

  typedef path-name {
    type srl_nokia-comm:name {
      length "1..64";
    }
    description
      "Path name.";
  }

  typedef p2p-path-name {
    type srl_nokia-comm:name {
      length "1..64";
    }
    description
      "P2P Path name.";
  }

  typedef frr-method-type {
    type enumeration {
      enum facility {
        value 1;
      }
    }
    description
      "Specifies the type for fast-reroute method.";
  }

  typedef hop-limit {
    type uint32 {
      range "2..255";
    }
    description
      "Specifies the hop limit for the tunnel.";
  }

  typedef path-bandwidth {
    type uint32 {
      range "0..6400000";
    }
    units "megabps";
    description
      "Specifies the maximum bandwidth for the LSP.";
  }

  typedef priority {
    type int32 {
      range "0..7";
    }
    description
      "Specifies the priority.";
  }
}
