module srl_nokia-tools-te-policies {
  yang-version 1.1;
  namespace "urn:nokia.com:srlinux:tepolicy:tools-te-policies";
  prefix srl_nokia-tools-te-policies;

  import srl_nokia-common {
    prefix srl_nokia-comm;
  }
  import srl_nokia-tools-network-instance {
    prefix srl_nokia-tools-netinst;
  }
  import srl_nokia-features {
    prefix srl_nokia-feat;
  }

  organization
    "Nokia";
  contact
    "Nokia SR Linux Support
     Web: <http://www.nokia.com>";
  description
    "Model for Taffic Engineering Policies operational commands";

  revision 2026-07-31 {
    description
      "SRLinux 26.7.1";
  }
  revision 2025-07-31 {
    description
      "SRLinux 25.7.1";
  }
  revision 2025-03-31 {
    description
      "SRLinux 25.3.1";
  }
  revision 2024-10-31 {
    description
      "SRLinux 24.10.1";
  }
  revision 2023-07-31 {
    description
      "SRLinux 23.7.1";
  }

  grouping te-policies-tools-top {
    container traffic-engineering-policies {
      if-feature "srl_nokia-feat:te-policies";
      container sr-uncolored {
        list policy {
          description
            "List of traffic engineering policies";
          key "policy-name protocol-origin";
          leaf policy-name {
            description
              "The name of the traffic engineering policy";
            type srl_nokia-comm:name;
          }
          leaf protocol-origin {
            description
              "Uncolored Traffic Enginering Policy, origination source. The method Policy path is computed. This list includes Path Computation Engine, explicitly configured paths, etc.";
            type srl_nokia-comm:protocol-origin-type;
          }
          container statistics {
            if-feature "srl_nokia-feat:te-policy-statistics";
            description
              "Enter the statistics context

               TE Policy Statistics tools options";
            container ingress {
              description
                "Enter the ingress context

                 TE Policy ingress statistics";
              leaf clear {
                type empty;
                description
                  "Clear TE Policy ingress statistics";
              }
            }
            container egress {
              description
                "Enter the egress context

                 TE Policy egress statistics";
              leaf clear {
                type empty;
                description
                  "Clear TE Policy egress statistics";
              }
            }
          }
          must "./protocol-origin = 'local'" {
            error-message "only local uncolored policies are supported";
          }
          list segment-list {
            key "segment-list-index";
            leaf segment-list-index {
              description
                "Index to enumerate the different segment lists of a TE policy.";
              type uint8 {
                range "1..32";
              }
            }
            leaf resignal {
              type empty;
              description
                "Trigger resignal for segment-list ";
            }
            leaf clear {
              type empty;
              description
                "Clear segment-list";
            }
          }
        }
        description
          "Enter the sr-uncolored context";
      }
      container sr-colored {
        if-feature "srl_nokia-feat:te-policy-colored-statistics";
        list policy {
          key "color endpoint";
          leaf color {
            type uint32;
            description
              "Name of Colored Traffic Engineering Policy to be traced. Any programmed candidate-path can be traced.";
          }
          leaf endpoint {
            type srl_nokia-comm:ip-address-unicast-without-local;
            description
              "Colored Traffic Engineering Policy, endpoint IP address.";
          }
          container statistics {
            if-feature "srl_nokia-feat:te-policy-colored-statistics";
            description
              "Enter the statistics context

               TE Policy Statistics tools options";
            container ingress {
              description
                "Enter the ingress context

                 TE Policy egress statistics";
              leaf clear {
                type empty;
                description
                  "Clear TE Policy egress statistics";
              }
            }
          }
          list candidate-path {
            description
              "SR policy candidate paths. This list includes local static policies, but only those that have both a color and endpoint.";
            key "protocol-origin discriminator originator-asn originator-address";
            leaf protocol-origin {
              type srl_nokia-comm:protocol-origin-type;
              description
                "Instantiation mechanism used to create the candidate path";
            }
            leaf originator-asn {
              type uint32;
              description
                "Autonomous System (ASN) Identifier of the node that signalled/instantiated the candidate path on headend";
            }
            leaf originator-address {
              type srl_nokia-comm:ip-address;
              description
                "IP address Identifier of the node that signalled/instantiated the candidate path on headend";
            }
            leaf discriminator {
              type uint32;
              description
                "Candidate path discriminator";
            }
            list segment-list {
              key "segment-list-index";
              leaf segment-list-index {
                description
                  "Index to enumerate the different segment lists of a TE policy.";
                type uint8 {
                  range "1..32";
                }
              }
              container statistics {
                if-feature "srl_nokia-feat:te-policy-colored-statistics";
                description
                  "Enter the statistics context

                   TE Policy Statistics tools options";
                container egress {
                  description
                    "Enter the egress context

                     TE Policy egress statistics";
                  leaf clear {
                    type empty;
                    description
                      "Clear TE Policy egress statistics";
                  }
                }
              }
            }
          }
        }
        description
          "Enter the sr-colored context";
      }
      description
        "Enter the traffic-engineering-policies context";
    }
  }

  augment "/srl_nokia-tools-netinst:network-instance" {
    uses te-policies-tools-top;
  }
}
