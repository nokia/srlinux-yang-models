module srl_nokia-tools-connection-point-bridge-table-mac-duplication {
  yang-version 1.1;
  namespace "urn:nokia.com:srlinux:l2-mac:tools-connection-point-bridge-table-mac-duplication";
  prefix srl_nokia-tools-connection-point-bridge-table-mac-duplication;

  import srl_nokia-tools-network-instance {
    prefix srl_nokia-tools-netinst;
  }
  import srl_nokia-tools-interfaces-bridge-table-mac-duplication {
    prefix srl_nokia-tools-interfaces-bridge-table-mac-duplication;
  }
  import srl_nokia-common {
    prefix srl_nokia-comm;
  }

  organization
    "Nokia";
  contact
    "Nokia SR Linux Support
     Web: <http://www.nokia.com>";
  description
    "Model for connection-point bridge-table mac duplication operational commands";

  revision 2024-03-31 {
    description
      "SRLinux 24.3.1";
  }

  augment "/srl_nokia-tools-netinst:network-instance/srl_nokia-tools-netinst:connection-point/srl_nokia-tools-netinst:bridge-table" {
    uses srl_nokia-tools-interfaces-bridge-table-mac-duplication:tools-bridge-table-mac-duplication-top;
  }
}
