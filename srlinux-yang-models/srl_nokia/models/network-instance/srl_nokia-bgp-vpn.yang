module srl_nokia-bgp-vpn {
  yang-version 1.1;
  namespace "urn:nokia.com:srlinux:bgp:bgp-vpn";
  prefix srl_nokia-bgp-vpn;

  import srl_nokia-common {
    prefix srl_nokia-comm;
  }
  import srl_nokia-features {
    prefix srl_nokia-feat;
  }
  import srl_nokia-network-instance {
    prefix srl_nokia-netinst;
  }
  import srl_nokia-bgp {
    prefix srl-bgp;
  }
  import srl_nokia-extensions {
    prefix srl_nokia-ext;
  }
  import srl_nokia-policy-types {
    prefix srl_nokia-pol-types;
  }
  import srl_nokia-routing-policy {
    prefix srl-rpol;
  }

  organization
    "Nokia";
  contact
    "Nokia SR Linux Support
     Web: <http://www.nokia.com>";
  description
    "This yang file models configuration and state of the bgp-vpn protocols (EVPN and IPVPN).";

  revision 2026-07-31 {
    description
      "SRLinux 26.7.1";
  }
  revision 2026-03-31 {
    description
      "SRLinux 26.3.1";
  }
  revision 2025-10-31 {
    description
      "SRLinux 25.10.1";
  }
  revision 2025-07-31 {
    description
      "SRLinux 25.7.1";
  }
  revision 2025-03-31 {
    description
      "SRLinux 25.3.1";
  }
  revision 2024-10-31 {
    description
      "SRLinux 24.10.1";
  }
  revision 2024-07-31 {
    description
      "SRLinux 24.7.1";
  }
  revision 2024-03-31 {
    description
      "SRLinux 24.3.1";
  }
  revision 2023-10-31 {
    description
      "SRLinux 23.10.1";
  }
  revision 2022-06-30 {
    description
      "SRLinux 22.6.1";
  }
  revision 2021-03-31 {
    description
      "SRLinux 21.3.1";
  }

  grouping bgp-vpn-top {
    description
      "Top-level grouping containing a list of bgp-vpn instances.";
    container bgp-vpn {
      if-feature "srl_nokia-feat:evpn or srl_nokia-feat:ipvpn";
      description
        "Top-level configuration and operational state for common bgp-ipvpn and bgp-evpn parameters";
      presence "Configuration and state of bgp-vpn.";
      must '(/srl_nokia-netinst:network-instance[srl_nokia-netinst:name = current()/../../srl_nokia-netinst:name]/srl_nokia-netinst:type != "srl_nokia-netinst:default")' {
        error-message "The bgp-vpn configuration is not possible on network-instance of type default.";
      }
      must '(/srl_nokia-netinst:network-instance[srl_nokia-netinst:name = current()/../../srl_nokia-netinst:name]/srl_nokia-netinst:type != "srl_nokia-netinst:host")' {
        error-message "The bgp-vpn configuration is not possible on network-instance of type host.";
      }
      leaf next-hop-resolution-policy {
        if-feature "srl_nokia-feat:bgp-next-hop-resolution-policy";
        description
          "Policy to evaluate whether the route or tunnel chosen to resolve each BGP next-hop is acceptable or not

           The policy applies to all BGP EVPN and IPVPN routes imported into the network-instance, and covers both IPv4 next-hop addresses and IPv6 next-hop addresses.";
        type leafref {
          path "/srl-rpol:routing-policy/srl-rpol:policy/srl-rpol:name";
        }
        must "current()/../../../srl_nokia-netinst:type != 'srl_nokia-netinst:vpws' and current()/../../../srl_nokia-netinst:type != 'srl_nokia-netinst:mac-vrf'" {
          error-message "next-hop-resolution-policy cannot be configured in network-instances of type vpws or mac-vrf";
        }
      }
      container backup-paths {
        if-feature "srl_nokia-feat:bgp-backup-path-frr-vpn or srl_nokia-feat:bgp-backup-path-frr-evpn";
        description
          "Enter the backup-paths context

           Configuration of BGP VPN fast reroute";
        container ipv4-unicast {
          description
            "Enter the ipv4-unicast context

             Configuration of IPv4 unicast backup paths";
          leaf install {
            type boolean;
            default "false";
            description
              "Install a backup path for every NLRI in the address family, when a suitable one exists";
            must ". = false() or current()/../../../../../srl_nokia-netinst:type = 'srl_nokia-netinst:ip-vrf'" {
              error-message "backup-paths can only be installed in network-instances of type ip-vrf";
            }
            must '. = false() or not (current()/../../../../../srl_nokia-netinst:protocols/srl_nokia-netinst:bgp-evpn)' {
              srl_nokia-ext:if-feature "not srl_nokia-feat:bgp-backup-path-frr-evpn";
              error-message "backup-paths not supported when EVPN is configured";
            }
          }
        }
        container ipv6-unicast {
          description
            "Enter the ipv6-unicast context

             Configuration of IPv6 unicast backup paths";
          leaf install {
            type boolean;
            default "false";
            description
              "Install a backup path for every NLRI in the address family, when a suitable one exists";
            must ". = false() or current()/../../../../../srl_nokia-netinst:type = 'srl_nokia-netinst:ip-vrf'" {
              error-message "backup-paths can only be installed in network-instances of type ip-vrf";
            }
            must '. = false() or not (current()/../../../../../srl_nokia-netinst:protocols/srl_nokia-netinst:bgp-evpn)' {
              srl_nokia-ext:if-feature "not srl_nokia-feat:bgp-backup-path-frr-evpn";
              error-message "backup-paths not supported when EVPN is configured";
            }
          }
        }
      }
      container combined-ecmp {
        if-feature "srl_nokia-feat:combined-bgp-ecmp";
        presence "Enable the combination of BGP PE-CE, EVPN IFL and/or VPN-IP routes into the same ECMP set";
        description
          "Combine BGP owners into the same ECMP set

           When enabled, candidate BGP PE-CE routes and BGP VPN routes (EVPN IFL or VPN-IP) to the same prefix are
           combined into a single ECMP set. A single route with a combined next hop group is installed in the
           route table. If different BGP owners are combined and have different configured ecmp maximum values,
           the minimum of the maximum configured values is considered for the combined ECMP set.";
        must "current()/../../../srl_nokia-netinst:type = 'srl_nokia-netinst:ip-vrf'" {
          error-message "combined BGP ECMP can only be enabled in network-instances of type ip-vrf";
        }
        must 'not(../allow-export)' {
          error-message "combined BGP ECMP and allow-export cannot be configured at the same time";
        }
      }
      container allow-export {
        if-feature "srl_nokia-feat:bgp-vpn-allow-export";
        presence "Enable reexport of EVPN IFL or VPN-IP routes";
        description
          "Allow re-export of EVPN IFL or VPN-IP routes

           When this feature is enabled, received EVPN IFL routes or VPN-IP routes are re-exported to the
           configured BGP peers. In IP-VRF network instances that contain both a bgp-evpn and a bgp-ipvpn instance,
           EVPN IFL routes are automatically re-exported to the BGP-IPVPN instance without requiring this command.
           Similarly, IPVPN routes are automatically re-exported to the BGP-EVPN instance.";
        must "current()/../../../srl_nokia-netinst:type = 'srl_nokia-netinst:ip-vrf'" {
          error-message "allow-export can only be enabled in network-instances of type ip-vrf";
        }
      }
      leaf local-routes-dpath-domain-id {
        if-feature "srl_nokia-feat:bgp-domain-path";
        type srl_nokia-comm:domain-id;
        description
          "Domain ID added to the Domain Path Attribute advertised for the IP-VRF local routes in BGP IPVPN/EVPN updates";
        must "current()/../../../srl_nokia-netinst:type = 'srl_nokia-netinst:ip-vrf'" {
          error-message "D-PATH domain-id for local routes can only be configured in network-instances of type ip-vrf";
        }
      }
      list bgp-instance {
        key "id";
        max-elements 2;
        description
          "List of bgp-vpn instances configured in the network-instance. Only one instance allowed in the current release.";
        leaf id {
          type uint8 {
            range "1..2";
          }
          description
            "The index of the bgp-vpn instance";
        }
        container route-distinguisher {
          description
            "Enter the route-distinguisher context

             Route Distinguisher (RD) of the bgp-vpn instance.";
          leaf rd {
            srl_nokia-ext:show-importance "high";
            type srl_nokia-comm:route-distinguisher;
            description
              "Route Distinguisher (RD) in the bgp-vpn instance. When used for evpn and if not configured, the RD is auto-derived
               as <ip-address>:<evi> where 'ip-address' is the ipv4 address associated to the subinterface lo0.1.";
            must 'not(starts-with(string(.), "0:"))' {
              error-message "invalid value 0:*";
            }
            must 'not(starts-with(string(.), "0.0:"))' {
              error-message "invalid value 0.0:*";
            }
            must 'not(starts-with(string(.), "0.0.0.0:") and (number(substring-after(string(.), ":")) < 513))' {
              error-message "route-distinguisher value reserved";
            }
          }
          leaf route-distinguisher-origin {
            config false;
            srl_nokia-ext:show-importance "high";
            type enumeration {
              enum auto-derived-from-evi;
              enum auto-derived-from-system-ip:0;
              enum manual;
              enum none;
            }
            description
              "Origin of the operational Route Distinguisher (RD) of the bgp-vpn instance.

                'Auto-derived-from-evi' refers to an RD that is automatically allocated with the format <ip-address>:<evi>
                where 'ip-address' is the ipv4 address associated to the subinterface lo0.1.
                'Auto-derived-from-system-ip:0' refers to the RD for the EVPN Ethernet Segment routes that is automatically allocated with the format <ip-address>:0
                where 'ip-address' is the ipv4 address associated to the subinterface lo0.1.
                'Manual' refers to an RD that is configured.
                'None' indicates that the RD is neither configured nor auto-derived.";
          }
        }
        container route-target {
          description
            "Enter the route-target context

             Route Target (RT) of the bgp-vpn instance.";
          leaf export-rt {
            srl_nokia-ext:show-importance "high";
            type srl_nokia-pol-types:bgp-ext-community-type;
            must "starts-with(.,'target')";
            description
              "Export Route Target (RT) in the bgp-vpn instance. When used for evpn and if not configured, the RT is auto-derived
               with the format <asn>:<evi> where 'asn' is the autonomous-system configured in the network-instance default.";
          }
          leaf export-route-target-origin {
            config false;
            srl_nokia-ext:show-importance "high";
            type enumeration {
              enum auto-derived-from-evi;
              enum auto-derived-from-esi-bytes-1-6;
              enum from-export-policy;
              enum manual;
              enum none;
            }
            description
              "Origin of the operational export Route Target (RT) of the bgp-vpn instance.

               'Auto-derived-from-evi' refers to an RT that is automatically allocated with the format <asn>:<evi>
                where 'asn' is the autonomous-system-number configured in the network-instance default.
               'Auto-derived-from-esi-bytes-1-6' refers to the ES-import RT for the EVPN Ethernet Segment routes that is derived from bytes 1 to 6 of the Ethernet Segment
                Identifier of the route.
               'From-export-policy' refers to export RT(s) that are set on the export-policy.
               'Manual' refers to an export RT that is configured.
               'None' indicates that the export RT is neither configured nor auto-derived.";
          }
          leaf import-rt {
            srl_nokia-ext:show-importance "high";
            type srl_nokia-pol-types:bgp-ext-community-type;
            must "starts-with(.,'target')";
            description
              "Import Route Target (RT) in the bgp-vpn instance. When used for evpn and if not configured, the RT is
               auto-derived with the format <asn>:<evi> where 'asn' is the autonomous-system configured in the network-instance default.";
          }
          leaf import-route-target-origin {
            config false;
            srl_nokia-ext:show-importance "high";
            type enumeration {
              enum auto-derived-from-evi;
              enum auto-derived-from-esi-bytes-1-6;
              enum from-import-policy;
              enum manual;
              enum none;
            }
            description
              "Origin of the operational import Route Target (RT) of the bgp-vpn instance.

               'Auto-derived-from-evi' refers to an RT that is automatically allocated with the format <asn>:<evi>
                where 'asn' is the autonomous-system-number configured in the network-instance default.
               'Auto-derived-from-esi-bytes-1-6' refers to the ES-import RT for the EVPN Ethernet Segment routes that is derived from bytes 1 to 6 of the Ethernet Segment
               Identifier of the route.
               'From-import-policy' refers to import RT(s) that are set on the import-policy.
               'Manual' refers to an import RT that is configured.
               'None' indicates that the import RT is neither configured nor auto-derived.";
          }
        }
        uses srl-bgp:bgp-policy;
        leaf oper-down-reason {
          config false;
          srl_nokia-ext:show-importance "high";
          type enumeration {
            enum no-loopback-address-or-rd;
            enum no-autonomous-system-or-rt;
            enum network-instance-oper-down;
            enum bad-rd-format;
            enum none;
          }
          description
            "Reason for bgp-instance being down";
        }
      }
    }
  }

  augment "/srl_nokia-netinst:network-instance/srl_nokia-netinst:protocols" {
    uses bgp-vpn-top;
  }
}
