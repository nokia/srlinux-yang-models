module srl_nokia-tunnel-tables {
  yang-version 1.1;
  namespace "urn:nokia.com:srlinux:fib:tunnel-tables";
  prefix srl_nokia-tunnel-tables;

  import srl_nokia-common {
    prefix srl_nokia-comm;
  }
  import srl_nokia-extensions {
    prefix srl_nokia-ext;
  }
  import srl_nokia-network-instance {
    prefix srl_nokia-netinst;
  }
  import srl_nokia-ip-route-tables {
    prefix srl_nokia-rt;
  }
  import srl_nokia-features {
    prefix srl_nokia-feat;
  }

  organization
    "Nokia";
  contact
    "Nokia SR Linux Support
     Web: <http://www.nokia.com>";
  description
    "A model describing the tunnel tables of a network instance.";

  revision 2026-07-31 {
    description
      "SRLinux 26.7.1";
  }
  revision 2025-10-31 {
    description
      "SRLinux 25.10.1";
  }
  revision 2025-03-31 {
    description
      "SRLinux 25.3.1";
  }
  revision 2024-07-31 {
    description
      "SRLinux 24.7.1";
  }
  revision 2024-03-31 {
    description
      "SRLinux 24.3.1";
  }
  revision 2022-11-30 {
    description
      "SRLinux 22.11.1";
  }
  revision 2021-11-30 {
    description
      "SRLinux 21.11.1";
  }
  revision 2021-03-31 {
    description
      "SRLinux 21.3.1";
  }

  grouping tunnel-entry-common-fields {
    leaf next-hop-group {
      type leafref {
        path "/srl_nokia-netinst:network-instance/srl_nokia-netinst:route-table/srl_nokia-rt:next-hop-group/srl_nokia-rt:index";
      }
      description
        "Leaf reference to a next-hop-group that has the direct next-hops towards the tunnel far-end";
    }
    leaf metric {
      type uint32;
      srl_nokia-ext:show-importance "high";
      description
        "The metric of the tunnel.";
    }
    leaf preference {
      type uint8;
      srl_nokia-ext:show-importance "high";
      description
        "The tunnel table preference.";
    }
    uses srl_nokia-rt:internal-tags;
    leaf color {
      if-feature "srl_nokia-feat:segment-routing-colored-te-policies";
      description
        "Color associated with the sr-mpls-colored TE policy";
      type uint32 {
        range "0..4294967295";
      }
    }
    leaf flex-algo-id {
      if-feature "srl_nokia-feat:flex-algo-common";
      description
        "Flexible Algorithm identifier of the tunnel";
      type uint8 {
        range "128..255";
      }
    }
    leaf igp-instance-id {
      description
        "IGP protocol instance ID associated with the tunnel";
      type uint32;
    }
    leaf last-app-update {
      type srl_nokia-comm:date-and-time-delta;
      description
        "The date and time of the last update of this tunnel by the owning application or protocol.";
    }
    leaf resource-allocation-failed {
      type boolean;
      description
        "True when an available resource was not available for this tunnel";
    }
    uses srl_nokia-rt:fib-programming-status {
      if-feature "srl_nokia-feat:fib-tunnel-programming";
    }
  }

  grouping vxlan-fields {
    container vxlan {
      leaf destination-address {
        srl_nokia-ext:show-importance "high";
        type srl_nokia-comm:ip-address;
        description
          "The IP address that identifies the remote VXLAN Termination Endpoint (VTEP).";
      }
      leaf source-address {
        srl_nokia-ext:show-importance "high";
        type srl_nokia-comm:ip-address;
        description
          "The IP address that identifies the local VXLAN Termination Endpoint (VTEP).";
      }
      leaf time-to-live {
        type uint8;
        description
          "The Time To Live (TTL) value written into the outer IP header of VXLAN packets associated with this tunnel and originated by this router.";
      }
      leaf destination-udp-port {
        type uint16;
        description
          "The destination UDP port number written into the outer IP/UDP header of VXLAN packets associated with this tunnel and originated by this router.";
      }
      description
        "Enter the vxlan context";
    }
  }

  grouping ip-in-ip-fields {
    container ip-in-ip {
      leaf destination-address {
        srl_nokia-ext:show-importance "high";
        type srl_nokia-comm:ip-address;
        description
          "The IP address that identifies the destination of the tunnel.";
      }
      leaf source-address {
        srl_nokia-ext:show-importance "high";
        type srl_nokia-comm:ip-address;
        description
          "The IP address that identifies the source of the tunnel.";
      }
      description
        "Enter the ip-in-ip context";
    }
  }

  grouping gre-tunnel-fields {
    container gre {
      leaf source-address {
        type srl_nokia-comm:ip-address;
        description
          "The source IP address in the outer IP header added by GRE encapsulation";
      }
      leaf destination-address {
        type srl_nokia-comm:ip-address;
        description
          "Destination IP address in the outer IP header added by GRE encapsulation";
      }
      leaf ip-ttl {
        type uint8;
        description
          "IP TTL in the outer IP header added by GRE encapsulation";
      }
      leaf in-profile-dscp {
        type srl_nokia-comm:dscp-value;
        description
          "DSCP value in the outer IP header except when the packet is out of profile";
      }
      leaf out-profile-dscp {
        type srl_nokia-comm:dscp-value;
        description
          "DSCP value in the outer IP header when the packet was policed as out of profile";
      }
      description
        "Enter the gre context";
    }
  }

  grouping udp-tunnel-fields {
    container udp {
      leaf source-address {
        type srl_nokia-comm:ip-address;
        description
          "The source IP address in the outer IP header added by GRE encapsulation";
      }
      leaf destination-address {
        type srl_nokia-comm:ip-address;
        description
          "Destination IP address in the outer IP header added by GRE encapsulation";
      }
      leaf destination-udp-port {
        type srl_nokia-comm:port-number;
        description
          "Destination UDP port number in the added UDP header

           Usually this reflects the encoded payload type";
      }
      leaf ip-ttl {
        type uint8;
        description
          "IP TTL in the outer IP header added by GRE encapsulation";
      }
      leaf in-profile-dscp {
        type srl_nokia-comm:dscp-value;
        description
          "DSCP value in the outer IP header except when the packet is out of profile";
      }
      leaf out-profile-dscp {
        type srl_nokia-comm:dscp-value;
        description
          "DSCP value in the outer IP header when the packet was policed as out of profile";
      }
      description
        "Enter the udp context";
    }
  }

  grouping tunnel-statistics {
    container statistics {
      leaf active-tunnels {
        type uint32;
        description
          "The total number of tunnels, belonging to this address family, that are active.";
      }
      leaf inactive-tunnels {
        type uint32;
        description
          "The total number of tunnels, belonging to this address family, that are inactive (not programmed).";
      }
      leaf total-tunnels {
        type srl_nokia-comm:zero-based-counter64;
        description
          "The total number of tunnels, active and inactive, belonging to this address family";
      }
      description
        "Enter the statistics context";
    }
  }

  grouping tunnel-summary {
    container tunnel-summary {
      description
        "Enter the tunnel-summary context

         Tunnel summary information";
      list tunnel-type {
        key "type";
        leaf type {
          type identityref {
            base srl_nokia-comm:tunnel-type;
          }
          description
            "Tunneling encapsulation format";
        }
        leaf active-tunnels {
          type uint32;
          description
            "The total number of tunnels, using this encapsulation type, that are active.";
        }
        leaf inactive-tunnels {
          type uint32;
          description
            "The total number of tunnels, using this encapsulation type, that are inactive (not programmed).";
        }
        leaf total-tunnels {
          type srl_nokia-comm:zero-based-counter64;
          description
            "The total number of tunnels, active and inactive, using this encapsulation type.";
        }
      }
    }
  }

  grouping tunnel-tables-top {
    container ipv4 {
      description
        "Enter the ipv4 context

         The container for the IPv4 tunnels associated with the network instance.";
      list tunnel {
        key "ipv4-prefix type owner id";
        leaf ipv4-prefix {
          type srl_nokia-comm:ipv4-prefix;
          description
            "The IPv4 prefix associated with the endpoint of the tunnel.";
        }
        leaf type {
          type identityref {
            base srl_nokia-comm:tunnel-type;
          }
          description
            "The tunnel (encapsulation) type";
        }
        leaf owner {
          type string;
          description
            "The name of the application that submitted the tunnel to TTM";
        }
        leaf id {
          type uint32;
          description
            "An owner-assigned index value that is unique for each of the tunnels terminating at a particular prefix.";
        }
        uses tunnel-entry-common-fields;
        uses vxlan-fields;
        uses ip-in-ip-fields;
        uses gre-tunnel-fields;
        uses udp-tunnel-fields;
      }
      uses tunnel-statistics;
      uses tunnel-summary;
    }
    container ipv6 {
      description
        "Enter the ipv6 context

         The container for the IPv6 tunnels associated with the network instance.";
      list tunnel {
        key "ipv6-prefix type owner id";
        leaf ipv6-prefix {
          type srl_nokia-comm:ipv6-prefix;
          description
            "The IPv6 prefix associated with the endpoint of the tunnel.";
        }
        leaf type {
          type identityref {
            base srl_nokia-comm:tunnel-type;
          }
          description
            "The tunnel (encapsulation) type";
        }
        leaf owner {
          type string;
          description
            "The name of the application that submitted the tunnel to TTM";
        }
        leaf id {
          type uint32;
          description
            "An owner-assigned index value that is unique for each of the tunnels terminating at a particular prefix.";
        }
        uses tunnel-entry-common-fields;
        uses vxlan-fields;
        uses ip-in-ip-fields;
        uses gre-tunnel-fields;
        uses udp-tunnel-fields;
      }
      uses tunnel-statistics;
      uses tunnel-summary;
    }
  }

  augment "/srl_nokia-netinst:network-instance/srl_nokia-netinst:tunnel-table" {
    uses tunnel-tables-top;
  }
}
