module srl_nokia-sr-policies {
  yang-version 1.1;
  namespace "urn:srl_nokia/sr-policies";
  prefix srl_nokia-sr-policies;

  import srl_nokia-common {
    prefix srl_nokia-comm;
  }
  import srl_nokia-network-instance {
    prefix srl_nokia-netinst;
  }
  import srl_nokia-segment-routing {
    prefix srl_nokia-sr;
  }
  import srl_nokia-system {
    prefix srl_nokia-system;
  }
  import srl_nokia-mpls-label-management {
    prefix srl_nokia-mplslbl;
  }
  import srl_nokia-features {
    prefix srl_nokia-feat;
  }

  description
    "Configuration and state related to segment routing policies.";

  revision 2022-06-30 {
    description
      "SRLinux 22.6.1";
  }
  revision 2022-03-31 {
    description
      "SRLinux 22.3.1";
  }
  revision 2021-11-30 {
    description
      "SRLinux 21.11.1";
  }

  identity policy-invalid-reason {
    description
      "Base identity for reasons that describe why a candidate path is invalid";
  }

  identity admin-disabled {
    base policy-invalid-reason;
    description
      "The candidate path is administratively disabled";
  }

  identity no-valid-segment-list {
    base policy-invalid-reason;
    description
      "The candidate path has no valid segment lists";
  }

  identity no-binding-sid-label {
    base policy-invalid-reason;
    description
      "No free labels in the label-range";
  }

  typedef policy-invalid-reason-type {
    type identityref {
      base policy-invalid-reason;
    }
  }

  identity segment-list-invalid-reason {
    description
      "Base identity for reasons that describe why a segment list is invalid.";
  }

  identity unresolved-first-segment {
    base segment-list-invalid-reason;
    description
      "The system is unable to resolve the first SID (MPLS label value) into one or more outgoing interface(s) and next-hop(s)";
  }

  identity unresolved-named-path {
    base segment-list-invalid-reason;
    description
      "The most recent query to TEDB about the named path (triggered by periodic re-optimization or initially) indicated that the named path is not viable.";
  }

  identity maximum-label-stack-depth-exceeded {
    base segment-list-invalid-reason;
    description
      "The resolution of the named path requires more labels than supported by the hardware datapath.";
  }

  typedef segment-list-invalid-reason-type {
    type identityref {
      base segment-list-invalid-reason;
    }
  }

  typedef protocol-origin-type {
    type enumeration {
      enum pcep {
        value 10;
        description
          "PCEP used as signalling mechanism for the candidate path";
      }
      enum bgp {
        value 20;
        description
          "BGP used as signalling mechanism for the candidate path";
      }
      enum local {
        value 30;
        description
          "Management interface used for candidate path instantiation";
      }
    }
    description
      "Originating protocol type";
  }

  typedef candidate-path-type {
    type enumeration {
      enum best {
        description
          "The candidate path is the best valid path but it does not have a protection policy with SBFD enabled";
      }
      enum primary {
        description
          "The candidate path is the best valid path and it has a protection policy with SBFD enabled.";
      }
      enum secondary {
        description
          "The candidate path is the second best valid path and it has a protection policy with SBFD enabled.";
      }
      enum tertiary {
        description
          "The candidate path is the third best valid path and it has a protection policy with SBFD enabled.";
      }
      enum other {
        description
          "The candidate path is invalid or else it is valid but without special designation as best, primary, secondary or tertiary.";
      }
    }
  }

  typedef segment-list-oper-state {
    type enumeration {
      enum up {
        description
          "The segment-list is valid and belongs to a candidate path that is best, primary, secondary or tertiary and if SBFD is enabled, the SBFD session state is up.";
      }
      enum sbfd-down {
        description
          "The segment-list is valid and belongs to a candidate path that is primary, secondary or tertiary but the SBFD session state is down (or in hold-down).";
      }
      enum valid {
        description
          "The segment-list is valid but does not belong to a candidate path that is best, primary, secondary or tertiary";
      }
      enum invalid {
        description
          "The segment-list is invalid and the reason will be provided";
      }
      enum down {
        description
          "The parent candidate path is administratively disabled, or this segment list has been administratively disabled";
      }
    }
  }

  grouping policy-state {
    leaf path-type {
      config false;
      type candidate-path-type;
      description
        "The candidate path type.

         One of the following values:
         -  best: the policy is the best valid path but it does not have a protection policy with SBFD enabled
         -  primary: the policy is the best valid path and it has a protection policy with SBFD enabled
         -  secondary: the policy is the second best valid path and it has a protection policy with SBFD enabled
         -  tertiary: the policy is the third best valid path and it has a protection policy with SBFD enabled
         -  other: the policy is any other path";
    }
    leaf valid {
      config false;
      type boolean;
      description
        "True when the candidate path is valid.";
    }
    leaf invalid-reason {
      config false;
      type policy-invalid-reason-type;
      description
        "The reason why the candidate path is invalid.

         One of the following values:
         -  admin-disabled: the candidate path is administratively disabled
         -  no-valid-segment-list: the candidate path has no valid segment lists
         -  binding-sid-failed: no free labels in the label-range or ILM programming failed
         -  tunnel-programming-failed: programming failed due to exhaustion of tunnel, NHLFE or other datapath resources";
    }
    leaf protection-available {
      config false;
      type boolean;
      description
        "True when this (primary) candidate path is protected by another pre-programmed candidate path.

         For a primary path to be protected all of the following conditions must be met:
         -  the primary path is bound to a protection-policy with seamless-bfd set to true
         -  there is a secondary path with a protection-policy having seamless-bfd set to true and the associated SBFD session is currently up OR there is a tertiary path with a protection-policy having seamless-bfd set to true and the associated SBFD session is currently up";
    }
  }

  grouping segment-list-state {
    leaf oper-state {
      config false;
      type segment-list-oper-state;
      description
        "Segment list operational state";
    }
    leaf invalid-reason {
      config false;
      type segment-list-invalid-reason-type;
      description
        "The reason why the segment list is invalid.

         One of the following values:
         -  unresolved-first-segment: the first SID (MPLS label value) cannot be resolved into one or more outgoing interface(s) and next-hop(s)
         -  unresolved-named-path: the most recent query to TEDB about the named path (triggered by periodic re-optimization or initially) indicated that the named path is not viable";
    }
    leaf sbfd-session-id {
      config false;
      type uint32;
      description
        "Sessions ID used to associate segement list to seamless-BFD session";
    }
    container statistics {
      config false;
      leaf out-packets {
        type srl_nokia-comm:zero-based-counter64;
        config false;
        description
          "Number of packets forwarded by the segment-list, including packets matched by the binding SID and packets matching the tunnel entry";
      }
      leaf out-octets {
        type srl_nokia-comm:zero-based-counter64;
        config false;
        units "byte";
        description
          "Number of octets forwarded by the segment-list, including packets matched by the binding SID and packets matching the tunnel entry";
      }
    }
  }

  grouping sr-policies-top {
    description
      "Traffic engineering policies grouping";
    container segment-routing-policies {
      if-feature "srl_nokia-feat:sr-policies";
      presence "Configure sr policies";
      description
        "Container with segment routing policies";
      uses binding-sid-label-blocks;
      uses named-paths;
      uses protection-policies;
      uses static-policies;
      uses policy-database;
    }
  }

  grouping binding-sid-label-blocks {
    container binding-sid {
      if-feature "srl_nokia-feat:label-management";
      description
        "Configuration and state related to the label block(s) used for the binding SIDs associated with SR policies";
      container static-assignment {
        description
          "Container applicable to statically assigned binding SIDs";
        leaf label-range {
          type leafref {
            path "/srl_nokia-system:system/srl_nokia-mplslbl:mpls/srl_nokia-mplslbl:label-ranges/srl_nokia-mplslbl:static/srl_nokia-mplslbl:name";
          }
          must 'not(/srl_nokia-system:system/srl_nokia-mplslbl:mpls/srl_nokia-mplslbl:label-ranges/srl_nokia-mplslbl:static[srl_nokia-mplslbl:name=current()]/srl_nokia-mplslbl:shared)' {
            error-message "Static label block for binding SIDs should be exclusive (not shared)";
          }
          description
            "Reference to a static label range";
        }
        leaf label-range-status {
          config false;
          type enumeration {
            enum available;
            enum unavailable;
          }
          description
            "Status of the label block.

             The label block may show as unavailable if there is pending cleanup.";
        }
      }
    }
  }

  grouping named-paths {
    container named-paths {
      description
        "Named paths used to specify SR policy segment lists";
      list path {
        key "named-path-name";
        leaf named-path-name {
          type srl_nokia-comm:name;
          description
            "A unique name to identify the named path";
        }
        list hop {
          max-elements 4;
          key "index";
          leaf index {
            type uint8 {
              range "1..4";
            }
            description
              "The index number of the hop. Hops are processed in ascending sequence.";
          }
          leaf ip-address {
            mandatory true;
            type srl_nokia-comm:ip-address;
            description
              "An IPv4 or IPv6 address that is a hop to be visited on the way to the destination";
          }
          leaf hop-type {
            mandatory true;
            type enumeration {
              enum strict {
                description
                  "A strict hop is always one hop away from the previous hop (or from the head-end in the case of the first hop). TE DB translates each strict hop into an adjacency-SID label. To be resolved to an adjacency SID, a strict hop must be a non-local IP address on a connected subnet (representing the neighbor's interface address on this subnet) or it must be a loopback or system address of the directly-connected neighbor.";
              }
              enum loose {
                description
                  "A loose hop can be any number of hops away from the previous hop (or from the head-end in the case of the first hop). TE DB translates each loose hop into a node-SID label. A loose hop can be any IP address of the remote router associated with the node SID, not just the IP address associated with the node SID itself.

                   Note that the endpoint of the policy is implicitly considered to be a final loose hop. If the final configured hop (previous hop of this implicit loose hop) is unnecessary TEDB indicates this to SR policy manager and the adjacency SID or node SID of the final confgired hop is omitted from the datapath programming.";
              }
            }
          }
        }
      }
    }
  }

  grouping protection-policies {
    container protection-policies {
      description
        "Container with protection policies";
      list policy {
        key "protection-policy-name";
        leaf protection-policy-name {
          type srl_nokia-comm:name;
          description
            "A unique identifying name for the protection policy";
        }
        container seamless-bfd {
          presence "Enable Seamless BFD within protection policy";
          description
            "When present, this node attempts to setup a seamless BFD session on every segment-list of every SR policy that uses this protection-policy, but only if that SR policy is a primary or secondary candidate path (or it is a tertiary path at a time when the secondary path is down). The transition of an SBFD session from up to down is a trigger for rerouting traffic around a failed primary path.";
          leaf multiplier {
            type uint8 {
              range "3..20";
            }
            default "3";
            description
              "The number of packets that must be missed to declare this session as down

               The detection interval for the BFD session is calculated by multiplying the
               value of the negotiated transmission interval by this value.";
          }
          leaf desired-minimum-transmit-interval {
            type uint32 {
              range "10000..100000000";
            }
            default "1000000";
            units "microseconds";
            description
              "The minimum interval between transmission of BFD control packets

               This value is advertised to the peer, however the actual interval used is specified
               by taking the maximum of desired-minimum-transmit-interval and the value of the remote
               required-minimum-receive interval value.
               This value is specified as an integer number of microseconds.";
          }
          leaf return-path-label {
            type uint32;
            description
              "The MPLS label to be used to by the far-end device to return the BFD message

               This label is added as the bottom value in the segment routing label stack
               and will be used by the far-end device to return BFD message to the originator.
               This value could either be a MPLS label or a binding SID that will be used
               at the far-end to match an appropriate polciy to return the traffic.";
          }
        }
        leaf hold-down-timer {
          type uint16;
          units "seconds";
          description
            "Specifies a hold-down timer value when seamless-bfd is enabled

             This timer is started whenever the SBFD session finishes a transition from up->down->up. While this timer is running the SBFD session state stays in hold-down and the corresponding segment-list stays in sbfd-down state.

             The default is 3 seconds.";
        }
        leaf revert-timer {
          type uint16;
          units "seconds";
          default "10";
          description
            "Specifies a revert timer value when seamless-bfd is enabled

             The revert timer applies to a primary candidate path with a segment-list for which the SBFD session has just completed the transition up -> down -> hold-down to up during a period where the candidate path has remained the primary path the entire time. While this timer is running traffic stays on the secondary (or tertiary) path, unless that secondary/tertiary path fails. When the timer expires, traffic reverts back to the primary path. If the SBFD session failure is followed by an event that causes the primary path to be considered invalid any remaining time on the revert-timer is cancelled and another candidate path may be selected as the new primary path; there is no delay in switching over to this new primary path.";
        }
      }
    }
  }

  grouping static-segment-lists {
    list segment-list {
      max-elements 1;
      key "segment-list-index";
      leaf segment-list-index {
        type uint8 {
          range "1..64";
        }
        description
          "Index to enumerate the different segment lists for a static policy.";
      }
      leaf admin-state {
        type srl_nokia-comm:admin-state;
        description
          "Used to administratively enable or disable a segment list";
      }
      choice type {
        description
          "Type of path";
        case explicit {
          description
            "Segment-list with explicitly defined segments that are possibly translated from IP addresses.";
          leaf named-path {
            type leafref {
              path "../../../../named-paths/path/named-path-name";
            }
          }
          leaf re-optimization-timer {
            description
              "Sets the value of the re-optimization timer specific to the named-path.

               Whenever a named-path segment-list transitions from down to up this periodic timer is started. Every time it expires SR policy manager queries TEDB for the latest resolution detail. The result of this query can change the valid state of the segment list (valid -> invalid or invalid -> valid) or it can return a new SID list based on the current network topology.

               TEDB determines that a named path is invalid if any of the following applies:
               -  there is a strict hop in the named path that refers to a non-existent adjacency (link could be down) or an adjacency for which no adjacency SID was advertised
               -  there is a loose hop in the named path that refers to a node that is not reachable at all, or not reachable over a loop-free path, or that refers to a node for which no node SID was advertised";
            type uint16 {
              range "3..600";
            }
            units "seconds";
            default "30";
          }
          list segment {
            must 'not(boolean(../named-path))' {
              error-message "A named path is mutually exclusive with a path defined using explicit SIDs";
            }
            max-elements 2;
            key "segment-index";
            leaf segment-index {
              type uint8;
              description
                "Index to enumerate the different segments in a segment-list";
            }
            container segment-type-a {
              description
                "Segment identified by MPLS label";
              leaf sid-value {
                type srl_nokia-comm:mpls-label-non-reserved;
                description
                  "MPLS label value";
              }
            }
          }
        }
        case dynamic {
          description
            "Segment-list with dynamically computed segments that satisfy specified constraints";
        }
      }
      uses segment-list-state;
    }
  }

  grouping static-policies {
    container static-policies {
      list policy {
        key "static-policy-name";
        unique "endpoint color preference";
        leaf static-policy-name {
          type srl_nokia-comm:name;
          description
            "policy name";
        }
        leaf endpoint {
          mandatory true;
          type srl_nokia-comm:ip-address-excluding-all-zero;
          description
            "Policy endpoint IP address";
        }
        leaf color {
          type uint32 {
            range "0..4294967295";
          }
          default "0";
          description
            "Color associated with the policy.";
        }
        leaf binding-sid {
          type srl_nokia-comm:mpls-label-non-reserved;
          description
            "The binding SID of the policy (candidate path).

             Amongst all static policies that have a configured binding-sid, each must have a unique value for this leaf. If no value is specified then no binding SID is allocated or programmed.";
          must '../../../binding-sid/static-assignment/label-range' {
            error-message "A static binding SID label block must be defined";
          }
          must '(current() >= /srl_nokia-system:system/srl_nokia-mplslbl:mpls/srl_nokia-mplslbl:label-ranges/srl_nokia-mplslbl:static[srl_nokia-mplslbl:name=current()/../../../binding-sid/static-assignment/label-range]/srl_nokia-mplslbl:start-label)'
             + ' and (current() <= /srl_nokia-system:system/srl_nokia-mplslbl:mpls/srl_nokia-mplslbl:label-ranges/srl_nokia-mplslbl:static[srl_nokia-mplslbl:name=current()/../../../binding-sid/static-assignment/label-range]/srl_nokia-mplslbl:end-label)' {
            error-message "Static bindig SID is outside of the defined range";
          }
        }
        leaf admin-state {
          type srl_nokia-comm:admin-state;
          default "enable";
          description
            "SR policy administrative state";
        }
        leaf description {
          type srl_nokia-comm:description;
          description
            "Description of the policy";
        }
        leaf preference {
          type uint32 {
            range "1..65535";
          }
          default "100";
          description
            "One valid candidate path is considered better than another valid candidate path for the same (color, endpoint) if it has a higher preference than the other path.";
        }
        leaf protection-policy {
          type leafref {
            path "../../../protection-policies/policy/protection-policy-name";
          }
        }
        uses policy-state;
        uses static-segment-lists;
      }
    }
  }

  grouping candidate-paths {
    description
      "SR policy candidate path grouping";
    list candidate-path {
      description
        "SR policy candidate paths. This list includes local static policies, but only those that have both a color and endpoint.";
      key "candidate-path-index";
      leaf candidate-path-index {
        type uint8;
        description
          "Index to enumerate the different candidate paths for a (color, endpoint).";
      }
      leaf protocol-origin {
        type protocol-origin-type;
        description
          "Instantiation mechanism used to create the candidate path";
      }
      leaf originator {
        type string;
        description
          "Identifier (concatenation of ASN and node-address) of the node that signalled/instantiated the candidate path on headend";
      }
      leaf discriminator {
        type uint32;
        description
          "Candidate path distinguisher";
      }
      leaf preference {
        type uint32 {
          range "1..65535";
        }
        description
          "Candidate path preference";
      }
      leaf binding-sid {
        type srl_nokia-comm:mpls-label-non-reserved;
        description
          "The binding SID of the candidate path.";
      }
      uses policy-state;
      uses dynamic-segment-lists;
    }
  }

  grouping dynamic-segment-lists {
    list segment-list {
      key "segment-list-index";
      leaf segment-list-index {
        type uint8 {
          range "1..32";
        }
        description
          "Index to enumerate the different segment lists.";
      }
      list segment {
        key "segment-index";
        leaf segment-index {
          type uint8;
          description
            "Index to enumerate the different segments in a segment-list";
        }
        container segment-type-a {
          description
            "Segment identified by MPLS label";
          leaf sid-value {
            type srl_nokia-comm:mpls-label-non-reserved;
            description
              "MPLS label value";
          }
        }
      }
      uses segment-list-state;
    }
  }

  grouping policy-database {
    container policy-database {
      config false;
      list policy {
        key "color endpoint";
        leaf color {
          type uint32 {
            range "0..4294967295";
          }
          description
            "Color associated with the SR policy";
        }
        leaf endpoint {
          type srl_nokia-comm:ip-address;
          description
            "Policy endpoint IP address";
        }
        uses candidate-paths;
      }
    }
  }

  augment "/srl_nokia-netinst:network-instance/srl_nokia-sr:segment-routing" {
    uses sr-policies-top;
  }
}
