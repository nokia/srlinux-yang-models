module srl_nokia-bgp-evpn-bgp-instance-vpws-destinations-remote-ac {
  yang-version 1.1;
  namespace "urn:nokia.com:srlinux:evpn:bgp-evpn-bgp-instance-vpws-destinations-remote-ac";
  prefix srl_nokia-bgp-evpn-bgp-instance-vpws-destinations-remote-ac;

  import srl_nokia-common {
    prefix srl_nokia-comm;
  }
  import srl_nokia-network-instance {
    prefix srl_nokia-netinst;
  }
  import srl_nokia-extensions {
    prefix srl_nokia-ext;
  }
  import srl_nokia-bgp-evpn {
    prefix srl_bgp-evpn;
  }

  organization
    "Nokia";
  contact
    "Nokia SR Linux Support
     Web: <http://www.nokia.com>";
  description
    "Model for vpws destinations on the bgp-evpn mpls instance";

  revision 2026-07-31 {
    description
      "SRLinux 26.7.1";
  }
  revision 2025-10-31 {
    description
      "SRLinux 25.10.1";
  }
  revision 2024-03-31 {
    description
      "SRLinux 24.3.1";
  }

  grouping evpn-mpls-vpws-destinations-destination-top {
    list destination {
      config false;
      key "tep evi-label tunnel-id";
      leaf tep {
        srl_nokia-ext:show-importance "high";
        type srl_nokia-comm:ip-address;
        description
          "The IP address that identifies the remote EVPN Termination Endpoint (TEP).";
      }
      leaf evi-label {
        type srl_nokia-comm:mpls-label-non-reserved;
        srl_nokia-ext:show-importance "high";
        description
          "EVI label of the destination.";
      }
      leaf tunnel-id {
        type uint64;
        srl_nokia-ext:show-importance "high";
        description
          "tunnel identitier of the destination.";
      }
      leaf destination-index {
        type uint64;
        srl_nokia-ext:show-importance "high";
        description
          "A system-wide unique identifier of this evpn-mpls destination object (system allocated).";
      }
      leaf not-programmed-reason {
        srl_nokia-ext:show-importance "high";
        type enumeration {
          enum no-destination-index;
        }
        description
          "The reason why the evpn-mpls destination is not programmed.";
      }
    }
  }

  grouping evpn-mpls-vpws-destinations-es-destination-next-hops-top {
    list destination {
      config false;
      key "tep evi-label tunnel-id";
      leaf tep {
        srl_nokia-ext:show-importance "high";
        type srl_nokia-comm:ip-address;
        description
          "The IP address that identifies the remote EVPN Termination Endpoint (TEP).";
      }
      leaf evi-label {
        type srl_nokia-comm:mpls-label-non-reserved;
        srl_nokia-ext:show-importance "high";
        description
          "EVI label of this next-hop.";
      }
      leaf tunnel-id {
        type uint64;
        srl_nokia-ext:show-importance "high";
        description
          "tunnel identitier of this next-hop.";
      }
    }
  }

  grouping evpn-mpls-vpws-destinations-es-destination-top {
    list es-destination {
      config false;
      key "esi";
      leaf esi {
        type srl_nokia-comm:esi;
        srl_nokia-ext:show-importance "high";
        description
          "The 10-byte Ethernet Segment Identifier of the ethernet segment.
           ESI-0 or MAX-ESI values are not allowed.";
      }
      leaf destination-index {
        type uint64;
        srl_nokia-ext:show-importance "high";
        description
          "A system-wide unique identifier of this evpn-mpls destination object (system allocated).";
      }
      leaf not-programmed-reason {
        srl_nokia-ext:show-importance "high";
        type enumeration {
          enum no-destination-index;
        }
        description
          "The reason why the evpn-mpls destination is not programmed.";
      }
      uses evpn-mpls-vpws-destinations-es-destination-next-hops-top;
    }
  }

  grouping evpn-srv6-vpws-destinations-destination-top {
    list destination {
      config false;
      key "tep sid";
      leaf tep {
        srl_nokia-ext:show-importance "high";
        type srl_nokia-comm:ip-address;
        description
          "The IP address that identifies the remote EVPN Termination Endpoint (TEP)";
      }
      leaf sid {
        type srl_nokia-comm:ipv6-address-unicast;
        srl_nokia-ext:show-importance "high";
        description
          "SRv6 Segment Identifier of the destination";
      }
      leaf destination-index {
        type uint64;
        srl_nokia-ext:show-importance "high";
        description
          "A system-wide unique identifier of this evpn-srv6 destination object (system allocated)";
      }
      leaf not-programmed-reason {
        srl_nokia-ext:show-importance "high";
        type enumeration {
          enum no-destination-index;
        }
        description
          "The reason why the evpn-srv6 destination is not programmed";
      }
    }
  }

  grouping evpn-srv6-vpws-destinations-es-destination-next-hops-top {
    list destination {
      config false;
      key "tep sid";
      leaf tep {
        srl_nokia-ext:show-importance "high";
        type srl_nokia-comm:ip-address;
        description
          "The IP address that identifies the remote EVPN Termination Endpoint (TEP)";
      }
      leaf sid {
        type srl_nokia-comm:ipv6-address-unicast;
        srl_nokia-ext:show-importance "high";
        description
          "SRv6 Segment Identifier of this next-hop";
      }
    }
  }

  grouping evpn-srv6-vpws-destinations-es-destination-top {
    list es-destination {
      config false;
      key "esi";
      leaf esi {
        type srl_nokia-comm:esi;
        srl_nokia-ext:show-importance "high";
        description
          "The 10-byte Ethernet Segment Identifier of the ethernet segment

           ESI-0 or MAX-ESI values are not allowed";
      }
      leaf destination-index {
        type uint64;
        srl_nokia-ext:show-importance "high";
        description
          "A system-wide unique identifier of this evpn-mpls destination object (system allocated)";
      }
      leaf not-programmed-reason {
        srl_nokia-ext:show-importance "high";
        type enumeration {
          enum no-destination-index;
        }
        description
          "The reason why the evpn-srv6 destination is not programmed";
      }
      uses evpn-srv6-vpws-destinations-es-destination-next-hops-top;
    }
  }

  grouping destinations-top {
    container destinations {
      config false;
      container mpls {
        uses evpn-mpls-vpws-destinations-destination-top;
        uses evpn-mpls-vpws-destinations-es-destination-top;
        description
          "Enter the mpls context";
      }
      container srv6 {
        uses evpn-srv6-vpws-destinations-destination-top;
        uses evpn-srv6-vpws-destinations-es-destination-top;
        description
          "Enter the srv6 context";
      }
      description
        "Enter the destinations context";
    }
  }

  augment "/srl_nokia-netinst:network-instance/srl_nokia-netinst:protocols/srl_nokia-netinst:bgp-evpn/srl_bgp-evpn:bgp-instance/srl_bgp-evpn:vpws-attachment-circuits/srl_bgp-evpn:remote/srl_bgp-evpn:remote-attachment-circuit" {
    uses destinations-top;
  }
}
