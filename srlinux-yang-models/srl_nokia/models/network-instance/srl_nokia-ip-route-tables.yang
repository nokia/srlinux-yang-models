module srl_nokia-ip-route-tables {
  yang-version 1.1;
  namespace "urn:nokia.com:srlinux:fib:ip-route-tables";
  prefix srl_nokia-ip-route-tables;

  import srl_nokia-common {
    prefix srl_nokia-comm;
  }
  import srl_nokia-extensions {
    prefix srl_nokia-ext;
  }
  import srl_nokia-network-instance {
    prefix srl_nokia-netinst;
  }
  import srl_nokia-interfaces {
    prefix srl_nokia-if;
  }
  import srl_nokia-features {
    prefix srl-feat;
  }
  import srl_nokia-platform {
    prefix srl_nokia-platform;
  }
  import srl_nokia-platform-lc {
    prefix srl_nokia-platform-lc;
  }
  import srl_nokia-platform-control {
    prefix srl_nokia-platform-control;
  }
  import srl_nokia-platform-control-fp {
    prefix srl_nokia-platform-control-fp;
  }
  import srl_nokia-platform-linecard-fib {
    prefix srl-lc-fib;
  }
  import srl_nokia-system {
    prefix srl_nokia-system;
  }
  import srl_nokia-srv6 {
    prefix srl_nokia-sys-srv6;
  }
  import srl_nokia-srv6-types {
    prefix srl_nokia-srv6-types;
  }

  organization
    "Nokia";
  contact
    "Nokia SR Linux Support
     Web: <http://www.nokia.com>";
  description
    "A model describing the IP routing tables of a network instance.";

  revision 2026-07-31 {
    description
      "SRLinux 26.7.1";
  }
  revision 2026-03-31 {
    description
      "SRLinux 26.3.1";
  }
  revision 2025-10-31 {
    description
      "SRLinux 25.10.1";
  }
  revision 2025-07-31 {
    description
      "SRLinux 25.7.1";
  }
  revision 2025-03-31 {
    description
      "SRLinux 25.3.1";
  }
  revision 2024-10-31 {
    description
      "SRLinux 24.10.1";
  }
  revision 2024-07-31 {
    description
      "SRLinux 24.7.1";
  }
  revision 2024-03-31 {
    description
      "SRLinux 24.3.1";
  }
  revision 2023-10-31 {
    description
      "SRLinux 23.10.1";
  }
  revision 2023-03-31 {
    description
      "SRLinux 23.3.1";
  }
  revision 2022-11-30 {
    description
      "SRLinux 22.11.1";
  }
  revision 2022-06-30 {
    description
      "SRLinux 22.6.1";
  }
  revision 2021-11-30 {
    description
      "SRLinux 21.11.1";
  }
  revision 2021-06-30 {
    description
      "SRLinux 21.6.1";
  }
  revision 2021-03-31 {
    description
      "SRLinux 21.3.1";
  }
  revision 2020-06-30 {
    description
      "SRLinux 20.6.1";
  }
  revision 2019-11-30 {
    description
      "SRLinux 19.11.1";
  }

  typedef failed-complex-list-including-control {
    type string {
      pattern 'control-A|control-B|complex-([0-9]|1[0-6])\.[01]';
    }
  }

  identity fib-nexthop-type {
    description
      "Base type for next-hop object types.";
  }

  identity extract {
    base fib-nexthop-type;
    description
      "Next-hop will cause matching packets to be delivered to the CPM.";
  }

  identity direct {
    base fib-nexthop-type;
    description
      "Next-hop was resolved by a local route - i.e. it is an address on a connected subnet.";
  }

  identity discard {
    base fib-nexthop-type;
    description
      "Next-hop will cause matching packets to be dropped without ICMP generation.";
  }

  identity reject {
    base fib-nexthop-type;
    description
      "Next-hop will cause matching packets to be dropped with ICMP generation.";
  }

  identity indirect {
    base fib-nexthop-type;
    description
      "Next-hop was resolved by a non-local route - i.e. it is not an address on a connected subnet.";
  }

  identity mpls {
    base fib-nexthop-type;
    description
      "An MPLS label will be pushed when forwarding to this next-hop.";
  }

  identity tunnel {
    base fib-nexthop-type;
    description
      "Next-hop is a tunnel.";
  }

  identity broadcast {
    base fib-nexthop-type;
    description
      "Next-hop will cause matching subnet-bradcast packets to be delivered to the control plane.";
  }

  identity redirect {
    base fib-nexthop-type;
    description
      "Next-hop will redirect to another network-instance.";
  }

  identity interface-with-mac {
    base fib-nexthop-type;
    description
      "Next-hop is associated with an outbound interface plus MAC address";
  }

  identity srv6 {
    if-feature "srl-feat:srv6 or srl-feat:srv6-usid-basic";
    base fib-nexthop-type;
    description
      "Packets forwarded to this next-hop have one or more SRv6 SIDs added";
  }

  identity srv6-endpoint {
    if-feature "srl-feat:srv6 or srl-feat:srv6-usid-basic";
    base fib-nexthop-type;
    description
      "Packets forwarded to this next-hop have an associated SRv6 endpoint behavior";
  }

  typedef operation-type {
    type enumeration {
      enum add {
        description
          "The current or last operation was an attempt to create a new entry.";
      }
      enum delete {
        description
          "The current or last operation was an attempt to delete an existing entry.";
      }
      enum modify {
        description
          "The current or last operation was an attempt to modify an existing entry.";
      }
      enum none {
        description
          "There was no prior operation for this entry or there is no current operation that is in process";
      }
    }
  }

  grouping tunnel-next-hop-fields {
    leaf ip-prefix {
      type srl_nokia-comm:ip-prefix;
      description
        "The IPv4 or IPv6 prefix associated with the endpoint of the tunnel";
    }
    leaf type {
      type identityref {
        base srl_nokia-comm:tunnel-type;
      }
      description
        "The tunnel (encapsulation) type";
    }
    leaf owner {
      type string;
      description
        "The name of the application that submitted the tunnel to TTM";
    }
    leaf tunnel-id {
      type uint32;
      description
        "An owner-assigned index value that is unique for each of the tunnels terminating at a particular prefix";
    }
    leaf network-instance {
      type leafref {
        path "/srl_nokia-netinst:network-instance/srl_nokia-netinst:name";
      }
      description
        "The network instance associated with the tunnel";
    }
  }

  grouping traffic-statistics {
    container counters {
      srl_nokia-ext:telemetry-atomic "false";
      description
        "Enter the counters context

         Packet forwarding counters";
      leaf resource-allocation-failed {
        type boolean;
        description
          "True when an available statistics resource was not available for this forwarding object";
      }
      leaf-list resource-allocation-failed-locations {
        description
          "List of forwarding complexes that reported a stat resource allocation failure. They appear in the format (slot-number,complex-number).";
        type failed-complex-list-including-control;
      }
      leaf packets-forwarded {
        type srl_nokia-comm:zero-based-counter64;
        description
          "The number of packets forwarded";
      }
      leaf octets-forwarded {
        type srl_nokia-comm:zero-based-counter64;
        description
          "The number of octets in the packets that were forwarded";
      }
    }
  }

  grouping internal-tags {
    description
      "Grouping containing the state of internal tags";
    leaf-list internal-tags {
      if-feature "srl-feat:internal-tags";
      max-elements 2;
      type string;
      description
        "Internal route tag written in the route/tunnel tables or BGP rib

         The internal-tag value is shown with the format 'type-string = hex-value-string'.
         For example:
         - tag-value = ff:ff
         - tag-value = 20";
    }
  }

  grouping ipv4-ipv6-entry-common-fields {
    leaf route-type {
      type identityref {
        base srl_nokia-comm:ip-route-type;
      }
      srl_nokia-ext:show-importance "high";
      description
        "The type of the IP route";
    }
    leaf route-owner {
      type string;
      srl_nokia-ext:show-importance "high";
      description
        "The application name of the owner of the IP route";
    }
    leaf origin-network-instance {
      type leafref {
        path "/srl_nokia-netinst:network-instance/srl_nokia-netinst:name";
      }
      description
        "Origin network instance of the route (where it was originally learned or configured)

         If the route was leaked from another network instance, the value of this leaf reflects the network-instance from which it was learned. If it was not leaked the value is the same as the parent network-instance.";
    }
    leaf leakable {
      if-feature "srl-feat:route-leaking";
      description
        "Reads true when the route was matched and accepted by the route-leaking inter-instance export-policy";
      type boolean;
    }
    leaf leaked {
      if-feature "srl-feat:route-table-show-report-improvements";
      description
        "Reads true when the route was leaked into this network-instance from another network-instance";
      type boolean;
    }
    leaf-list target-network-instances {
      type leafref {
        path "/srl_nokia-netinst:network-instance/srl_nokia-netinst:name";
      }
      description
        "List of network-instances that have imported this route as a result of matching and accepting it in their inter-instance import-policy";
    }
    leaf metric {
      type uint32;
      srl_nokia-ext:show-importance "high";
      description
        "The metric of the IP route. In general, when comparing two routes with the same owner and preference, the route with the lower metric is the one that is activated and used for forwarding.";
    }
    leaf preference {
      type uint8;
      srl_nokia-ext:show-importance "high";
      description
        "The IP route table preference. This is sometimes called the administrative distance of the route. In general, when comparing any two routes, the route with the lower preference is the one that is activated and used for forwarding.";
    }
    leaf active {
      type boolean;
      srl_nokia-ext:show-importance "high";
      description
        "If set to true then the route is installed as the active route for the IP prefix in the FIB. A route can be inactive because there is a more preferred route for the same prefix or else its next-hops are unresolved.";
    }
    leaf route-limit-exceeded {
      if-feature "srl-feat:network-instance-route-limits";
      description
        "Reads true when, at the time the route was received by FIB manager, the current route count was over the specified maximum for the family";
      type boolean;
    }
    leaf last-app-update {
      type srl_nokia-comm:date-and-time-delta;
      description
        "The date and time of the last update of this route by the owning application or protocol.";
    }
    leaf next-hop-group {
      type leafref {
        path "../../../next-hop-group/index";
      }
      description
        "The next-hop-group indirection object used by this route.";
    }
    leaf next-hop-group-network-instance {
      type leafref {
        path "/srl_nokia-netinst:network-instance/srl_nokia-netinst:name";
      }
      description
        "The network instance where the next-hop-group can be found.  If unspecified, the next hop group is in the local network instance.";
    }
    leaf gribi-metadata {
      type binary {
        length "0..8";
      }
      description
        "Metadata persistently stored with the entry.";
    }
    leaf resilient-hash {
      type boolean;
      description
        "Set to true if the route is covered by a resilient-hash-prefix entry or policy action applied in this network-instance";
    }
    leaf dynamic-load-balancing {
      type boolean;
      description
        "Set to true if the route is covered by a dynamic-load-balancing prefix configured in this network-instance

         True does not guarantee that the route is programmed for DLB. This information is found in the NHG used by the route";
    }
    leaf group-based-policy-tag {
      if-feature "srl-feat:group-based-policy";
      type uint16 {
        range "0..65535";
      }
      srl_nokia-ext:show-importance "high";
      description
        "The group-based-policy tag value associated to this IP route";
    }
    uses traffic-statistics;
    uses internal-tags;
    uses fib-programming-status;
  }

  grouping fib-programming-status {
    container fib-programming {
      description
        "Enter the fib-programming context

         Container for state related to the FIB programming of the object";
      leaf suppressed {
        description
          "When true, FIB programming for this entry has been suppressed and it is only installed in the control plane route table";
        type boolean;
      }
      leaf last-successful-operation-type {
        type operation-type;
        description
          "The last operation type that completed successfully, if the entry was not suppressed.";
      }
      leaf last-successful-operation-timestamp {
        type srl_nokia-comm:date-and-time-delta;
        description
          "The date and time of the last operation to complete successfully, if the entry was not suppressed.

           A delete operation is immediately timestamped by FIB manager on the assumption that it will ultimately be successful on all complexes. For other operations the timestamp is generated when the last complex that was expected to respond has responded with a success acknowledgement.";
      }
      leaf pending-operation-type {
        type operation-type;
        description
          "The current operation type that is in progress because not all complexes have responded.";
      }
      leaf last-failed-operation-type {
        type operation-type;
        description
          "The last operation type that failed.";
      }
      leaf-list last-failed-locations {
        description
          "List of forwarding complexes that reported a failure for the last operation. They appear in the format (slot-number,complex-number).";
        type failed-complex-list-including-control;
      }
    }
  }

  grouping ip-table-statistics {
    container statistics {
      leaf active-routes {
        type uint32;
        description
          "The total number of prefixes, belonging to this address family, with an active route in the FIB.";
      }
      leaf active-routes-with-ecmp {
        type uint32;
        description
          "The total number of prefixes, belonging to this address family, that have an active route in the FIB with multiple ECMP next-hops.";
      }
      leaf leaked-routes {
        if-feature "srl-feat:route-table-show-report-improvements";
        type uint32;
        description
          "The total number of prefixes, belonging to this address family, that have been leaked into this network-instance from another network-instance";
      }
      leaf resilient-hash-routes {
        type uint32;
        description
          "The total number of prefixes, belonging to this address family, with an active route in the FIB that have resilient hash support

           This count excludes routes with resilient hashing behavior enabled by configuration in another network-instance and then leaked into this network-instance.";
      }
      leaf dynamic-load-balancing-routes {
        if-feature "srl-feat:route-table-show-report-improvements";
        type uint32;
        description
          "The total number of prefixes, belonging to this address family, with an active route in the FIB that has dynamic LB support

           This count excludes routes with dynamic load-balancing behavior enabled by configuration in another network-instance and then leaked into this network-instance.";
      }
      leaf fib-failed-routes {
        type uint32;
        description
          "The total number of prefixes, belonging to this address family, that were not installed successfully because datapath resources were unavailable";
      }
      leaf fib-suppressed-routes {
        if-feature "srl-feat:route-table-show-report-improvements";
        type uint32;
        description
          "The total number of prefixes, belonging to this address family, that fib-mgr purposely did not try to install in the datapath";
      }
      leaf routes-with-per-prefix-statistics {
        if-feature "srl-feat:route-table-show-report-improvements";
        type uint32;
        description
          "The total number of prefixes, belonging to this address family, that have counter resources allocated for statistics collection";
      }
      leaf total-routes {
        type srl_nokia-comm:zero-based-counter64;
        description
          "The total number of routes, active and inactive, belonging to this address family, that are present in the routing table";
      }
      description
        "Enter the statistics context";
    }
  }

  grouping route-summary {
    container route-summary {
      description
        "Enter the route-summary context

         Route summary information";
      list route-type {
        key "ip-route-type-name";
        leaf ip-route-type-name {
          type identityref {
            base srl_nokia-comm:ip-route-type;
          }
          description
            "IP route type";
        }
        leaf active-routes {
          type uint32;
          description
            "Total number of prefixes associated with this route type that were submitted to fib-mgr and that fib-mgr successfully installed as active routes";
        }
      }
    }
  }

  grouping entry-programming-progress {
    leaf entries-remaining-to-add {
      type uint64;
      description
        "The number of entries that need to be created in order to reach synchronization with the CPM";
    }
    leaf entries-remaining-to-modify {
      type uint64;
      description
        "The number of entries that need to be modified in order to reach synchronization with the CPM";
    }
    leaf last-sync-time {
      type srl_nokia-comm:date-and-time-delta;
      description
        "The time when the forwarding complex last reached sync with the control plane

         A linecard reaches sync when both entries-remaining-to-add and entries-remaining-to-modify reach zero";
    }
  }

  grouping ip-tables-top {
    container ipv4-unicast {
      description
        "Enter the ipv4-unicast context

         The container for the IPv4 unicast routing table of the network instance.";
      list route {
        key "ipv4-prefix route-type route-owner id origin-network-instance";
        leaf ipv4-prefix {
          type srl_nokia-comm:ipv4-prefix;
          description
            "The IPv4 prefix associated with the route.";
        }
        leaf id {
          type uint32;
          description
            "An owner-assigned index value that is unique for each of the routes for a given prefix.";
        }
        uses ipv4-ipv6-entry-common-fields;
      }
      uses ip-table-statistics;
      uses route-summary;
      container prefix-length-distribution {
        if-feature "srl-feat:route-table-show-report-improvements";
        list length {
          description
            "List of prefix lengths";
          key "prefix-length";
          leaf prefix-length {
            description
              "The prefix length of the route";
            type uint8 {
              range "0..32";
            }
          }
          leaf active-routes {
            type uint32;
            description
              "Total number of prefixes with this prefix length that were submitted to fib-mgr and that fib-mgr successfully installed as active routes";
          }
        }
        description
          "Enter the prefix-length-distribution context";
      }
    }
    container ipv6-unicast {
      description
        "Enter the ipv6-unicast context

         The container for the IPv6 unicast routing table of the network instance.";
      list route {
        key "ipv6-prefix route-type route-owner id origin-network-instance";
        leaf ipv6-prefix {
          type srl_nokia-comm:ipv6-prefix;
          description
            "The IPv6 prefix associated with the route.";
        }
        leaf id {
          type uint32;
          description
            "An owner-assigned index value that is unique for each of the routes for a given prefix.";
        }
        uses ipv4-ipv6-entry-common-fields;
      }
      uses ip-table-statistics;
      uses route-summary;
      container prefix-length-distribution {
        if-feature "srl-feat:route-table-show-report-improvements";
        list length {
          description
            "List of prefix lengths";
          key "prefix-length";
          leaf prefix-length {
            description
              "The prefix length of the route";
            type uint8 {
              range "0..128";
            }
          }
          leaf active-routes {
            type uint32;
            description
              "Total number of prefixes with this prefix length that were submitted to fib-mgr and that fib-mgr successfully installed as active routes";
          }
        }
        description
          "Enter the prefix-length-distribution context";
      }
    }
  }

  grouping fib-programming-progress {
    container programming-progress {
      description
        "Enter the programming-progress context

         State that shows the FIB programming progress of the forwarding complex";
      container ip-routes {
        description
          "Enter the ip-routes context

           Container for the FIB programming state of IP route entries";
        uses entry-programming-progress;
      }
      container next-hop-groups {
        description
          "Enter the next-hop-groups context

           Container for the FIB programming state of next-hop-group (NHG) entries";
        uses entry-programming-progress;
      }
      container mpls-labels {
        if-feature "srl-feat:fib-ilm-programming";
        description
          "Enter the mpls-labels context

           Container for the FIB programming state of ILM entries";
        uses entry-programming-progress;
      }
      container tunnels {
        if-feature "srl-feat:fib-tunnel-programming";
        description
          "Enter the tunnels context

           Container for the FIB programming state of tunnels";
        uses entry-programming-progress;
      }
    }
  }

  grouping next-hops-top {
    list next-hop-group {
      key "index";
      leaf index {
        type uint64;
        description
          "A system-wide unique identifier of a next-hop-group indirection object (system allocated).";
      }
      leaf group-name-alias {
        type string;
        description
          "The alias name associated with this next-hop-group.";
      }
      leaf programmed-index {
        type uint64;
        description
          "The index assigned to the next-hop-group by the gRIBI client";
      }
      leaf backup-next-hop-group {
        type leafref {
          path "../index";
        }
        description
          "The backup next-hop-group for the current group. When all entries within the next-hop group become unusable, the backup next-hop group is used if specified.";
      }
      leaf backup-active {
        description
          "When true, this NHG is not being used to forward traffic and its backup NHG is being relied upon to provide reachability";
        type boolean;
      }
      container dynamic-load-balancing {
        if-feature "srl-feat:dynamic-load-balancing";
        leaf requested {
          description
            "Reads true when the NHG is used by one or more routes that are covered by DLB prefixes";
          type boolean;
        }
        leaf enabled {
          description
            "Reads true when the NHG has been programmed into the datapath with DLB support";
          type boolean;
        }
        leaf flows-rebalanced {
          description
            "Number of times the NHG has been re-programmed to move flows to new ECMP members

             This increments by one every time any flow in the flowset is inactive and it is moved to a new ECMP member";
          type srl_nokia-comm:zero-based-counter64;
        }
        description
          "Enter the dynamic-load-balancing context";
      }
      uses fib-programming-status;
      list next-hop {
        description
          "List of primary next-hops associated with the NHG";
        key "id";
        leaf id {
          type uint16 {
            range "0..1023";
          }
          description
            "A unique identifier of a next-hop member (system allocated).";
        }
        leaf next-hop {
          type leafref {
            path "../../../next-hop/index";
          }
        }
        leaf weight {
          type uint64;
          description
            "The configured/programmed weight assigned to the next-hop within the group

             This may be different from the actual weight used by the datapath, which changes depending on the next-hops that are up/down in the group. Traffic is balanced across the next-hops within the group in proportion of the actual weight.";
        }
        leaf resolved {
          type enumeration {
            enum true;
            enum false;
            enum not-applicable;
          }
          description
            "Set to true when the next-hop was resolved. This reads not-applicable for resolve=false next-hops.";
        }
        leaf resource-allocation-failed {
          type boolean;
          description
            "True when an available resource was not available for this next-hop";
        }
      }
      list backup-next-hop {
        description
          "List of backup next-hops associated with the NHG";
        key "id";
        leaf id {
          type uint16 {
            range "0..1023";
          }
          description
            "A unique identifier of a next-hop member (system allocated).";
        }
        leaf next-hop {
          type leafref {
            path "../../../next-hop/index";
          }
        }
        leaf resolved {
          type enumeration {
            enum true;
            enum false;
            enum not-applicable;
          }
          description
            "Set to true when the next-hop was resolved. This reads not-applicable for resolve=false next-hops.";
        }
        leaf resource-allocation-failed {
          type boolean;
          description
            "True when an available resource was not available for this next-hop";
        }
      }
    }
    list next-hop {
      srl_nokia-ext:telemetry-atomic "true";
      key "index";
      leaf index {
        type uint64;
        description
          "A system-wide unique identifier of a next-hop object (system allocated).";
      }
      leaf resource-allocation-failed {
        type boolean;
        description
          "True when an available resource was not available for this next-hop";
      }
      leaf programmed-index {
        type uint64;
        description
          "The index assigned to the next-hop by the gRIBI client";
      }
      leaf type {
        type identityref {
          base fib-nexthop-type;
        }
        srl_nokia-ext:show-importance "high";
        description
          "The next-hop type used by the datapath.";
      }
      leaf ip-address {
        type srl_nokia-comm:ip-address;
        srl_nokia-ext:show-importance "high";
        description
          "The next-hop IP address";
      }
      leaf subinterface {
        type leafref {
          path "/srl_nokia-if:interface/srl_nokia-if:subinterface/srl_nokia-if:name";
        }
        srl_nokia-ext:show-importance "high";
        description
          "The next-hop interface";
      }
      container interface-with-mac {
        description
          "Enter the interface-with-mac context

           State that applies to an interface+MAC next-hop";
        leaf mac-address {
          type srl_nokia-comm:mac-address;
          description
            "The MAC address of the next-hop that has been provided directly";
        }
      }
      container indirect {
        description
          "Enter the indirect context

           State that applies to an indirect next-hop";
        leaf resolved {
          type boolean;
          srl_nokia-ext:show-importance "high";
          description
            "Indicates whether the next-hop is reachable and has been resolved";
        }
        leaf usable {
          type boolean;
          description
            "Indicates whether the next-hop is usable

             It may not be usable if the indirect requires other indirect next-hops for resolution, exceeding the capabilities of the platform";
        }
        container resolving-route {
          leaf next-hop-group {
            type leafref {
              path "../../../../next-hop-group/index";
            }
            description
              "Reference to the next-hop-group used by the route that resolves this next-hop";
          }
          leaf ip-prefix {
            type srl_nokia-comm:ip-prefix;
            description
              "The prefix of the resolving route";
          }
          leaf route-type {
            type identityref {
              base srl_nokia-comm:ip-route-type;
            }
            description
              "The type of the resolving route";
          }
          leaf route-owner {
            type string;
            description
              "The application name of the owner of the resolving route";
          }
          description
            "Enter the resolving-route context";
        }
        container resolving-tunnel {
          leaf next-hop-group {
            type leafref {
              path "../../../../next-hop-group/index";
            }
            description
              "Reference to the next-hop-group used by the tunnel that resolves this next-hop";
          }
          leaf ip-prefix {
            type srl_nokia-comm:ip-prefix;
            description
              "The endpoint of the resolving tunnel";
          }
          leaf tunnel-type {
            type identityref {
              base srl_nokia-comm:tunnel-type;
            }
            description
              "The type of the tunnel";
          }
          leaf tunnel-owner {
            type string;
            description
              "The application name of the owner of the resolving tunnel";
          }
          leaf tunnel-id {
            type uint32;
            description
              "An owner-assigned index value that is unique for each of the tunnels terminating at a particular prefix";
          }
          description
            "Enter the resolving-tunnel context";
        }
      }
      container redirect {
        description
          "Enter the redirect context

           State that applies to a redirect next-hop";
        leaf network-instance {
          type leafref {
            path "/srl_nokia-netinst:network-instance/srl_nokia-netinst:name";
          }
          srl_nokia-ext:show-importance "high";
          description
            "Indicates that the next-hop is another network instance

             A new IP lookup should occur in the other network instance.";
        }
      }
      container mpls {
        description
          "Enter the mpls context

           State that applies to an MPLS next-hop";
        container tunnel {
          uses tunnel-next-hop-fields;
          description
            "Enter the tunnel context";
        }
        leaf next-hop-group {
          type leafref {
            path "../../../next-hop-group/index";
          }
          description
            "The next-hop-group indirection object used by MPLS nexthop.";
        }
      }
      container srv6 {
        if-feature "srl-feat:srv6 or srl-feat:srv6-usid-basic";
        description
          "Enter the srv6 context

           State that applies to an SRv6 next-hop";
        container tunnel {
          uses tunnel-next-hop-fields;
          description
            "Enter the tunnel context";
        }
      }
      container srv6-endpoint {
        if-feature "srl-feat:srv6 or srl-feat:srv6-usid-basic";
        leaf sid-value {
          description
            "A local SRv6 SID";
          type srl_nokia-comm:ipv6-prefix;
        }
        leaf behavior {
          description
            "The type of SRv6 endpoint behavior encoded by the function";
          type identityref {
            base srl_nokia-srv6-types:srv6-endpoint-behavior;
          }
        }
        leaf locator-name {
          description
            "Associated SRv6 locator";
          type leafref {
            path "/srl_nokia-system:system/srl_nokia-sys-srv6:srv6/srl_nokia-sys-srv6:locator/srl_nokia-sys-srv6:locator-name";
          }
        }
        leaf srh-mode {
          type srl_nokia-srv6-types:srh-mode;
          description
            "Segment Routing Header (SRH) mode";
        }
        leaf block-length {
          description
            "Length of the block part of the SRv6 SID";
          type uint8;
        }
        container tunnel {
          uses tunnel-next-hop-fields;
          description
            "Enter the tunnel context";
        }
        description
          "Enter the srv6-endpoint context";
      }
      container tunnel {
        description
          "Enter the tunnel context

           State that applies to a tunnel next-hop";
        leaf encapsulate-header {
          type srl_nokia-comm:encapsulation-header-type;
          description
            "Packets matching this next-hop are encapsulated by adding the specified header

             Only populated when the tunnel is ip-in-ip.";
        }
        container ip-in-ip {
          description
            "Enter the ip-in-ip context

             Specifies details of the IP-in-IP header added to the packet. This is provided only when encapsulate-header is ipv4 or ipv6";
          leaf source-ip {
            type srl_nokia-comm:ip-address;
            description
              "Source IP address to use for the encapsulated packet.";
          }
          leaf destination-ip {
            type srl_nokia-comm:ip-address;
            description
              "Destination IP address to use for the encapsulated packet.";
          }
        }
        container gre {
          description
            "Enter the gre context

             Details of the GRE in IPv4 or IPv6 encapsulation";
          leaf source-ip {
            type srl_nokia-comm:ip-address;
            description
              "The source IP address in the outer IP header added by GRE encapsulation";
          }
          leaf destination-ip {
            type srl_nokia-comm:ip-address;
            description
              "Destination IP address in the outer IP header added by GRE encapsulation";
          }
          leaf ip-ttl {
            type uint8;
            description
              "IP TTL in the outer IP header added by GRE encapsulation";
          }
          leaf in-profile-dscp {
            type srl_nokia-comm:dscp-value;
            description
              "DSCP value in the outer IP header except when the packet is out of profile";
          }
          leaf out-profile-dscp {
            type srl_nokia-comm:dscp-value;
            description
              "DSCP value in the outer IP header when the packet was policed as out of profile";
          }
        }
        container udp {
          description
            "Enter the udp context

             Details of the UDP in IPv4 or IPv6 encapsulation";
          leaf source-ip {
            type srl_nokia-comm:ip-address;
            description
              "The source IP address in the outer IPv4 header";
          }
          leaf destination-ip {
            type srl_nokia-comm:ip-address;
            description
              "Destination IP address in the outer IPv4 header";
          }
          leaf destination-udp-port {
            type srl_nokia-comm:port-number;
            description
              "Destination UDP port number in the outer UDP header

               Usually this reflects the encoded payload type";
          }
          leaf ip-ttl {
            type uint8;
            description
              "The IP TTTL in the outer IP header";
          }
          leaf in-profile-dscp {
            type srl_nokia-comm:dscp-value;
            description
              "DSCP value in the outer IP header except when the packet is out of profile";
          }
          leaf out-profile-dscp {
            type srl_nokia-comm:dscp-value;
            description
              "DSCP value in the outer IP header when the packet was policed as out of profile";
          }
        }
        uses tunnel-next-hop-fields;
      }
      container mpls-encapsulation {
        leaf-list pushed-mpls-label-stack {
          type srl_nokia-comm:mpls-label-with-implicit-and-explicit-null;
          description
            "The list of MPLS labels to push onto the packet when forwarding to this particular next-hop.";
        }
        leaf entropy-label-transmit {
          description
            "Entropy label (EL/ELI) is pushed when transmitting to this next-hop";
          type boolean;
        }
        leaf traffic-class {
          type uint8 {
            range "0..7";
          }
          description
            "The value of the MPLS traffic class (TC) bits written into each pushed label";
        }
        description
          "Enter the mpls-encapsulation context";
      }
      container srv6-encapsulation {
        if-feature "srl-feat:srv6";
        description
          "Enter the srv6-encapsulation context

           Information about SRv6 encapsulation";
        leaf-list pushed-srv6-sid-stack {
          type srl_nokia-comm:ipv6-address;
          description
            "The list of SRv6 SIDs to push onto the packet when forwarding to this particular next-hop";
        }
        leaf source-address {
          type srl_nokia-comm:ipv6-address;
          description
            "Source IP address in the outer IPv6 header";
        }
      }
      container vxlan-encapsulation {
        leaf vni {
          type uint32 {
            range "1..16777215";
          }
          description
            "VXLAN Network Identifier of the destination.";
        }
        leaf interface {
          type srl_nokia-netinst:network-instance-vxlan-if-ref;
          description
            "The VXLAN interface.";
        }
        leaf destination-mac {
          type srl_nokia-comm:mac-address;
          description
            "VXLAN inner ethernet destination mac-address.";
        }
        description
          "Enter the vxlan-encapsulation context";
      }
      leaf decapsulate-header {
        description
          "Packets matching this next-hop are decapsulated by removing the specified header.";
        type srl_nokia-comm:encapsulation-header-type;
      }
      uses traffic-statistics;
    }
  }

  augment "/srl_nokia-netinst:network-instance/srl_nokia-netinst:route-table" {
    uses ip-tables-top;
    uses next-hops-top;
  }

  augment "/srl_nokia-platform:platform/srl_nokia-platform-lc:linecard/srl_nokia-platform-lc:forwarding-complex/srl-lc-fib:fib-table" {
    uses fib-programming-progress {
      if-feature "srl-feat:fib-programming-progress";
    }
  }

  augment "/srl_nokia-platform:platform/srl_nokia-platform-control:control/srl_nokia-platform-control-fp:forwarding-plane/srl_nokia-platform-control-fp:fib-table" {
    uses fib-programming-progress {
      if-feature "srl-feat:fib-programming-progress";
    }
  }
}
