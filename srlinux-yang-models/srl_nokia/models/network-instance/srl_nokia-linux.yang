module srl_nokia-linux {
  yang-version 1.1;
  namespace "urn:nokia.com:srlinux:linux:linux";
  prefix srl_nokia-linux;

  import srl_nokia-network-instance {
    prefix srl_nokia-netinst;
  }

  organization
    "Nokia";
  contact
    "Nokia SR Linux Support
     Web: <http://www.nokia.com>";
  description
    "This YANG file gives a description of network-instance interface to linux";

  revision 2026-07-31 {
    description
      "SRLinux 26.7.1";
  }
  revision 2019-11-30 {
    description
      "SRLinux 19.11.1";
  }

  grouping linux-top {
    container linux {
      description
        "Enter the linux context

         Enables routing interaction with the Linux kernel";
      leaf import-routes {
        type boolean;
        default "false";
        description
          "Import routes from linux routing table";
      }
      leaf export-routes {
        type boolean;
        default "false";
        description
          "Export routes to linux routing table";
      }
      leaf export-neighbors {
        type boolean;
        default "true";
        description
          "Export neighbors to linux routing table";
      }
    }
  }

  augment "/srl_nokia-netinst:network-instance/srl_nokia-netinst:protocols" {
    uses linux-top;
  }
}
