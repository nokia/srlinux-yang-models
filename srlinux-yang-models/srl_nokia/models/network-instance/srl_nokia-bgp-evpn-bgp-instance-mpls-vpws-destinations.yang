module srl_nokia-bgp-evpn-bgp-instance-mpls-vpws-destinations {
  yang-version 1.1;
  namespace "urn:srl_nokia/network-instance/protocols/bgp-evpn/bgp-instance/mpls/vpws-destinations";
  prefix srl_nokia-bgp-evpn-bgp-instance-mpls-vpws_destinations;

  import srl_nokia-common {
    prefix srl_nokia-comm;
  }
  import srl_nokia-network-instance {
    prefix srl_nokia-netinst;
  }
  import srl_nokia-extensions {
    prefix srl_nokia-ext;
  }
  import srl_nokia-bgp-evpn {
    prefix srl_bgp-evpn;
  }

  organization
    "Nokia";
  contact
    "Nokia SR Linux Support
     Web: <http://www.nokia.com>";
  description
    "Model for vpws destinations on the bgp-evpn mpls instance";

  revision 2023-07-31 {
    description
      "SRLinux 23.7.1";
  }

  grouping evpn-mpls-vpws-destinations-destination-top {
    list destination {
      config false;
      key "tep evi-label tunnel-id connection-point";
      leaf tep {
        srl_nokia-ext:show-importance "high";
        type srl_nokia-comm:ip-address;
        description
          "The IP address that identifies the remote EVPN Termination Endpoint (TEP).";
      }
      leaf evi-label {
        type srl_nokia-comm:mpls-label-non-reserved;
        srl_nokia-ext:show-importance "high";
        description
          "EVI label of the destination.";
      }
      leaf tunnel-id {
        type uint64;
        srl_nokia-ext:show-importance "high";
        description
          "tunnel identitier of the destination.";
      }
      leaf connection-point {
        type string;
        description
          "The connection-point this destination is associated to.";
      }
      leaf destination-index {
        type uint64;
        srl_nokia-ext:show-importance "high";
        description
          "A system-wide unique identifier of this evpn-mpls destination object (system allocated).";
      }
      leaf not-programmed-reason {
        srl_nokia-ext:show-importance "high";
        type enumeration {
          enum no-destination-index;
        }
        description
          "The reason why the evpn-mpls destination is not programmed.";
      }
    }
  }

  grouping evpn-mpls-vpws-destinations-es-destination-next-hops-top {
    list destination {
      config false;
      key "tep evi-label tunnel-id";
      leaf tep {
        srl_nokia-ext:show-importance "high";
        type srl_nokia-comm:ip-address;
        description
          "The IP address that identifies the remote EVPN Termination Endpoint (TEP).";
      }
      leaf evi-label {
        type srl_nokia-comm:mpls-label-non-reserved;
        srl_nokia-ext:show-importance "high";
        description
          "EVI label of this next-hop.";
      }
      leaf tunnel-id {
        type uint64;
        srl_nokia-ext:show-importance "high";
        description
          "tunnel identitier of this next-hop.";
      }
    }
  }

  grouping evpn-mpls-vpws-destinations-es-destination-top {
    list es-destination {
      config false;
      key "esi connection-point";
      leaf esi {
        type srl_nokia-comm:esi;
        srl_nokia-ext:show-importance "high";
        description
          "The 10-byte Ethernet Segment Identifier of the ethernet segment.
           ESI-0 or MAX-ESI values are not allowed.";
      }
      leaf connection-point {
        type string;
        description
          "The connection-point this destination is associated to.";
      }
      leaf destination-index {
        type uint64;
        srl_nokia-ext:show-importance "high";
        description
          "A system-wide unique identifier of this evpn-mpls destination object (system allocated).";
      }
      leaf not-programmed-reason {
        srl_nokia-ext:show-importance "high";
        type enumeration {
          enum no-destination-index;
        }
        description
          "The reason why the evpn-mpls destination is not programmed.";
      }
      uses evpn-mpls-vpws-destinations-es-destination-next-hops-top;
    }
  }

  grouping evpn-mpls-vpws-destinations-top {
    container vpws-destinations {
      config false;
      uses evpn-mpls-vpws-destinations-destination-top;
      uses evpn-mpls-vpws-destinations-es-destination-top;
    }
  }

  augment "/srl_nokia-netinst:network-instance/srl_nokia-netinst:protocols/srl_nokia-netinst:bgp-evpn/srl_bgp-evpn:bgp-instance/srl_bgp-evpn:mpls" {
    uses evpn-mpls-vpws-destinations-top;
  }
}
