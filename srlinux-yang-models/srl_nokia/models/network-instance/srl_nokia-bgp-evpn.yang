module srl_nokia-bgp-evpn {
  yang-version 1.1;
  namespace "urn:nokia.com:srlinux:net-inst:bgp-evpn";
  prefix srl_nokia-bgp-evpn;

  import srl_nokia-common {
    prefix srl_nokia-comm;
  }
  import srl_nokia-network-instance {
    prefix srl_nokia-netinst;
  }
  import srl_nokia-extensions {
    prefix srl_nokia-ext;
  }
  import srl_nokia-bgp-vpn {
    prefix srl_bgp-vpn;
  }
  import srl_nokia-bgp {
    prefix srl-bgp;
  }
  import srl_nokia-routing-policy {
    prefix srl_nokia-routing-pol;
  }
  import srl_nokia-features {
    prefix srl_nokia-feat;
  }
  import srl_nokia-system-network-instance-bgp-evpn-ethernet-segments {
    prefix srl_nokia-system-bgp-evpn-ethernet-segments;
  }
  import srl_nokia-srv6 {
    prefix srl_nokia-srv6;
  }
  import srl_nokia-srv6-instance {
    prefix srl_nokia-srv6-inst;
  }
  import srl_nokia-system {
    prefix srl_nokia-system;
  }
  import srl_nokia-segment-routing {
    prefix srl_nokia-sr;
  }
  import srl_nokia-group-based-policy {
    prefix srl_nokia-gbp;
  }
  import srl_nokia-pim {
    prefix srl_nokia-pim;
  }
  import srl_nokia-igmp {
    prefix srl_nokia-igmp;
  }
  import srl_nokia-mld {
    prefix srl_nokia-mld;
  }

  organization
    "Nokia";
  contact
    "Nokia SR Linux Support
     Web: <http://www.nokia.com>";
  description
    "This yang file models configuration and state of the bgp-evpn protocol";

  revision 2026-07-31 {
    description
      "SRLinux 26.7.1";
  }
  revision 2026-04-30 {
    description
      "SRLinux 26.3.2";
  }
  revision 2026-03-31 {
    description
      "SRLinux 26.3.1";
  }
  revision 2025-10-31 {
    description
      "SRLinux 25.10.1";
  }
  revision 2025-07-31 {
    description
      "SRLinux 25.7.1";
  }
  revision 2024-10-31 {
    description
      "SRLinux 24.10.1";
  }
  revision 2024-07-31 {
    description
      "SRLinux 24.7.1";
  }
  revision 2024-03-31 {
    description
      "SRLinux 24.3.1";
  }
  revision 2023-07-31 {
    description
      "SRLinux 23.7.1";
  }
  revision 2023-03-31 {
    description
      "SRLinux 23.3.1";
  }
  revision 2022-06-30 {
    description
      "SRLinux 22.6.1";
  }
  revision 2022-03-31 {
    description
      "SRLinux 22.3.1";
  }
  revision 2021-11-30 {
    description
      "SRLinux 21.11.1";
  }
  revision 2021-03-31 {
    description
      "SRLinux 21.3.1";
  }

  typedef ethernet-tag-id {
    description
      "The Ethernet Tag ID encoded in the NLRI. The Ethernet Tag ID identifies a broadcast domain.";
    type uint32 {
      range "0..16777215";
    }
  }

  typedef evpn-multicast-gateway-type {
    description
      "The type of EVPN multicast gateway";
    type enumeration {
      enum peg {
        value 1;
      }
      enum peg-transit {
        value 2;
      }
    }
  }

  grouping multicast-evpn-gateway-dr-candidates-info {
    container computed-designated-router-candidates {
      list designated-router-candidate {
        key "address";
        description
          "designated router PEG/MEG gateway candidates";
        leaf address {
          type srl_nokia-comm:ip-address;
          srl_nokia-ext:show-importance "high";
        }
        leaf add-time {
          type srl_nokia-comm:date-and-time-delta;
          description
            "The date and time when the designated-router-candidate was added to the designated router candidate list";
          srl_nokia-ext:show-importance "high";
        }
        leaf designated-router {
          type boolean;
          default "false";
          description
            "Indicates if this designated-router-candidate is the designated-router.";
          srl_nokia-ext:show-importance "high";
        }
      }
      description
        "Enter the computed-designated-router-candidates context";
    }
  }

  grouping multicast-evpn-gateway-dr-election {
    container dr-election {
      description
        "Enter the dr-election context

         DR election configuration";
      container timers {
        leaf dr-activation-timer {
          type uint32 {
            range "0..100";
          }
          units "seconds";
          default "3";
          description
            "Specifies the DR activation timer for the EVPN gateway

             The Designated Router (DR) activation timer determines for how long the router waits
             to run the DR election as a MEG or PEG Gateway. This gives some time to collect
             Inclusive Multicast Ethernet Tag routes from other MEG/PEG gateways to avoid running
             the DR election multiple times.";
        }
        description
          "Enter the timers context";
      }
    }
  }

  grouping multicast-evpn-gateway {
    container evpn-multicast-gateway {
      if-feature "srl_nokia-feat:evpn-vxlan-oism-peg";
      presence "Configure EVPN multicast gateway functionality";
      description
        "Configuration for EVPN multicast gateway functionality in EVPN OISM

         This enables MEG (MVPN to EVPN) or PEG (PIM to EVPN Gateway) functionality
         in EVPN OISM networks.";
      leaf admin-state {
        type srl_nokia-comm:admin-state;
        default "disable";
        description
          "Administrative state for the EVPN gateway functionality

           When enabled, the system will participate in EVPN gateway DR (Designated Router)
           election and will behave as a multicast gateway between MVPN/PIM and EVPN. The
           DR triggers the MEG/PEG First Hop and Last Hop actions on the router.";
      }
      leaf gateway-type {
        srl_nokia-ext:show-importance "high";
        type evpn-multicast-gateway-type;
        description
          "Type of EVPN multicast gateway";
        mandatory true;
      }
      leaf non-dr-attract-traffic {
        type boolean;
        default "false";
        description
          "When enabled, allows a non-Designated Router to attract traffic

           When set to true, the router triggers the advertisement of a wildcard SMET route that
           will attract the traffic from OISM sources, irrespective of the router being MEG/PEG DR.
           This can be used to speed up the convergence of the network in case of a DR change.";
      }
      uses multicast-evpn-gateway-dr-election;
    }
  }

  grouping bgp-evpn-oism {
    description
      "Grouping containing the configuration and state for the use of EVPN OISM in 7250 IXR platforms";
    container optimized-inter-subnet-multicast-forwarding {
      if-feature "srl_nokia-feat:ixr-dnx and srl_nokia-feat:evpn-vxlan-oism";
      presence "Configure EVPN OISM functionality";
      must '(/srl_nokia-netinst:network-instance[srl_nokia-netinst:name = current()/../../../srl_nokia-netinst:name]/srl_nokia-netinst:type = "srl_nokia-netinst:ip-vrf")' {
        error-message "The optimized-inter-subnet-multicast-forwarding command can only be enabled on network-instances of type ip-vrf";
      }
      must '(/srl_nokia-netinst:network-instance[srl_nokia-netinst:name = current()/../../../srl_nokia-netinst:name]/srl_nokia-netinst:protocols/srl_nokia-pim:pim/srl_nokia-pim:admin-state = "enable")' {
        error-message "The optimized-inter-subnet-multicast-forwarding command can only be enabled when PIM is enabled on the ip-vrf network-instance";
      }
      must '(/srl_nokia-netinst:network-instance[srl_nokia-netinst:name = current()/../../../srl_nokia-netinst:name]/srl_nokia-netinst:protocols/srl_nokia-igmp:igmp/srl_nokia-igmp:admin-state = "enable" or /srl_nokia-netinst:network-instance[srl_nokia-netinst:name = current()/../../../srl_nokia-netinst:name]/srl_nokia-netinst:protocols/srl_nokia-mld:mld/srl_nokia-mld:admin-state = "enable")' {
        error-message "The optimized-inter-subnet-multicast-forwarding command can only be enabled when IGMP or MLD is enabled on the ip-vrf network-instance";
      }
      description
        "Configuration for EVPN OISM functionality in 7250 IXR platforms

         This command enables the use of the optimized inter-subnet multicast forwarding functionality
         in 7250 IXR platforms. An multicast-enabled SBD IRB interface cannot be attached to the IP-VRF network-instance
         unless this command is enabled. This command can only be enabled when PIM and IGMP or MLD are enabled on the IP-VRF
         network-instance.";
    }
  }

  grouping supplementary-bd {
    description
      "Grouping containing the configuration and state for the use of supplementary broadcast domains";
    container supplementary-broadcast-domain {
      presence "Configure the MAC-VRF as a supplementary broadcast domain for the EVPN-IFF model";
      if-feature "srl_nokia-feat:evpn-iff";
      must '/srl_nokia-netinst:network-instance[srl_nokia-netinst:name = current()/../../../../srl_nokia-netinst:name]/srl_nokia-netinst:type = "srl_nokia-netinst:mac-vrf"' {
        error-message "The supplementary-broadcast-domain command can only be enabled on network-instances of type mac-vrf";
      }
      must 'not(/srl_nokia-netinst:network-instance[srl_nokia-netinst:name = current()/../../../../srl_nokia-netinst:name]/srl_nokia-gbp:group-based-policy)' {
        error-message "The supplementary-broadcast-domain command can only be enabled when group-based-policy is not configured";
      }
      uses multicast-evpn-gateway;
    }
  }

  grouping evpn-ifl-gw-ip {
    description
      "Grouping containing the configuration and state for the use of GW-IP load balancing for EVPN IFL routes";
    container evpn-interface-less-gateway-ip {
      if-feature "srl_nokia-feat:evpn-ifl-gw-ip";
      container advertise {
        presence "Enables the advertisement of non-zero GW-IP addresses in EVPN IFL routes";
        must '/srl_nokia-netinst:network-instance[srl_nokia-netinst:name = current()/../../../../../../../../srl_nokia-netinst:name]/srl_nokia-netinst:type = "srl_nokia-netinst:ip-vrf"' {
          error-message "The EVPN-IFL gateway-ip advertisement can only be enabled on network-instances of type ip-vrf";
        }
        must 'not(../../srl_nokia-bgp-evpn:evpn-link-bandwidth/srl_nokia-bgp-evpn:advertise)' {
          error-message "The EVPN-IFL gateway-ip advertisement is only supported on bgp-evpn instances where the evpn-link-bandwidth advertisement is not configured";
        }
      }
      container resolve {
        leaf admin-state {
          type srl_nokia-comm:admin-state;
          must '. = "disable" or (. = "enable" and (/srl_nokia-netinst:network-instance[srl_nokia-netinst:name = current()/../../../../../../../../../srl_nokia-netinst:name]/srl_nokia-netinst:type = "srl_nokia-netinst:ip-vrf"))' {
            error-message "The resolve command can only be enabled on network-instances of type ip-vrf";
          }
          must '. = "disable" or (. = "enable" and (../../../srl_nokia-bgp-evpn:evpn-link-bandwidth/srl_nokia-bgp-evpn:weighted-ecmp/srl_nokia-bgp-evpn:admin-state = "disable"))' {
            error-message "The EVPN-IFL gateway-ip resolve can only be enabled on bgp-evpn instances where the evpn-link-bandwidth weighted-ecmp is disabled";
          }
          default "disable";
          description
            "Enable triggers the resolution of EVPN IFL routes GW-IP to EVPN-IFL-HOST routes

             When set to enable, the router processes the GW-IP field in the EVPN-IFL routes, and tries to resolve
             the GW-IP to the next hops of the received EVPN-IFL-HOST (MAC/IP Advertisement routes with layer 3
             information) routes that contain the GW-IP. If more than one EVPN-IFL-HOST route resolves the GW-IP of
             the EVPN-IFL route, the EVPN-IFL route is programmed with a next hop group that contains all the next
             hops of the EVPN-IFL-HOST routes. Weights are used to influence the load balancing when multiple
             EVPN-IFL-HOST routes resolving the IP Prefix come from the same next-hop.";
        }
        leaf max-ecmp-hash-buckets-per-next-hop-group {
          type uint16 {
            range "1..256";
          }
          description
            "Specifies the maximum number of ECMP hash buckets per next-hop-group

             Weighted ECMP weights are normalized based on this number of hash buckets.";
          must '. <= 64' {
            error-message "Valid range for max-ecmp-hash-buckets-per-next-hop-group:[1..64] ";
            srl_nokia-ext:if-feature "srl_nokia-feat:fpcx";
          }
          must '. <= 128' {
            error-message "Valid range for max-ecmp-hash-buckets-per-next-hop-group:[1..128] ";
            srl_nokia-ext:if-feature "srl_nokia-feat:trident3 or srl_nokia-feat:trident4";
          }
          must '. <= 256' {
            error-message "Valid range for max-ecmp-hash-buckets-per-next-hop-group:[1..256] ";
            srl_nokia-ext:if-feature "srl_nokia-feat:ixr-dnx";
          }
        }
        description
          "Enter the resolve context";
      }
      description
        "Enter the evpn-interface-less-gateway-ip context";
    }
  }

  grouping evpn-unequal-ecmp {
    description
      "Grouping containing the configuration and state for unequal ECMP";
    container evpn-link-bandwidth {
      if-feature "srl_nokia-feat:evpn-ifl-unequal-ecmp";
      container advertise {
        presence "Enables the advertisement of the EVPN link bandwitdth extended community";
        leaf weight {
          type union {
            type uint32 {
              range "1..128";
            }
            type enumeration {
              enum dynamic {
                value -1;
              }
            }
          }
          default "dynamic";
          description
            "Determines the weight to be advertised in the evpn-link-bandwidth extended community

             If set to dynamic, the weight is dynamically set based on the number of BGP PE-CE paths
             for the IP Prefix that is advertised in an EVPN IP Prefix route. Alternatively, the
             weight can be set to a fixed integer value in the range 1..128. The dynamic weight only
             considers BGP PE-CE paths.";
        }
        leaf maximum-dynamic-weight {
          type uint32 {
            range "1..128";
          }
          default "128";
          description
            "Determines the maximum weight to be advertised in the evpn-link-bandwidth extended community

             If weight 'dynamic' is configured, the actual advertised weight is the minimum of the number
             of BGP PE-CE paths for the prefix and the configured maximum weight.";
        }
      }
      container weighted-ecmp {
        leaf admin-state {
          type srl_nokia-comm:admin-state;
          default "disable";
          description
            "Setting enable triggers weighted ECMP programming for all elegible multipath EVPN IFL routes

             When set to enable, the router processes the evpn-link-bandwidth extended community when installing
             an ECMP set for an EVPN IP-Prefix route in the ip-vrf route table. Flows to an IP Prefix received
             with a weight and a zero-ESI are sprayed based on the weight. If the EVPN IP Prefix route
             received with the weight has a non-zero ESI, the weight is divided into the number of PEs attached
             to the Ethernet Segment (and rounded up if the result is not an integer). The command also enables
             the weighted ECMP functionality for BGP CEs that are configured with the parameter evpn-link-bandwidth
             add-weight-to-received-bgp-routes <weight>.";
        }
        leaf max-ecmp-hash-buckets-per-next-hop-group {
          type uint16 {
            range "1..256";
          }
          description
            "Specifies the maximum number of ECMP hash buckets per next-hop-group

             Weighted ECMP weights are normalized based on this number of hash buckets.";
          must '. <= 64' {
            error-message "Valid range for max-ecmp-hash-buckets-per-next-hop-group:[1..64] ";
            srl_nokia-ext:if-feature "srl_nokia-feat:fpcx";
          }
          must '. <= 128' {
            error-message "Valid range for max-ecmp-hash-buckets-per-next-hop-group:[1..128] ";
            srl_nokia-ext:if-feature "srl_nokia-feat:trident3 or srl_nokia-feat:trident4";
          }
          must '. <= 256' {
            error-message "Valid range for max-ecmp-hash-buckets-per-next-hop-group:[1..256] ";
            srl_nokia-ext:if-feature "srl_nokia-feat:ixr-dnx";
          }
        }
        description
          "Enter the weighted-ecmp context";
      }
      description
        "Enter the evpn-link-bandwidth context";
    }
  }

  grouping evpn-anycast-l3-subnet {
    description
      "Grouping containing the configuration and state for EVPN Anycast for multi-homing L3 subnets";
    container anycast-multi-homing {
      if-feature "srl_nokia-feat:evpn-anycast-l3-subnet";
      presence "Enabled EVPN Anycast for multi-homing L3 subnets";
      must '(/srl_nokia-netinst:network-instance[srl_nokia-netinst:name = current()/../../../../../../../srl_nokia-netinst:name]/srl_nokia-netinst:type = "srl_nokia-netinst:ip-vrf")' {
        error-message "The anycast multi-homing L3 subnet configuration is possible only on network-instances of type ip-vrf";
      }
      must "../../../../encapsulation-type = 'vxlan'" {
        error-message "The anycast multi-homing L3 subnet configuration is possible only when encapsulation-type is vxlan";
      }
      description
        "Configuration for EVPN Anycast for multi-homing L3 subnets";
      leaf ip-address {
        type union {
          type srl_nokia-comm:ipv4-address-unicast;
        }
        description
          "The IP address of the Anycast VTEP for multi-homing L3 subnets";
      }
    }
  }

  grouping bgp-evpn-routes {
    description
      "Grouping containing bgp-evpn route configuration and state.";
    container routes {
      container bridge-table {
        presence "Configure evpn routes advertised for the bridge-table";
        must '(/srl_nokia-netinst:network-instance[srl_nokia-netinst:name = current()/../../../../../srl_nokia-netinst:name]/srl_nokia-netinst:type = "srl_nokia-netinst:vpws") or (/srl_nokia-netinst:network-instance[srl_nokia-netinst:name = current()/../../../../../srl_nokia-netinst:name]/srl_nokia-netinst:type = "srl_nokia-netinst:mac-vrf")' {
          error-message "The bridge-table configuration is possible only on network-instances of type mac-vrf or vpws";
        }
        container mac-ip {
          presence "Configure evpn mac-ip routes advertised for the bridge-table";
          must '(/srl_nokia-netinst:network-instance[srl_nokia-netinst:name = current()/../../../../../../srl_nokia-netinst:name]/srl_nokia-netinst:type = "srl_nokia-netinst:mac-vrf")' {
            error-message "The bridge-table configuration is possible only on network-instances of type mac-vrf.";
          }
          leaf advertise {
            type boolean;
            default "true";
            description
              "If set to true then local mac's and local mac-ip pairs will be advertised in this evpn instance";
          }
          leaf advertise-arp-nd-extended-community {
            description
              "ARP/ND extended community";
            type boolean;
            default "false";
          }
        }
        container inclusive-mcast {
          presence "Configure evpn inclusive-mcast routes advertised for the bridge-table";
          must '(/srl_nokia-netinst:network-instance[srl_nokia-netinst:name = current()/../../../../../../srl_nokia-netinst:name]/srl_nokia-netinst:type = "srl_nokia-netinst:mac-vrf")' {
            error-message "The bridge-table configuration is possible only on network-instances of type mac-vrf.";
          }
          leaf advertise {
            type boolean;
            default "true";
            description
              "If set to true an inclusive multicast route will be advertised in this evpn instance.";
          }
          leaf originating-ip {
            type srl_nokia-comm:ip-address;
            description
              "The originating ip-address that the inclusive multicast route will be advertised with in this evpn instance";
          }
        }
        leaf next-hop {
          type srl_nokia-comm:next-hop-type;
          must ". != 'use-system-ipv6-address'" {
            srl_nokia-ext:if-feature "not srl_nokia-feat:evpn-mh-non-system-ipv4-address";
            error-message "The next-hop ip-address must not be the system ipv6 address";
          }
          must "(../../../encapsulation-type != 'vxlan') or (not(contains(., ':')) and not(. = 'use-system-ipv6-address'))" {
            srl_nokia-ext:if-feature "not srl_nokia-feat:vxlan-v6";
            error-message "IPv6 next-hop address is not supported when encapsulation-type is vxlan";
          }
          default "use-system-ipv4-address";
          description
            "The ip-address that will be used as the bgp next-hop for all routes advertised in this evpn instance.";
        }
        leaf vlan-aware-bundle-eth-tag {
          type ethernet-tag-id;
          must '(../../../../../../srl_nokia-netinst:type = "srl_nokia-netinst:mac-vrf")' {
            error-message "The vlan-aware-bundle ethernet tag configuration is possible only on network-instances of type mac-vrf";
          }
          description
            "Configures the Ethernet Tag ID to be encoded in the EVPN routes for control-plane interoperability mode
             with VLAN-aware bundle services.

             When set to a non-zero value, all the EVPN routes advertised for the MAC-VRF will be advertised with this value
             into the ethernet-tag-id field of the routes.

             On reception of EVPN routes with non-zero ethernet-tag-id, BGP will import the routes based on the import
             route-target as usual. However, the system checks the received ethernet-tag-id field and will process only
             those routes whose ethernet-tag-id match the local vlan-aware-bundle-eth-tag value.";
          reference
            "RFC7432";
        }
      }
      container route-table {
        presence "Configure evpn routes advertised for the route-table";
        must '(/srl_nokia-netinst:network-instance[srl_nokia-netinst:name = current()/../../../../../srl_nokia-netinst:name]/srl_nokia-netinst:type = "srl_nokia-netinst:ip-vrf") or (/srl_nokia-netinst:network-instance[srl_nokia-netinst:name = current()/../../../../../srl_nokia-netinst:name]/srl_nokia-netinst:type = "srl_nokia-netinst:mac-vrf")' {
          error-message "The route-table configuration is possible only on network-instances of type ip-vrf or mac-vrf";
        }
        container mac-ip {
          leaf advertise-gateway-mac {
            type boolean;
            default "false";
            description
              "If set to true in an ip-vrf where bgp-evpn is enabled, a MAC/IP route containing the gateway-MAC
               is advertised.

               This gateway-MAC matches the MAC advertised along with the EVPN IFL routes type 5 for the ip-vrf
               network-instance. This advertisement is needed so that the EVPN IFL (Interface-Less) model in the
               ip-vrf can interoperate with a remote system working in EVPN IFF (Interface-ful) Unnumbered mode.";
          }
          description
            "Enter the mac-ip context";
        }
        container ip-prefix {
          leaf advertise-interface-ful {
            if-feature "srl_nokia-feat:evpn-iff";
            type boolean;
            must '. = false() or (. = true() and (/srl_nokia-netinst:network-instance[srl_nokia-netinst:name = current()/../../../../../../../srl_nokia-netinst:name]/srl_nokia-netinst:type = "srl_nokia-netinst:mac-vrf"))' {
              error-message "The advertise-interface-ful command can only be enabled on network-instances of type mac-vrf";
            }
            must '. = false() or (. = true() and ../../../../supplementary-broadcast-domain)' {
              error-message "The advertise-interface-ful command can only be enabled on a mac-vrf configured as supplementary-broadcast-domain";
            }
            default "false";
            description
              "If set to true, the router advertises EVPN Interface-ful (EVPN-IFF) IP Prefix routes";
          }
          uses evpn-unequal-ecmp;
          uses evpn-ifl-gw-ip;
          uses evpn-anycast-l3-subnet;
          description
            "Enter the ip-prefix context";
        }
      }
      description
        "Enter the routes context";
    }
  }

  grouping next-hop-resolution {
    description
      "Options for controlling next-hop resolution procedures for VPN families";
    container next-hop-resolution {
      description
        "Enter the next-hop-resolution context

         Options related to the resolution of IPv4 or IPv6 BGP next-hops to Tunnels";
      leaf-list allowed-tunnel-types {
        min-elements 1;
        type identityref {
          base srl_nokia-comm:bgp-next-hop-resolution-tunnel-type;
        }
        description
          "list of allowed tunnel types";
      }
      uses srl-bgp:color-aware-next-hop-resolution {
        if-feature "srl_nokia-feat:bgp-next-hop-resolution-tag or srl_nokia-feat:isis-flex-algo or srl_nokia-feat:segment-routing-colored-te-policies";
      }
    }
  }

  grouping evpn-mpls-bridge-table-group-top {
    container bridge-table {
      presence "Bridge table config and state for evpn-mpls";
      must '(/srl_nokia-netinst:network-instance[srl_nokia-netinst:name = current()/../../../../../srl_nokia-netinst:name]/srl_nokia-netinst:type = "srl_nokia-netinst:mac-vrf")' {
        error-message "The bridge-table configuration is possible only on network-instances of type mac-vrf.";
      }
      leaf split-horizon-group {
        if-feature "srl_nokia-feat:bridged and srl_nokia-feat:bt-split-horizon-groups and srl_nokia-feat:evpn-mpls-shg";
        type leafref {
          path "../../../../../../srl_nokia-netinst:bridge-table/srl_nokia-netinst:split-horizon-group/srl_nokia-netinst:name";
        }
        description
          "The split-horizon-group associated to the evpn-mpls instance";
      }
      leaf ingress-multicast-mpls-label {
        config false;
        type srl_nokia-comm:mpls-label-non-reserved;
        description
          "The ingress label allocated for Broadcast, Unknown unicast and Multicast traffic

           The ingress multicast mpls label is advertised by the EVPN Inclusive
           Multicast Ethernet Tag (IMET) route and it is expected on received
           EVPN packets that were generated as BUM packets.";
      }
      leaf ingress-unicast-mpls-label {
        config false;
        type srl_nokia-comm:mpls-label-non-reserved;
        description
          "The ingress label allocated for unicast traffic

           The ingress unicast mpls label is advertised by the EVPN MAC/IP
           Advertisement routes and it is expected on received EVPN packets
           that were generated as unicast packets.";
      }
    }
  }

  grouping evpn-mpls-route-table-group-top {
    container route-table {
      presence "Route table config and state for evpn-mpls";
      must '(/srl_nokia-netinst:network-instance[srl_nokia-netinst:name = current()/../../../../../srl_nokia-netinst:name]/srl_nokia-netinst:type = "srl_nokia-netinst:ip-vrf")' {
        error-message "The route-table configuration is possible only on network-instances of type ip-vrf";
      }
      leaf ingress-mpls-label {
        config false;
        type srl_nokia-comm:mpls-label-non-reserved;
        description
          "The ingress label allocated for Routed traffic

           The ingress mpls label is advertised by the Route-Type 5(RT5)
           route and it is expected on received routed EVPN packets.";
      }
    }
  }

  grouping evpn-vpws {
    description
      "Parameters related to EVPN VPWS services";
    container vpws-attachment-circuits {
      presence "Configure EVPN VPWS local and remote attachment circuits";
      if-feature "srl_nokia-feat:vpws";
      must "../../../../srl_nokia-netinst:type = 'srl_nokia-netinst:vpws'" {
        error-message "VPWS attachment circuits can only be configured on VPWS network instances";
      }
      must "../encapsulation-type = 'mpls' or 'srv6'" {
        error-message "Supported only when encapsulation is mpls or srv6";
      }
      container local {
        description
          "Enter the local context

           The local parameters of the VPWS";
        list local-attachment-circuit {
          key "name";
          min-elements 1;
          max-elements 1;
          description
            "A local attachment circuit in the VPWS

             Each local attachment circuit is identified in EVPN with an
             Ethernet Tag that is advertised in the Auto Discovery per EVI
             route. Configurable on network instances of type vpws.";
          leaf name {
            type srl_nokia-comm:name {
              length "1..32";
            }
            description
              "The list of local attachment circuits in the network instance";
          }
          leaf ethernet-tag {
            type ethernet-tag-id;
            description
              "The Ethernet Tag ID advertised in the Auto Discovery per EVI route

               The Ethernet Tag ID identifies the local attachment circuit in the
               EVPN control plane.";
            mandatory true;
          }
          leaf connection-point {
            if-feature "srl_nokia-feat:connection-point";
            type leafref {
              path "../../../../../../../srl_nokia-netinst:connection-point/srl_nokia-netinst:name";
            }
            description
              "The connection-point associated to the local attachement circuit";
            mandatory true;
          }
          leaf ingress-mpls-label {
            config false;
            type srl_nokia-comm:mpls-label-non-reserved;
            description
              "The ingress label allocated for EVPN VPWS traffic

               The ingress mpls label is advertised by the EVPN Auto-Discovery
               per EVI routes and it is expected on received EVPN packets
               for the VPWS network instance.";
          }
          container srv6 {
            if-feature "srl_nokia-feat:srv6";
            presence "Enable and configure srv6 for the use by bgp-evpn control plane";
            description
              "Enable and configure srv6 for the use by bgp-evpn control plane";
            leaf default-locator {
              if-feature "srl_nokia-feat:segment-routing";
              type leafref {
                path "../../../../../../../../srl_nokia-sr:segment-routing/srl_nokia-srv6-inst:srv6/srl_nokia-srv6-inst:instance[srl_nokia-srv6-inst:id = current()/../instance]/srl_nokia-srv6-inst:locator/srl_nokia-srv6-inst:locator-name";
              }
              description
                "Default route locator";
            }
            leaf instance {
              if-feature "srl_nokia-feat:segment-routing";
              type leafref {
                path "../../../../../../../../srl_nokia-sr:segment-routing/srl_nokia-srv6-inst:srv6/srl_nokia-srv6-inst:instance/srl_nokia-srv6-inst:id";
              }
              description
                "Segment routing IPv6 instance";
            }
          }
        }
      }
      container remote {
        description
          "Enter the remote context

           The remote parameters of the VPWS";
        list remote-attachment-circuit {
          key "name";
          min-elements 1;
          max-elements 1;
          description
            "A remote attachment circuit in the VPWS

             Each remote attachment circuit is identified in EVPN with an
             Ethernet Tag that is received in the Auto Discovery per EVI
             route from the remote PE. Configurable on network instances
             of type vpws.";
          leaf name {
            type srl_nokia-comm:name {
              length "1..32";
            }
            description
              "The list of remote attachment circuits in the network instance";
          }
          leaf ethernet-tag {
            type ethernet-tag-id;
            description
              "The Ethernet Tag ID received in the Auto Discovery per EVI route

               The Ethernet Tag ID identifies the remote attachment circuit in the
               EVPN control plane.";
            mandatory true;
          }
          leaf connection-point {
            if-feature "srl_nokia-feat:connection-point";
            type leafref {
              path "../../../../../../../srl_nokia-netinst:connection-point/srl_nokia-netinst:name";
            }
            description
              "The connection-point associated to the local attachement circuit";
            mandatory true;
          }
        }
      }
    }
  }

  grouping route-internal-tags {
    description
      "Grouping containing the configuration of internal tags";
    container internal-tags {
      if-feature "srl_nokia-feat:internal-tags and srl_nokia-feat:evpn-route-internal-tags";
      description
        "Enter the internal-tags context

         Configuration and state of internal tags";
      leaf-list set-tag-set {
        max-elements 1;
        type leafref {
          path "/srl_nokia-routing-pol:routing-policy/srl_nokia-routing-pol:tag-set/srl_nokia-routing-pol:name";
        }
        description
          "Reference to a tag-set defined under routing-policy";
      }
    }
  }

  grouping network-instance-mpls-attributes {
    description
      "Grouping containing the configuration and state of network instance mpls attributes";
    leaf control-word {
      if-feature "srl_nokia-feat:evpn-mpls-control-word";
      type boolean;
      must '. = false() or (. = true() and ((/srl_nokia-netinst:network-instance[srl_nokia-netinst:name = current()/../../../../../srl_nokia-netinst:name]/srl_nokia-netinst:type = "srl_nokia-netinst:mac-vrf") or (/srl_nokia-netinst:network-instance[srl_nokia-netinst:name = current()/../../../../../srl_nokia-netinst:name]/srl_nokia-netinst:type = "srl_nokia-netinst:vpws")))' {
        error-message "The control-word can only be enabled on network-instances of type mac-vrf or vpws";
      }
      default "false";
      description
        "Configures the use of control-word for EVPN MPLS packets

         When set to true, the router pushes the control-word below the bottom of the stack label. This
         prevents the Provider routers from mistakenly decode the payload of EVPN packets as an IP header
         and misorder packets of the same flow.";
    }
    leaf flow-label {
      if-feature "srl_nokia-feat:flow-aware-transport-label-evpn-mpls-vpws";
      type boolean;
      must '. = false() or (. = true() and (/srl_nokia-netinst:network-instance[srl_nokia-netinst:name = current()/../../../../../srl_nokia-netinst:name]/srl_nokia-netinst:type = "srl_nokia-netinst:vpws"))' {
        error-message "The flow-label for EVPN can only be enabled on network-instances of type vpws";
      }
      default "false";
      description
        "Configures the use of flow-label for EVPN MPLS packets

         When set to true, the router signals the use of the Flow Aware Transport (FAT) label in the F flag
         of the Layer 2 attributes extended community sent along with the EVPN routes (AD per EVI for VPWS or
         Inclusive Multicast Ethernet Tag route for MAC-VRF). For EVPN VPWS network instances, if the local
         and remote flags are set to 1 and match, the flow label is pushed at the bottom of the stack. On
         reception, the flow label is also expected and packets without it are dropped. If there is a
         mismatch between the local and remote F flags, the EVPN destination is removed.";
    }
  }

  grouping bgp-evpn-top {
    description
      "Top-level grouping containing the bgp-evpn configuration and state.";
    list bgp-instance {
      if-feature "srl_nokia-feat:evpn or srl_nokia-feat:ipvpn";
      key "id";
      max-elements 2;
      unique "encapsulation-type";
      description
        "bgp evpn instances configured in net-instance";
      leaf id {
        type leafref {
          path "/srl_nokia-netinst:network-instance/srl_nokia-netinst:protocols/srl_bgp-vpn:bgp-vpn/srl_bgp-vpn:bgp-instance/srl_bgp-vpn:id";
        }
      }
      leaf admin-state {
        type srl_nokia-comm:admin-state;
        default "enable";
        description
          "Configurable state of the bgp evpn instance.";
      }
      leaf encapsulation-type {
        must "(not(.='mpls') and not(../mpls)) or ((.='mpls') and (../mpls))" {
          error-message "encapsulation-type mpls and mpls next-hop-resolution with at least one allowed-tunnel-type must be configured together";
        }
        must 'not(/srl_nokia-netinst:network-instance[srl_nokia-netinst:name = current()/../../../../srl_nokia-netinst:name]/srl_nokia-netinst:type = "srl_nokia-netinst:mac-vrf") or not(. = "srv6")' {
          error-message "encapsulation-type srv6 not supported on network-instances of type mac-vrf";
        }
        type enumeration {
          enum vxlan {
            value 1;
          }
          enum mpls {
            if-feature "srl_nokia-feat:evpn-mpls";
            value 2;
          }
          enum srv6 {
            if-feature "srl_nokia-feat:srv6";
            value 3;
          }
        }
        description
          "encap type of the bgp evpn instance.";
        default "vxlan";
      }
      uses evpn-vpws;
      uses supplementary-bd;
      uses srl-bgp:bgp-group-based-policy {
        if-feature "srl_nokia-feat:bgp-group-based-policy";
      }
      leaf vxlan-interface {
        if-feature "srl_nokia-feat:vxlan";
        must "../encapsulation-type = 'vxlan'" {
          error-message "supported only when encapsulation is vxlan";
        }
        type leafref {
          path "../../../../srl_nokia-netinst:vxlan-interface/srl_nokia-netinst:name";
        }
        description
          "Identifier of vxlan-interface used in this bgp-instance.";
      }
      leaf evi {
        type srl_nokia-comm:evi;
        description
          "EVPN Instance identifier associated to the bgp-evpn instance.

           Used for auto-derivation of:
           - the bgp-instance route distinguisher in the format <ip-address>:evi (where 'ip-address' is the ipv4 address
             associated to the subinterface lo0.1.
           - the bgp-instance route target in the format <asn>:<evi>, where 'asn' is the autonomous-system configured in
             the network-instance default (under /protocols/bgp/autonomous-system).

           In addition, the evi value is used for the EVPN Multi-Homing Designated Forwarder (DF) Election.";
        mandatory true;
      }
      leaf ecmp {
        type uint32 {
          range "1..128";
        }
        default "1";
        description
          "The supported range of ECMP values for layer-2 aliasing (in mac-vrf or vpws instances) or layer-3 ecmp (in routed
           instances)";
        must '(. <= 8) or (/srl_nokia-netinst:network-instance[srl_nokia-netinst:name = current()/../../../../srl_nokia-netinst:name]/srl_nokia-netinst:type = "srl_nokia-netinst:ip-vrf")' {
          error-message "The valid range for ecmp paths with the configured network-instance type is 1..8";
        }
        must '(. <= 1) or (/srl_nokia-netinst:network-instance[srl_nokia-netinst:name = current()/../../../../srl_nokia-netinst:name]/srl_nokia-netinst:type = "srl_nokia-netinst:ip-vrf")' {
          srl_nokia-ext:if-feature "not srl_nokia-feat:evpn-layer-2-ecmp";
          error-message "The valid range for ecmp paths with the configured network-instance type is 1..1";
        }
      }
      leaf dpath-domain-id {
        if-feature "srl_nokia-feat:bgp-domain-path";
        type srl_nokia-comm:domain-id;
        description
          "D-PATH Domain ID of the received EVPN route that is added to the D-PATH Attribute when the route is readvertised";
        must '(/srl_nokia-netinst:network-instance[srl_nokia-netinst:name = current()/../../../../srl_nokia-netinst:name]/srl_nokia-netinst:type = "srl_nokia-netinst:ip-vrf")' {
          error-message "D-PATH domain-id can only be configured in network-instances of type ip-vrf";
        }
      }
      leaf multi-homing-mode {
        type enumeration {
          enum network {
            value 0;
          }
          enum access {
            value 1;
          }
        }
        default "network";
        description
          "Multi-homing mode of the EVPN bgp instance in a network-instance";
        must '(/srl_nokia-netinst:network-instance[srl_nokia-netinst:name = current()/../../../../srl_nokia-netinst:name]/srl_nokia-netinst:type = "srl_nokia-netinst:mac-vrf") or (. = "network")' {
          error-message "multi-homing-mode access not allowed on ip-vrf ";
          srl_nokia-ext:if-feature "not srl_nokia-feat:bgp-ip-vrf-evpn-mi-mpls-vxlan";
        }
      }
      uses route-internal-tags;
      leaf oper-state {
        config false;
        srl_nokia-ext:show-importance "high";
        type srl_nokia-comm:oper-state;
        description
          "This leaf contains the operational state of bgp-instance.";
      }
      leaf oper-down-reason {
        config false;
        srl_nokia-ext:show-importance "high";
        type enumeration {
          enum admin-disabled;
          enum no-nexthop-address;
          enum no-evi;
          enum network-instance-oper-down;
          enum no-vxlan-interface;
          enum ethernet-segment-multiple-subinterfaces;
          enum vxlan_interface_no_source_ip_address;
          enum bgp-vpn-instance-oper-down;
          enum no-mpls-label;
          enum no-mcid;
          enum no-local-attachment-circuit;
          enum no-remote-attachment-circuit;
          enum tag-set-not-resolved;
          enum esi-label-required-in-ethernet-segment;
          enum srv6_no_locator;
          enum srv6_no_source_address;
          enum srv6_no_sid;
        }
        description
          "The reason for the bgp-instance being down";
      }
      container mpls {
        presence "Configure EVPN-MPLS and enables the resolution of BGP-EVPN route next-hops to tunnels in TTM";
        if-feature "srl_nokia-feat:evpn-mpls";
        must "../encapsulation-type = 'mpls'" {
          error-message "supported only when encapsulation is mpls";
        }
        uses network-instance-mpls-attributes;
        uses evpn-mpls-bridge-table-group-top;
        uses evpn-mpls-route-table-group-top;
        uses next-hop-resolution;
      }
      container srv6 {
        if-feature "srl_nokia-feat:srv6";
        presence "Enable and configure srv6 for the use by bgp-evpn control plane";
        description
          "Enable and configure srv6 for the use by bgp-evpn control plane";
        leaf default-locator {
          if-feature "srl_nokia-feat:segment-routing";
          must '(/srl_nokia-netinst:network-instance[srl_nokia-netinst:name = current()/../../../../../srl_nokia-netinst:name]/srl_nokia-netinst:type = "srl_nokia-netinst:ip-vrf" or /srl_nokia-netinst:network-instance[srl_nokia-netinst:name = current()/../../../../../srl_nokia-netinst:name]/srl_nokia-netinst:type = "srl_nokia-netinst:mac-vrf")' {
            error-message "The default-locator configuration under bgp-evpn is possible only on network-instances of type ip-vrf or mac-vrf";
          }
          type leafref {
            path "../../../../../srl_nokia-sr:segment-routing/srl_nokia-srv6-inst:srv6/srl_nokia-srv6-inst:instance[srl_nokia-srv6-inst:id = current()/../instance]/srl_nokia-srv6-inst:locator/srl_nokia-srv6-inst:locator-name";
          }
          description
            "Default route locator";
        }
        leaf instance {
          if-feature "srl_nokia-feat:segment-routing";
          must '(/srl_nokia-netinst:network-instance[srl_nokia-netinst:name = current()/../../../../../srl_nokia-netinst:name]/srl_nokia-netinst:type = "srl_nokia-netinst:ip-vrf" or /srl_nokia-netinst:network-instance[srl_nokia-netinst:name = current()/../../../../../srl_nokia-netinst:name]/srl_nokia-netinst:type = "srl_nokia-netinst:mac-vrf")' {
            error-message "The instance configuration under bgp-evpn is possible only on network-instances of type ip-vrf or mac-vrf";
          }
          type leafref {
            path "../../../../../srl_nokia-sr:segment-routing/srl_nokia-srv6-inst:srv6/srl_nokia-srv6-inst:instance/srl_nokia-srv6-inst:id";
          }
          description
            "Segment routing IPv6 instance";
        }
        leaf source-address {
          if-feature "srl_nokia-feat:srv6";
          type leafref {
            path "/srl_nokia-system:system/srl_nokia-srv6:srv6/srl_nokia-srv6:source-address/srl_nokia-srv6:ip-address";
          }
          description
            "Source address used in SRv6 packets";
        }
      }
      uses bgp-evpn-routes;
    }
  }

  augment "/srl_nokia-netinst:network-instance/srl_nokia-netinst:protocols/srl_nokia-netinst:bgp-evpn" {
    uses bgp-evpn-oism;
    uses bgp-evpn-top;
  }
}
