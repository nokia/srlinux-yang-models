module srl_nokia-tools-igmp {
  yang-version 1.1;
  namespace "urn:nokia.com:srlinux:igmp:tools-igmp";
  prefix srl_nokia-tools-igmp;

  import srl_nokia-common {
    prefix srl_nokia-comm;
  }
  import srl_nokia-tools-network-instance {
    prefix srl_nokia-tools-netinst;
  }
  import srl_nokia-features {
    prefix srl_nokia-feat;
  }

  organization
    "Nokia";
  contact
    "Nokia SR Linux Support
     Web: <http://www.nokia.com>";
  description
    "Model for IGMP operational commands";

  revision 2026-07-31 {
    description
      "SRLinux 26.7.1";
  }
  revision 2023-03-31 {
    description
      "SRLinux 23.3.1";
  }
  revision 2022-11-30 {
    description
      "SRLinux 22.11.1";
  }
  revision 2022-03-31 {
    description
      "SRLinux 22.3.1";
  }
  revision 2021-11-30 {
    description
      "SRLinux 21.11.1";
  }

  grouping igmp-tools-top {
    container igmp {
      if-feature "srl_nokia-feat:igmp";
      presence "Send operational commands to IGMP manager";
      container version {
        leaf clear {
          type empty;
          description
            "Reset the IGMP operational version for all interfaces";
        }
        description
          "Enter the version context";
      }
      container statistics {
        leaf clear {
          type empty;
          description
            "Reset IGMP statistics for all interfaces";
        }
        description
          "Enter the statistics context";
      }
      container membership-groups {
        leaf clear {
          type empty;
          description
            "Clear the IGMP memberships for all interfaces";
        }
        list group {
          key "group";
          description
            "Multicast group membership";
          leaf group {
            type srl_nokia-comm:ipv4-address;
            description
              "Multicast address";
          }
          leaf clear {
            type empty;
            description
              "Clear all IGMP memberships for this group on all interfaces";
          }
          list source {
            key "source";
            description
              "Source addresses of multicast";
            leaf source {
              type srl_nokia-comm:ipv4-address;
              description
                "Source address of multicast";
            }
            leaf clear {
              type empty;
              description
                "Clear all IGMP memberships for this group on all interfaces";
            }
          }
        }
        description
          "Enter the membership-groups context";
      }
      list interface {
        description
          "List of IGMP interfaces";
        key "interface-name";
        leaf interface-name {
          type srl_nokia-comm:subinterface-all;
          description
            "Reference to a specific subinterface of the form <interface-name>.<subinterface-index>";
        }
        container version {
          leaf clear {
            type empty;
            description
              "Reset the IGMP operational version for this interface";
          }
          description
            "Enter the version context";
        }
        container statistics {
          leaf clear {
            type empty;
            description
              "Reset IGMP statistics for this interface";
          }
          description
            "Enter the statistics context";
        }
        container membership-groups {
          leaf clear {
            type empty;
            description
              "Clear all IGMP memberships for this interface";
          }
          list group {
            key "group";
            description
              "Multicast group membership";
            leaf group {
              type srl_nokia-comm:ipv4-address;
              description
                "Multicast address";
            }
            leaf clear {
              type empty;
              description
                "Clear all IGMP memberships for this group on this interface";
            }
            list source {
              key "source";
              description
                "Source addresses of multicast";
              leaf source {
                type srl_nokia-comm:ipv4-address;
                description
                  "Source address of multicast";
              }
              leaf clear {
                type empty;
                description
                  "Clear all IGMP memberships for this source on this interface";
              }
            }
          }
          description
            "Enter the membership-groups context";
        }
      }
    }
  }

  augment "/srl_nokia-tools-netinst:network-instance/srl_nokia-tools-netinst:protocols" {
    uses igmp-tools-top;
  }
}
