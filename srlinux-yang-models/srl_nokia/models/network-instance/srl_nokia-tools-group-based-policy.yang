module srl_nokia-tools-group-based-policy {
  yang-version 1.1;
  namespace "urn:nokia.com:srlinux:group-based-policy:tools-gbp";
  prefix srl_nokia-tools-gbp;

  import srl_nokia-tools-network-instance {
    prefix srl_nokia-tools-netinst;
  }
  import srl_nokia-features {
    prefix srl_nokia-feat;
  }

  organization
    "Nokia";
  contact
    "Nokia SR Linux Support
     Web: <http://www.nokia.com>";
  description
    "A model tools for Group Based Policy of a network instance";

  revision 2026-07-31 {
    description
      "SRLinux 26.7.1";
  }
  revision 2025-10-31 {
    description
      "SRLinux 25.10.1";
  }

  grouping gbp-tools-top {
    container group-based-policy {
      description
        "Enter the group-based-policy context";
    }
  }

  augment "/srl_nokia-tools-netinst:network-instance" {
    uses gbp-tools-top;
    if-feature "srl_nokia-feat:group-based-policy";
  }
}
