module srl_nokia-bgp-evpn-bgp-instance-mpls-bridge-table-multicast-destinations {
  yang-version 1.1;
  namespace "urn:nokia.com:srlinux:mcid:bgp-evpn-bgp-instance-mpls-bridge-table-multicast-destinations";
  prefix srl_nokia-bgp-evpn-bgp-instance-mpls-bt-multicast-destinations;

  import srl_nokia-common {
    prefix srl_nokia-comm;
  }
  import srl_nokia-network-instance {
    prefix srl_nokia-netinst;
  }
  import srl_nokia-extensions {
    prefix srl_nokia-ext;
  }
  import srl_nokia-bgp-evpn {
    prefix srl_bgp-evpn;
  }

  organization
    "Nokia";
  contact
    "Nokia SR Linux Support
     Web: <http://www.nokia.com>";
  description
    "Model for bridge-table multicast destinations on the bgp-evpn mpls instance";

  revision 2026-07-31 {
    description
      "SRLinux 26.7.1";
  }
  revision 2023-10-31 {
    description
      "SRLinux 23.10.1";
  }
  revision 2023-07-31 {
    description
      "SRLinux 23.7.1";
  }
  revision 2022-06-30 {
    description
      "SRLinux 22.6.1";
  }
  revision 2022-03-31 {
    description
      "SRLinux 22.3.1";
  }

  grouping evpn-mpls-bridge-table-multicast-destinations-destination-top {
    list destination {
      key "tep evi-label tunnel-id";
      leaf tep {
        srl_nokia-ext:show-importance "high";
        type srl_nokia-comm:ip-address;
        description
          "The IP address that identifies the remote EVPN Termination Endpoint (TEP).";
      }
      leaf evi-label {
        type srl_nokia-comm:mpls-label-non-reserved;
        srl_nokia-ext:show-importance "high";
        description
          "EVI label of the destination.";
      }
      leaf tunnel-id {
        type uint64;
        srl_nokia-ext:show-importance "high";
        description
          "tunnel identitier of the destination.";
      }
      leaf multicast-forwarding {
        srl_nokia-ext:show-importance "high";
        type srl_nokia-comm:multicast-type;
        description
          "The type of multicast data forwarded by this evpn-mpls destination.";
      }
      leaf destination-index {
        type uint64;
        srl_nokia-ext:show-importance "high";
        description
          "A system-wide unique identifier of this evpn-mpls destination object (system allocated).";
      }
      leaf not-programmed-reason {
        srl_nokia-ext:show-importance "high";
        type enumeration {
          enum no-destination-index;
          enum multicast-limit;
        }
        description
          "The reason why the destination is not programmed in the floodlist";
      }
    }
  }

  grouping evpn-mpls-bridge-table-multicast-destinations-limits-top {
    container multicast-limit {
      description
        "Enter the multicast-limit context

         Multicast limits per vxlan interface.";
      leaf maximum-entries {
        type int32;
        description
          "Maximum number of multicast vxlan-destinations allowed on a bgp-evpn mpls instance.";
      }
      leaf current-usage {
        type int32;
        description
          "Maximum number of multicast vxlan-destinations in use on this bgp-evpn mpls instance.";
      }
    }
  }

  grouping evpn-mpls-bridge-table-multicast-destinations-top {
    container multicast-destinations {
      config false;
      uses evpn-mpls-bridge-table-multicast-destinations-limits-top;
      uses evpn-mpls-bridge-table-multicast-destinations-destination-top;
      description
        "Enter the multicast-destinations context";
    }
  }

  augment "/srl_nokia-netinst:network-instance/srl_nokia-netinst:protocols/srl_nokia-netinst:bgp-evpn/srl_bgp-evpn:bgp-instance/srl_bgp-evpn:mpls/srl_bgp-evpn:bridge-table" {
    uses evpn-mpls-bridge-table-multicast-destinations-top;
  }
}
