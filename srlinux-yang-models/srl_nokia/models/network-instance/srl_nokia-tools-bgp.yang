module srl_nokia-tools-bgp {
  yang-version 1.1;
  namespace "urn:nokia.com:srlinux:bgp:tools-bgp";
  prefix srl_nokia-tools-bgp;

  import srl_nokia-common {
    prefix srl_nokia-comm;
  }
  import srl_nokia-features {
    prefix srl_nokia-feat;
  }
  import srl_nokia-tools-network-instance {
    prefix srl_nokia-tools-netinst;
  }

  organization
    "Nokia";
  contact
    "Nokia SR Linux Support
     Web: <http://www.nokia.com>";
  description
    "Model for BGP operational commands";

  revision 2024-03-31 {
    description
      "SRLinux 24.3.1";
  }
  revision 2023-03-31 {
    description
      "SRLinux 23.3.1";
  }
  revision 2021-03-31 {
    description
      "SRLinux 21.3.1";
  }
  revision 2019-11-30 {
    description
      "SRLinux 19.11.1";
  }

  typedef autonomous-system-number {
    type uint32 {
      range "1..4294967295";
    }
  }

  grouping bgp-tools-top {
    container bgp {
      presence "Enable the BGP protocol";
      container reset-peer {
        presence "Hard reset peers";
        leaf peer-as {
          type autonomous-system-number;
          description
            "Hard reset only BGP peers that have the specified peer-AS number, whether they are configured peers or dynamic peers";
        }
      }
      container soft-clear {
        presence "Soft reset peers by sending them ROUTE_REFRESH messages";
        leaf route-refresh {
          type identityref {
            base srl_nokia-comm:bgp-address-family;
          }
          description
            "The address family to refresh

             This is encoded in the ROUTE_REFRESH message. By default all families are refreshed.";
        }
        leaf peer-as {
          type autonomous-system-number;
          description
            "Soft reset only BGP peers that have the specified peer-AS number, whether they are configured peers or dynamic peers";
        }
      }
      container route-flap-damping {
        if-feature "srl_nokia-feat:bgp-route-flap-damping";
        presence "Clear the route-flap-damping state for the bgp-instance";
        leaf clear-history {
          type empty;
          description
            "Clear the route-flap-damping data for all routes of the BGP instance

              This also has the effect of unsuppressing routes that were previously suppressed";
        }
      }
      list group {
        key "group-name";
        leaf group-name {
          type srl_nokia-comm:name;
          description
            "The configured name of the peer group";
        }
        container reset-peer {
          presence "Hard reset group peers";
          leaf peer-as {
            type autonomous-system-number;
            description
              "Hard reset only BGP peers in the peer-group that have the specified peer-AS number, whether they are configured peers or dynamic peers";
          }
        }
        container soft-clear {
          presence "Soft reset group peers by sending them ROUTE_REFRESH messages";
          leaf route-refresh {
            type identityref {
              base srl_nokia-comm:bgp-address-family;
            }
            description
              "The address family to refresh

               This is encoded in the ROUTE_REFRESH message. By default all families are refreshed.";
          }
          leaf peer-as {
            type autonomous-system-number;
            description
              "Soft reset only BGP peers in the peer-group that have the specified peer-AS number, whether they are configured peers or dynamic peers";
          }
        }
        container route-flap-damping {
          if-feature "srl_nokia-feat:bgp-route-flap-damping";
          presence "Clear the route-flap-damping state for the peer group";
          leaf clear-history {
            type empty;
            description
              "Clear the route-flap-damping data for all routes received from group peers

               This also has the effect of unsuppressing routes that were previously suppressed";
          }
        }
      }
      list neighbor {
        key "peer-address";
        leaf peer-address {
          type srl_nokia-comm:ip-address-with-zone;
          description
            "The transport address of the BGP peer

             The peer-address must be a valid IPv4 unicast address or a valid IPv6 global unicast address. Sessions to a link-local IPv6 address are not supported.";
        }
        leaf reset-peer {
          type empty;
          description
            "Hard reset the peer";
        }
        container soft-clear {
          presence "Soft reset the peer by sending it ROUTE_REFRESH messages";
          leaf route-refresh {
            type identityref {
              base srl_nokia-comm:bgp-address-family;
            }
            description
              "The address family to refresh

               This is encoded in the ROUTE_REFRESH message. By default all families are refreshed.";
          }
        }
        container route-flap-damping {
          if-feature "srl_nokia-feat:bgp-route-flap-damping";
          presence "Clear the route-flap-damping state for the peer";
          leaf clear-history {
            type empty;
            description
              "Clear the route-flap-damping data for all routes received from the single peer

               This also has the effect of unsuppressing routes that were previously suppressed";
          }
        }
      }
    }
  }

  augment "/srl_nokia-tools-netinst:network-instance/srl_nokia-tools-netinst:protocols" {
    uses bgp-tools-top;
  }
}
