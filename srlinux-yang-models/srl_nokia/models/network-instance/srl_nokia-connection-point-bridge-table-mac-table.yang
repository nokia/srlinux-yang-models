module srl_nokia-connection-point-bridge-table-mac-table {
  yang-version 1.1;

  // namespace

  namespace "urn:nokia.com:srlinux:l2-mac:connection-point-bridge-table-mac-table";
  prefix srl_nokia-connection-point-bridge-table-mac-table;

  import srl_nokia-network-instance {
    prefix srl_nokia-netinst;
  }
  import srl_nokia-interfaces-bridge-table-mac-table {
    prefix srl_nokia-interfaces-bridge-table-mac-table;
  }

  organization
    "Nokia";
  contact
    "Nokia SR Linux Support
     Web: <http://www.nokia.com>";
  description
    "This yang file gives a description of the mac entries installed on this connection-points bridge table.";

  revision 2024-03-31 {
    description
      "SRLinux 24.3.3";
  }

  augment "/srl_nokia-netinst:network-instance/srl_nokia-netinst:connection-point/srl_nokia-netinst:bridge-table" {
    uses srl_nokia-interfaces-bridge-table-mac-table:bridge-table-mac-table-top;
  }
}
