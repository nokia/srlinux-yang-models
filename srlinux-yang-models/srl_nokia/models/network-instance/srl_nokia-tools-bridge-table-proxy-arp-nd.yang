module srl_nokia-tools-bridge-table-proxy-arp-nd {
  yang-version 1.1;
  namespace "urn:nokia.com:srlinux:l2-proxy-arp-nd:tools-bridge-table-proxy-arp-nd";
  prefix srl_nokia-tools-bridge-table-proxy-arp-nd;

  import srl_nokia-common {
    prefix srl_nokia-comm;
  }
  import srl_nokia-features {
    prefix srl-feat;
  }
  import srl_nokia-tools-network-instance {
    prefix srl_nokia-tools-netinst;
  }

  organization
    "Nokia";
  contact
    "Nokia SR Linux Support
     Web: <http://www.nokia.com>";
  description
    "Model for network-instance bridge-table proxy arp nd operational commands";

  revision 2022-03-30 {
    description
      "SRLinux 22.3.1";
  }

  grouping tools-bridge-table-proxy-type-delete-all-top {
    leaf delete-all {
      type empty;
      description
        "Delete all entries.";
    }
  }

  grouping tools-bridge-table-proxy-type-delete-ip-top {
    leaf delete-ip {
      type empty;
      description
        "delete the proxy entry.";
    }
  }

  grouping tools-bridge-table-proxy-arp-common-top {
    uses tools-bridge-table-proxy-type-delete-all-top;
    list entry {
      key "address";
      description
        "proxy-arp entry to delete";
      leaf address {
        type srl_nokia-comm:ipv4-address;
      }
      uses tools-bridge-table-proxy-type-delete-ip-top;
    }
  }

  grouping tools-bridge-table-proxy-nd-common-top {
    uses tools-bridge-table-proxy-type-delete-all-top;
    list entry {
      key "address";
      description
        "proxy-nd entry to delete";
      leaf address {
        type srl_nokia-comm:ipv6-address;
      }
      uses tools-bridge-table-proxy-type-delete-ip-top;
    }
  }

  grouping tools-bridge-table-proxy-arp-duplicate-top {
    container duplicate {
      presence "bridge table proxy arp duplicate";
      uses tools-bridge-table-proxy-arp-common-top;
    }
  }

  grouping tools-bridge-table-proxy-arp-dynamic-top {
    container dynamic {
      presence "bridge table proxy arp dynamic";
      uses tools-bridge-table-proxy-arp-common-top;
    }
  }

  grouping tools-bridge-table-proxy-nd-duplicate-top {
    container duplicate {
      presence "bridge table proxy nd duplicate";
      uses tools-bridge-table-proxy-nd-common-top;
    }
  }

  grouping tools-bridge-table-proxy-nd-dynamic-top {
    container dynamic {
      presence "bridge table proxy nd dynamic";
      uses tools-bridge-table-proxy-nd-common-top;
    }
  }

  grouping tools-bridge-table-proxy-arp-top {
    container proxy-arp {
      if-feature "srl-feat:l2-proxy-arp";
      presence "bridge table proxy arp";
      uses tools-bridge-table-proxy-arp-duplicate-top;
      uses tools-bridge-table-proxy-arp-dynamic-top;
    }
  }

  grouping tools-bridge-table-proxy-nd-top {
    container proxy-nd {
      if-feature "srl-feat:l2-proxy-nd";
      presence "bridge table proxy nd";
      uses tools-bridge-table-proxy-nd-duplicate-top;
      uses tools-bridge-table-proxy-nd-dynamic-top;
    }
  }

  augment "/srl_nokia-tools-netinst:network-instance/srl_nokia-tools-netinst:bridge-table" {
    uses tools-bridge-table-proxy-arp-top;
    uses tools-bridge-table-proxy-nd-top;
  }
}
