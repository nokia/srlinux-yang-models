module srl_nokia-tools-isis {
  yang-version 1.1;
  namespace "urn:nokia.com:srlinux:isis:tools-isis";
  prefix srl_nokia-tools-isis;

  import srl_nokia-common {
    prefix srl_nokia-comm;
  }
  import srl_nokia-features {
    prefix srl_nokia-feat;
  }
  import srl_nokia-tools-network-instance {
    prefix srl_nokia-tools-netinst;
  }

  organization
    "Nokia";
  contact
    "Nokia SR Linux Support
     Web: <http://www.nokia.com>";
  description
    "Model for ISIS operational commands";

  revision 2026-07-31 {
    description
      "SRLinux 26.7.1";
  }
  revision 2026-03-31 {
    description
      "SRLinux 26.3.1";
  }
  revision 2025-10-31 {
    description
      "SRLinux 25.10.1";
  }
  revision 2023-07-31 {
    description
      "SRLinux 23.7.1";
  }
  revision 2020-06-30 {
    description
      "SRLinux 20.6.1";
  }

  typedef isis-common-subintf-name {
    type string {
      length "1..255";
    }
    description
      "User defined name or reference type to a specific subinterface of the form <interface-name>.<subinterface-index>";
  }

  typedef isis-level {
    description
      "Specifies the IS-IS Level.";
    type enumeration {
      enum L1 {
        description
          "This enum describes ISIS level 1";
      }
      enum L2 {
        description
          "This enum describes ISIS level 2";
      }
      enum L1L2 {
        description
          "This enum describes ISIS level 1-2";
      }
    }
  }

  grouping isis-tools-top {
    container isis {
      presence "Send operational commands to ISIS manager";
      list instance {
        max-elements 1;
        description
          "List of IS-IS protocol instances associated with this network-instance. Only a single instance is supported for now";
        key "name";
        leaf name {
          description
            "The name of the IS-IS instance";
          type srl_nokia-comm:name;
        }
        container ldp-synchronization {
          description
            "Enter the ldp-synchronization context

             IS-IS LDP-IGP synchronisation";
          leaf exit {
            type empty;
            description
              "Advertise the norrmal metric for all IS-IS interfaces, even if some are configured for LDP synchronization and ISIS is not in sync with LDP on these interfaces";
          }
        }
        container link-state-database {
          description
            "Enter the link-state-database context

             The ISIS link state database";
          leaf clear {
            type empty;
            description
              "Clear the contents of the LSDB.";
          }
        }
        list interface {
          description
            "List of IS-IS interfaces";
          key "interface-name";
          leaf interface-name {
            type isis-common-subintf-name;
            description
              "Reference to a specific subinterface of the form <interface-name>.<subinterface-index>";
          }
          container adjacencies {
            leaf clear {
              type empty;
              description
                "Reset all of the adjacencies on this interface";
            }
            description
              "Enter the adjacencies context";
          }
        }
        container multi-part-tlv-statistics {
          if-feature "srl_nokia-feat:isis-multi-part-tlv";
          leaf clear {
            type empty;
            description
              "Reset all of the IS-IS instance mult-tlv-part statistics to zero.";
          }
          description
            "Enter the multi-part-tlv-statistics context";
        }
        container statistics {
          leaf clear {
            type empty;
            description
              "Reset all of the IS-IS instance statistics to zero.";
          }
          description
            "Enter the statistics context";
        }
        container segment-routing-statistics {
          if-feature "srl_nokia-feat:segment-routing-isis-lsp-stats";
          leaf clear {
            type empty;
            description
              "Reset all of the applicable Node, Adj, SID statistics to zero.";
          }
          description
            "Enter the segment-routing-statistics context";
        }
        container overload {
          if-feature "srl_nokia-feat:igp-overload-on-fib-failure";
          leaf clear {
            type empty;
            description
              "Reset ISIS instance overload status.";
          }
          description
            "Enter the overload context";
        }
      }
    }
  }

  augment "/srl_nokia-tools-netinst:network-instance/srl_nokia-tools-netinst:protocols" {
    uses isis-tools-top;
  }
}
