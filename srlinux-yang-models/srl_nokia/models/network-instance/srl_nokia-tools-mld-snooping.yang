module srl_nokia-tools-mld-snooping {
  yang-version 1.1;
  namespace "urn:nokia.com:srlinux:igmp:tools-mld-snooping";
  prefix srl_nokia-tools-mld-snooping;

  import srl_nokia-common {
    prefix srl_nokia-comm;
  }
  import srl_nokia-tools-network-instance {
    prefix srl_nokia-tools-netinst;
  }
  import srl_nokia-features {
    prefix srl_nokia-feat;
  }

  organization
    "Nokia";
  contact
    "Nokia SR Linux Support
     Web: <http://www.nokia.com>";
  description
    "Model for MLD SNOOPING operational commands";

  revision 2026-07-31 {
    description
      "SRLinux 26.7.1";
  }
  revision 2023-03-31 {
    description
      "SRLinux 23.3.1";
  }

  grouping mld-snooping-tools-top {
    container mld-snooping {
      if-feature "srl_nokia-feat:mld-snooping";
      presence "Send operational commands to IGMP manager";
      container statistics {
        leaf clear {
          type empty;
          description
            "Reset MLD SNOOPING statistics for all interfaces";
        }
        description
          "Enter the statistics context";
      }
      container membership-groups {
        leaf clear {
          type empty;
          description
            "Clear all MLD SNOOPING memberships for all interfaces";
        }
        list group {
          key "group";
          description
            "Multicast group membership";
          leaf group {
            type srl_nokia-comm:ipv6-address;
            description
              "Multicast address";
          }
          leaf clear {
            type empty;
            description
              "Clear all MLD SNOOPING memberships for this group on all interfaces";
          }
          list source {
            key "source";
            description
              "Source addresses of multicast";
            leaf source {
              type srl_nokia-comm:ipv6-address;
              description
                "Source address of multicast";
            }
            leaf clear {
              type empty;
              description
                "Clear all MLD SNOOPING memberships for this source on all interfaces";
            }
          }
        }
        description
          "Enter the membership-groups context";
      }
      container querier {
        leaf clear {
          type empty;
          description
            "Clear all MLD SNOOPING querier info on all interfaces";
        }
        description
          "Enter the querier context";
      }
      list interface {
        description
          "List of MLD SNOOPING interfaces";
        key "interface-name";
        leaf interface-name {
          type srl_nokia-comm:subinterface-all;
          description
            "Reference to a specific subinterface of the form <interface-name>.<subinterface-index>";
        }
        container statistics {
          leaf clear {
            type empty;
            description
              "Reset MLD SNOOPING statistics for this interface";
          }
          description
            "Enter the statistics context";
        }
        container membership-groups {
          leaf clear {
            type empty;
            description
              "Clear all MLD SNOOPING memberships for this interface";
          }
          list group {
            key "group";
            description
              "Multicast group membership";
            leaf group {
              type srl_nokia-comm:ipv6-address;
              description
                "Multicast address";
            }
            leaf clear {
              type empty;
              description
                "Clear all MLD SNOOPING memberships for this group on this interface";
            }
            list source {
              key "source";
              description
                "Source addresses of multicast";
              leaf source {
                type srl_nokia-comm:ipv6-address;
                description
                  "Source address of multicast";
              }
              leaf clear {
                type empty;
                description
                  "Clear all MLD SNOOPING memberships for this source on this interface";
              }
            }
          }
          description
            "Enter the membership-groups context";
        }
      }
    }
  }

  augment "/srl_nokia-tools-netinst:network-instance/srl_nokia-tools-netinst:protocols" {
    uses mld-snooping-tools-top;
  }
}
