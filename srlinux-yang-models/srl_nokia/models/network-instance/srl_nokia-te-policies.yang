module srl_nokia-te-policies {
  yang-version 1.1;
  namespace "urn:nokia.com:srlinux:tepolicy:te-policies";
  prefix srl_nokia-te-policies;

  import srl_nokia-common {
    prefix srl_nokia-comm;
  }
  import srl_nokia-network-instance {
    prefix srl_nokia-netinst;
  }
  import srl_nokia-system {
    prefix srl_nokia-system;
  }
  import srl_nokia-extensions {
    prefix srl_nokia-ext;
  }
  import srl_nokia-mpls-label-management {
    prefix srl_nokia-mplslbl;
  }
  import srl_nokia-features {
    prefix srl_nokia-feat;
  }
  import srl_nokia-protection-policies {
    prefix srl_nokia-prot-pol;
  }
  import srl_nokia-traffic-engineering {
    prefix srl_nokia-te;
  }
  import srl_nokia-routing-policy {
    prefix srl_nokia-routing-pol;
  }
  import srl_nokia-pcep {
    prefix srl_nokia-pcep;
  }

  organization
    "Nokia";
  contact
    "Nokia SR Linux Support
     Web: <http://www.nokia.com>";
  description
    "Configuration and state for traffic engineering policies.";

  revision 2026-07-31 {
    description
      "SRLinux 26.7.1";
  }
  revision 2026-03-31 {
    description
      "SRLinux 26.3.1";
  }
  revision 2025-10-31 {
    description
      "SRLinux 25.10.1";
  }
  revision 2025-07-31 {
    description
      "SRLinux 25.7.1";
  }
  revision 2025-03-31 {
    description
      "SRLinux 25.3.1";
  }
  revision 2024-10-31 {
    description
      "SRLinux 24.10.1";
  }
  revision 2024-07-31 {
    description
      "SRLinux 24.7.1";
  }
  revision 2024-03-31 {
    description
      "SRLinux 24.3.1";
  }
  revision 2023-10-31 {
    description
      "SRLinux 23.10.1";
  }
  revision 2023-07-31 {
    description
      "SRLinux 23.7.1";
  }
  revision 2023-03-31 {
    description
      "SRLinux 23.3.1";
  }

  identity candidate-path-failure-reason {
    description
      "Base identity for reasons that describe why a candidate path is invalid";
  }

  identity operational-segment-lists-below-threshold {
    base candidate-path-failure-reason;
    description
      "The candidate path does not have enough number of operationally up segment lists that meets or exceeds the threshold";
  }

  identity no-valid-segment-lists {
    base candidate-path-failure-reason;
    description
      "The candidate path does not have any valid segment list";
  }

  identity better-candidate-path-available {
    base candidate-path-failure-reason;
    description
      "Candidate path with higher preference or protocol-origin, lower value of originator or higher value of discriminator is available";
  }

  identity policy-admin-disabled {
    base candidate-path-failure-reason;
    description
      "The candidate path is administratively disabled";
  }

  identity binding-sid-allocation-failed {
    base candidate-path-failure-reason;
    description
      "No free labels in the label-range";
  }

  identity binding-sid-conflict {
    base candidate-path-failure-reason;
    description
      "Binding SID already in use by another TE-Policy";
  }

  identity protection-mode-conflict {
    base candidate-path-failure-reason;
    description
      "Protection mode assigned to others CPs within the same TE-Policy do no match";
  }

  typedef candidate-path-failure-reason-type {
    type identityref {
      base candidate-path-failure-reason;
    }
  }

  identity te-policy-oper-down-reason {
    description
      "Base identity for reasons that describe why a TE policy is operationally down";
  }

  identity te-policy-admin-disabled {
    base te-policy-oper-down-reason;
    description
      "The TE policy is administratively disabled";
  }

  identity te-policy-no-valid-segment-list {
    base te-policy-oper-down-reason;
    description
      "The TE policy has no valid segment lists";
  }

  identity te-policy-no-operational-candidate-path {
    base te-policy-oper-down-reason;
    description
      "The TE policy has no operational Candidate Path";
  }

  typedef te-policy-oper-down-reason-type {
    type identityref {
      base te-policy-oper-down-reason;
    }
  }

  typedef dynamic-segment-path-computation-type {
    type enumeration {
      enum local-cspf;
      enum pce;
    }
  }

  typedef protocol-origin-type {
    type enumeration {
      enum pcep {
        value 10;
        description
          "PCEP used as signalling mechanism for the candidate path";
      }
      enum bgp {
        value 20;
        description
          "BGP used as signalling mechanism for the candidate path";
      }
      enum local {
        value 30;
        description
          "Management interface used for candidate path instantiation";
      }
    }
    description
      "Originating protocol type";
  }

  typedef oper-state {
    type enumeration {
      enum up {
        value 1;
      }
      enum down {
        value 2;
      }
    }
  }

  typedef forwarding-state {
    type enumeration {
      enum active {
        value 1;
      }
      enum inactive {
        value 2;
      }
      enum backup {
        value 3;
      }
    }
  }

  typedef delay-metric-limit {
    type union {
      type enumeration {
        enum no-limit {
          value -1;
        }
      }
      type uint32 {
        range "1..16777215";
      }
    }
  }

  typedef metric-type {
    type enumeration {
      enum igp {
        value 1;
      }
      enum te {
        value 2;
      }
      enum delay {
        if-feature "srl_nokia-feat:te-policy-delay-metric-limit";
        value 3;
      }
    }
  }

  typedef local-sr-protection {
    type enumeration {
      enum none {
        value 1;
      }
      enum preferred {
        value 2;
      }
      enum mandated {
        value 3;
      }
    }
  }

  identity segment-list-failure-reason {
    description
      "Base identity that describes why a segment list is invalid.";
  }

  identity path-computation-request-timeout {
    base segment-list-failure-reason;
    description
      "Path computation request timed out";
  }

  identity path-computation-no-route {
    base segment-list-failure-reason;
    description
      " No valid route is returned for path computation request";
  }

  identity no-resources-available {
    base segment-list-failure-reason;
    description
      "Required resources are depleted, not enough resources to estbalish the requested segment-list";
  }

  identity path-computation-bad-node {
    base segment-list-failure-reason;
    description
      "Path computation failure due to a resolution issue of one or more of the hops";
  }

  identity path-computation-routing-loop {
    base segment-list-failure-reason;
    description
      "Path computation failure due to routing loop";
  }

  identity unknown {
    base segment-list-failure-reason;
    description
      "Segment-list is down due to unknown reason";
  }

  identity path-computation-no-route-owner {
    base segment-list-failure-reason;
    description
      "Path computation failure as none of the IGP instances had a valid route to one of the hops";
  }

  identity path-computation-hop-limit-exceeded {
    base segment-list-failure-reason;
    description
      "Path computation failure due to hop limit. No path within the hop limit constraint configured";
  }

  identity srlg-not-disjoint {
    base segment-list-failure-reason;
    description
      "SRLG is shared with primary segment-list and there is no other viable path with dispersed SRLG";
  }

  identity srlg-not-computed-path {
    base segment-list-failure-reason;
    description
      "SRLG is not applicable, as primary segment-list has no applicable SRLG for path computation";
  }

  identity srlg-primary-segment-list-down {
    base segment-list-failure-reason;
    description
      "SRLG is not applicable, as primary segment-list is down";
  }

  identity unresolved-first-segment {
    base segment-list-failure-reason;
    description
      "The router is unable to resolve the first SID (MPLS label value) into one or more outgoing interface(s) and next-hop(s)";
  }

  identity fib-add-pending {
    base segment-list-failure-reason;
    description
      "Segment-list is kept down, when adding next-hop into the FIB";
  }

  identity fib-add-failed {
    base segment-list-failure-reason;
    description
      "FIB has failed to add the next-hop group. Next-hop group represents a group of next-hops for valid segment-lists under a TE-policy";
  }

  identity maximum-label-stack-depth-exceeded {
    base segment-list-failure-reason;
    description
      "The resolution of the named path requires more labels than supported by the datapath.";
  }

  identity pce-update-with-empty-ero {
    base segment-list-failure-reason;
    description
      "PCE update has empty Explicit Route Object (EROs)";
  }

  identity segment-list-admin-down {
    base segment-list-failure-reason;
    description
      "Segment-list is administratively down";
  }

  identity ipv4-hops-in-ipv6-path {
    base segment-list-failure-reason;
    description
      "IPv4 and IPv6 hops are mixed in explicit path";
  }

  identity ipv6-hops-in-ipv4-path {
    base segment-list-failure-reason;
    description
      "IPv6 and IPv4 hops are mixed in explicit path";
  }

  identity sid-hops-in-ip-path {
    base segment-list-failure-reason;
    description
      "SID (label-based) and IP hops are mixed in explicit path";
  }

  identity sid-hops-with-invalid-path-computation {
    base segment-list-failure-reason;
    description
      "SID hops (labeled hops) with path computation local-cspf/pcep is not allowed";
  }

  identity invalid-path-computation {
    base segment-list-failure-reason;
    description
      "Segment-list with unsupported path computation method";
  }

  identity policy-down {
    base segment-list-failure-reason;
    description
      "Traffic engineering policy is down";
  }

  identity pce-association-conflict {
    base segment-list-failure-reason;
    description
      "PCE-association conflict";
  }

  identity retry-on-config-change {
    base segment-list-failure-reason;
    description
      "Segment-list retry attempted due to config change";
  }

  identity clear-command {
    base segment-list-failure-reason;
    description
      "Segment-list retry attempted due to manual clear command";
  }

  identity secondary-segment-list {
    base segment-list-failure-reason;
    description
      "Secondary type segment-list, Primary is always preferred when available";
  }

  identity bfd-down {
    base segment-list-failure-reason;
    description
      "BFD is reported down";
  }

  identity te-rtr-id-not-configured {
    base segment-list-failure-reason;
    description
      "TE router ID config is missing";
  }

  identity pce-down {
    base segment-list-failure-reason;
    description
      "PCE is unavailable";
  }

  identity pcc-down {
    base segment-list-failure-reason;
    description
      "PCC is unavailable";
  }

  identity pce-error {
    base segment-list-failure-reason;
    description
      "PCE response has error or timed-out";
  }

  identity pcc-error {
    base segment-list-failure-reason;
    description
      "PCC responded with error";
  }

  identity delay-metric-limit-exceeded {
    base segment-list-failure-reason;
    description
      "Segment-list delay metric limit exceeded";
  }

  identity invalid-protection-mode {
    base segment-list-failure-reason;
    description
      "Invalid protection mode for the TE-policy type";
  }

  identity no-weight {
    base segment-list-failure-reason;
    description
      "Segment-list with no weight";
  }

  identity exceeds-protection-mode-allowed {
    base segment-list-failure-reason;
    description
      "More than the protection policy allows";
  }

  identity admin-group-missing {
    base segment-list-failure-reason;
    description
      "Admin group info not available at TE database";
  }

  typedef segment-list-failure-reason-type {
    type identityref {
      base segment-list-failure-reason;
    }
  }

  grouping te-policies-top {
    container traffic-engineering-policies {
      if-feature "srl_nokia-feat:te-policies";
      presence "Configure traffic engineering policies";
      must "(../srl_nokia-netinst:type = 'srl_nokia-netinst:default')" {
        error-message "traffic-engineering-policies are only allowed on network-instance of type default";
      }
      description
        "Container with traffic engineering policies";
      uses binding-sid-label-blocks;
      uses explicit-paths;
      uses policy-template;
      uses te-policies;
      uses policy-database;
    }
  }

  grouping binding-sid-label-blocks {
    container binding-sid {
      if-feature "srl_nokia-feat:label-management";
      description
        "Enter the binding-sid context

         Configuration and state related to the label block(s) used for the binding SIDs associated with TE policies";
      leaf static-label-block {
        type leafref {
          path "/srl_nokia-system:system/srl_nokia-mplslbl:mpls/srl_nokia-mplslbl:label-ranges/srl_nokia-mplslbl:static/srl_nokia-mplslbl:name";
        }
        must 'not(/srl_nokia-system:system/srl_nokia-mplslbl:mpls/srl_nokia-mplslbl:label-ranges/srl_nokia-mplslbl:static[srl_nokia-mplslbl:name=current()]/srl_nokia-mplslbl:shared)' {
          error-message "Static label block for binding SIDs should be exclusive (not shared)";
        }
        description
          "Reference to a static label range";
      }
      leaf static-label-block-status {
        config false;
        type enumeration {
          enum available;
          enum unavailable;
        }
        description
          "Status of the label block.

           \t\t\t  The label block may show as unavailable if there is pending cleanup.";
      }
      leaf dynamic-label-block {
        if-feature "srl_nokia-feat:pcep-pcc-pce-init";
        type leafref {
          path "/srl_nokia-system:system/srl_nokia-mplslbl:mpls/srl_nokia-mplslbl:label-ranges/srl_nokia-mplslbl:dynamic/srl_nokia-mplslbl:name";
        }
        description
          "Reference to a dynamic label block";
      }
      leaf dynamic-label-block-status {
        config false;
        if-feature "srl_nokia-feat:pcep-pcc-pce-init";
        type enumeration {
          enum available;
          enum unavailable;
        }
        description
          "Status of the label block

           The label block may show as unavailable if there is pending cleanup";
      }
    }
  }

  grouping explicit-paths {
    container explicit-paths {
      description
        "Enter the explicit-paths context

         Named paths used to specify SR policy segment lists";
      list path {
        key "explicit-path-name";
        leaf explicit-path-name {
          type srl_nokia-comm:name;
          description
            "A unique name to identify the explicit path";
        }
        list hop {
          key "index";
          leaf index {
            type uint8;
            description
              "The index number of the hop. Hops are processed in ascending sequence.";
          }
          container ip {
            presence "ip hop";
            must 'boolean(./ip-address)' {
              error-message "ip-address must be configured in a ip-hop";
            }
            leaf ip-address {
              type srl_nokia-comm:ip-address-unicast-without-local;
              description
                "An IPv4 or IPv6 address that is a hop to be visited on the way to the destination";
            }
            leaf hop-type {
              type enumeration {
                enum strict {
                  description
                    "A strict hop is always one hop away from the previous hop (or from the head-end in the case of the first hop). TE DB translates each strict hop into an adjacency-SID label. To be resolved to an adjacency SID, a strict hop must be a non-local IP address on a connected subnet (representing the neighbor's interface address on this subnet) or it must be a loopback or system address of the directly-connected neighbor.";
                  value 1;
                }
                enum loose {
                  description
                    "A loose hop can be any number of hops away from the previous hop (or from the head-end in the case of the first hop). TE DB translates each loose hop into a node-SID label. A loose hop can be any IP address of the remote router associated with the node SID, not just the IP address associated with the node SID itself.
                     Note that the endpoint of the policy is implicitly considered to be a final loose hop. If the final configured hop (previous hop of this implicit loose hop) is unnecessary TEDB indicates this to SR policy manager and the adjacency SID or node SID of the final confgired hop is omitted from the datapath programming.";
                  value 2;
                }
              }
              default "loose";
            }
          }
          must 'boolean(./ip or ./mpls-label)' {
            error-message "ip or mpls-label must be configured in a hop";
          }
          must 'not(./ip and ./mpls-label)' {
            error-message "ip and mpls-label must not be configured together in a hop";
          }
          leaf mpls-label {
            type srl_nokia-comm:mpls-label-non-reserved;
            description
              "An MPLS label value representing a segment routing instruction";
          }
        }
      }
    }
  }

  grouping entropy-label {
    container entropy-label {
      if-feature "srl_nokia-feat:te-policies-entropy-label";
      description
        "Enter the entropy-label context

         Options for configuring control and data plane aspects of entropy label";
      leaf transmit {
        description
          "Specify conditions for adding ELI/EL under the stack of labels comprising the segment-list";
        type enumeration {
          enum enable {
            value 1;
          }
          enum disable {
            value 2;
          }
        }
        default "disable";
      }
    }
  }

  grouping stats-resource-allocation-status {
    leaf resource-allocation {
      type enumeration {
        enum success {
          description
            "Counter resource allocation succeeded";
        }
        enum failed {
          description
            "Counter resource allocation failed";
        }
      }
      description
        "Indication whether resource allocation succeeded or failed for the set of counters";
    }
  }

  grouping policy-template {
    list template {
      if-feature "srl_nokia-feat:pcep-pcc-pce-init";
      description
        "List of traffic engineering policy templates";
      key "template-name";
      leaf template-name {
        description
          "The name of the traffic engineering policy template";
        type srl_nokia-comm:name;
      }
      leaf template-type {
        mandatory true;
        description
          "Specifies the TE policy template type

           TE Policy can be of type sr-mpls-colored where label based segment-list or segment-lists constitute a candidate path and color with endpoint is used to configure a path. TE Policy can be of type uncolored in which case a single primary LSP can be backed by one or more secondary LSPs";
        type srl_nokia-comm:te-policy-template-type;
      }
      leaf template-id {
        description
          "Unique identifier for the TE Policy template

           Identifier is used by PCE as an unique identifier of the Segment List";
        type union {
          type uint32 {
            range "1..4294967295";
          }
          type enumeration {
            enum default {
              value -1;
            }
          }
        }
        default "default";
      }
      uses entropy-label;
      leaf tag-set {
        if-feature "srl_nokia-feat:internal-tags and srl_nokia-feat:te-policies-tag-set";
        description
          "Tag set to associate with an sr-mpls-uncolored TE policy template";
        type leafref {
          path "/srl_nokia-routing-pol:routing-policy/srl_nokia-routing-pol:tag-set/srl_nokia-routing-pol:name";
        }
      }
      leaf metric {
        description
          "Metric for the TE Policy template";
        type uint32 {
          range "1..16777215";
        }
      }
      container statistics {
        if-feature "srl_nokia-feat:te-policy-statistics";
        description
          "Enter the statistics context

           Traffic Statistics";
        container ingress {
          description
            "Enter the ingress context

             Ingress statistics context";
          leaf admin-state {
            type srl_nokia-comm:admin-state;
            default "disable";
            description
              "Administrative state of the traffic statistics";
          }
        }
        container egress {
          description
            "Enter the egress context

             Egress-statistics context";
          leaf admin-state {
            type srl_nokia-comm:admin-state;
            default "disable";
            description
              "Administrative state of the traffic statistics";
          }
        }
      }
      container protection {
        description
          "Enter the protection context

           Protection context for TE Policy template, hold and wait timers, sBFD, revertive behavior and alike available under this context";
        leaf protection-policy {
          if-feature "srl_nokia-feat:protection-policies";
          description
            "The protection policy for the TE policy template";
          type leafref {
            path "/srl_nokia-system:system/srl_nokia-prot-pol:protection-policies/srl_nokia-prot-pol:policy/srl_nokia-prot-pol:protection-policy-name";
          }
        }
      }
    }
  }

  grouping te-policies {
    list policy {
      description
        "List of traffic engineering policies";
      key "policy-name";
      leaf policy-name {
        description
          "The name of the traffic engineering policy";
        type srl_nokia-comm:name;
      }
      leaf policy-type {
        description
          "Specifies the TE policy type

           TE Policy can be of type sr-mpls-colored where label based segment-list or segment-lists constitute a candidate path and color with endpoint is used to configure a path. TE Policy can be of type uncolored in which case a single primary LSP can be backed by one or more secondary LSPs";
        type srl_nokia-comm:te-policy-type;
        default "sr-mpls-uncolored";
      }
      leaf admin-state {
        description
          "Enable/disable the traffic engineering policy";
        type srl_nokia-comm:admin-state;
        default "enable";
      }
      must "boolean(./binding-sid/mpls-label or ./policy-type = 'sr-mpls-uncolored')" {
        error-message "binding-sid is mandatory for colored type policies";
      }
      must "boolean(./color = 0 or ./color or ./policy-type = 'sr-mpls-uncolored')" {
        error-message "color is mandatory for colored type policies";
      }
      must "boolean(./discriminator or ./policy-type = 'sr-mpls-uncolored')" {
        error-message "discriminator is mandatory for colored type policies";
      }
      container binding-sid {
        description
          "Enter the binding-sid context

           Identifier that opaquely represents the Uncolored Traffic Engineering Policy (a.k.a. SR-TE LSP) to upstream routers";
        leaf mpls-label {
          description
            "MPLS label that represents the Uncolored Traffic Engineering Policy to upstream routers";
          type srl_nokia-comm:mpls-label-non-reserved;
          must "../../head-end != 'local' or ../../../binding-sid/static-label-block" {
            error-message "A static binding SID label block must be defined";
          }
          must "../../head-end != 'local' or ((current() >= /srl_nokia-system:system/srl_nokia-mplslbl:mpls/srl_nokia-mplslbl:label-ranges/srl_nokia-mplslbl:static[srl_nokia-mplslbl:name=current()/../../../binding-sid/static-label-block]/srl_nokia-mplslbl:start-label)"
             + " and (current() <= /srl_nokia-system:system/srl_nokia-mplslbl:mpls/srl_nokia-mplslbl:label-ranges/srl_nokia-mplslbl:static[srl_nokia-mplslbl:name=current()/../../../binding-sid/static-label-block]/srl_nokia-mplslbl:end-label))" {
            error-message "Static binding SID is outside of the defined range";
          }
        }
      }
      leaf color {
        if-feature "srl_nokia-feat:segment-routing-colored-te-policies";
        description
          "Color associated with the sr-mpls-colored TE policy.";
        type uint32 {
          range "0..4294967295";
        }
        must "../policy-type = 'sr-mpls-colored'" {
          error-message "Color is specific to sr-mpls-colored TE policies";
        }
      }
      leaf endpoint {
        mandatory true;
        description
          "Destination of the TE policy";
        type srl_nokia-comm:ip-address-unicast-without-local;
      }
      leaf discriminator {
        if-feature "srl_nokia-feat:segment-routing-colored-te-policies";
        description
          "Discriminator value to make different sr-mpls-colored policies unique";
        type uint32 {
          range "1..4294967295";
        }
        must "../policy-type = 'sr-mpls-colored'" {
          error-message "Discriminator is specific to sr-mpls-colored TE policies";
        }
      }
      must "./policy-type = 'sr-mpls-uncolored' or ./entropy-label/transmit = 'disable'" {
        srl_nokia-ext:if-feature "srl_nokia-feat:te-policies-entropy-label";
        error-message "Entropy label is supported only for sr-mpls-uncolored TE policies";
      }
      uses entropy-label;
      leaf head-end {
        description
          "Targeted head end address for an sr-mpls-colored policy";
        type union {
          type srl_nokia-comm:ip-address-unicast-without-local;
          type enumeration {
            enum local {
              value 1;
            }
          }
        }
        default "local";
        must "../head-end = 'local' or ../policy-type = 'sr-mpls-colored'" {
          error-message "head-end must be local for uncolored type policy";
        }
      }
      leaf tag-set {
        if-feature "srl_nokia-feat:internal-tags and srl_nokia-feat:te-policies-tag-set";
        description
          "Tag set to associate with an sr-mpls-uncolored TE policy";
        type leafref {
          path "/srl_nokia-routing-pol:routing-policy/srl_nokia-routing-pol:tag-set/srl_nokia-routing-pol:name";
        }
        must "../policy-type = 'sr-mpls-uncolored'" {
          error-message "Tag set is specific to sr-mpls-uncolored TE policies";
        }
      }
      leaf re-optimization-timer {
        description
          "Re-optimizaion timer for the TE policy";
        type union {
          type uint32 {
            range "30..10800";
          }
          type enumeration {
            enum disable {
              value -1;
            }
          }
        }
        units "minutes";
        default "30";
      }
      leaf candidate-path-preference {
        if-feature "srl_nokia-feat:segment-routing-colored-te-policies";
        type uint32 {
          range "0..4294967295";
        }
        description
          "One sr-mpls-colored TE policy is considered better than another sr-mpls-colored for thesame (color, endpoint) if it has a higher preference than the other path.";
        must "../policy-type = 'sr-mpls-colored'" {
          error-message "Preference is specific to sr-mpls-colored TE policies";
        }
      }
      leaf metric {
        description
          "Metric for the TE Policy";
        type uint32 {
          range "1..16777215";
        }
        must "../head-end = 'local' " {
          error-message "Metric can only be assigned to a local Colored TE-Policy. Non-local ones such as BGP Colored TE-Policy does not support metric";
        }
      }
      leaf retry-timer {
        description
          "Time between TE policy re-establishment attempts after failure";
        type uint32 {
          range "1..600";
        }
        units "seconds";
        default "30";
      }
      container statistics {
        if-feature "srl_nokia-feat:te-policy-statistics";
        description
          "Enter the statistics context

           Traffic Statistics";
        container ingress {
          must "../../policy-type = 'sr-mpls-uncolored' or ./admin-state = 'disable'" {
            error-message "Statistics are supported only for uncolored type policies";
            srl_nokia-ext:if-feature "not srl_nokia-feat:te-policy-colored-statistics";
          }
          description
            "Enter the ingress context

             Ingress statistics context";
          leaf admin-state {
            type srl_nokia-comm:admin-state;
            default "disable";
            description
              "Administrative state of the traffic statistics";
          }
        }
        container egress {
          description
            "Enter the egress context

             Egress-statistics context";
          must "../../policy-type = 'sr-mpls-uncolored' or ./admin-state = 'disable'" {
            error-message "Statistics are supported only for uncolored type policies";
            srl_nokia-ext:if-feature "not srl_nokia-feat:te-policy-colored-statistics";
          }
          leaf admin-state {
            type srl_nokia-comm:admin-state;
            default "disable";
            description
              "Administrative state of the traffic statistics";
          }
        }
      }
      container protection {
        description
          "Enter the protection context

           Protection context for TE Policy, hold and wait timers, sBFD, revertive behavior and alike available under this context";
        leaf protection-policy {
          if-feature "srl_nokia-feat:protection-policies";
          description
            "The protection policy to use with the TE policy";
          type leafref {
            path "/srl_nokia-system:system/srl_nokia-prot-pol:protection-policies/srl_nokia-prot-pol:policy/srl_nokia-prot-pol:protection-policy-name";
          }
          must "../../head-end = 'local' " {
            error-message "Protection policy can only be assigned to a local Colored TE-Policy";
          }
        }
        container return-path {
          if-feature "srl_nokia-feat:sbfd-return-label";
          description
            "Enter the return-path context

             Context for defining return path identifier";
          leaf mpls-label {
            must 'boolean(../../protection-policy)' {
              error-message "Return path label is only applicable when protection policy is configured";
            }
            description
              "MPLS label that is used by reflector while responding to the sBFD request. Assigned value should uniquely identify the sender. Binding-SID or a Node-SID are commonly used options";
            type srl_nokia-comm:mpls-label-non-reserved;
          }
        }
      }
      uses segment-list;
    }
  }

  grouping pce-associations-config {
    container pce-associations {
      if-feature "srl_nokia-feat:pcep-pcc and srl_nokia-feat:pcep-pcc-pce-association";
      description
        "Enter the pce-associations context

         PCE association policy and diversity ";
      leaf-list diversity {
        max-elements 5;
        description
          "List of diversity names";
        type leafref {
          path "../../../../../../../srl_nokia-netinst:protocols/srl_nokia-pcep:pcep/srl_nokia-pcep:pcc/srl_nokia-pcep:pce-associations/srl_nokia-pcep:diversity/srl_nokia-pcep:association-name";
        }
      }
      leaf-list policy-association {
        max-elements 5;
        description
          "List of PCE associations configured under the PCC";
        type leafref {
          path "../../../../../../../srl_nokia-netinst:protocols/srl_nokia-pcep:pcep/srl_nokia-pcep:pcc/srl_nokia-pcep:pce-associations/srl_nokia-pcep:policy/srl_nokia-pcep:association-name";
        }
      }
    }
  }

  grouping pce-associations-state {
    container pce-associations {
      if-feature "srl_nokia-feat:pcep-pcc and srl_nokia-feat:pcep-pcc-pce-association";
      description
        "Enter the pce-associations context

         PCE association policy and diversity ";
      leaf-list diversity {
        max-elements 5;
        description
          "List of diversity names";
        type leafref {
          path "/srl_nokia-netinst:network-instance/srl_nokia-netinst:protocols/srl_nokia-pcep:pcep/srl_nokia-pcep:pcc/srl_nokia-pcep:pce-associations/srl_nokia-pcep:diversity/srl_nokia-pcep:association-name";
        }
      }
      leaf-list policy-association {
        max-elements 5;
        description
          "List of PCE associations configured under the PCC";
        type leafref {
          path "/srl_nokia-netinst:network-instance/srl_nokia-netinst:protocols/srl_nokia-pcep:pcep/srl_nokia-pcep:pcc/srl_nokia-pcep:pce-associations/srl_nokia-pcep:policy/srl_nokia-pcep:association-name";
        }
      }
    }
  }

  grouping segment-list {
    list segment-list {
      key "segment-list-index";
      leaf segment-list-index {
        description
          "Index to enumerate the different segment lists of a TE policy.";
        type uint8 {
          range "1..32";
        }
      }
      leaf admin-state {
        type srl_nokia-comm:admin-state;
        description
          "Administratively enable or disable a segment list";
      }
      leaf explicit-path {
        type leafref {
          path "../../../explicit-paths/path/explicit-path-name";
        }
      }
      must "boolean(./segment-list-type or ../policy-type = 'sr-mpls-colored')" {
        error-message "segment-list-type is mandatory for uncolored type policies";
      }
      leaf segment-list-type {
        description
          "Segment-list type: primary, standby or secondary

           Standby is programmed in datapath, consumes resources and is ready for a failover any time. Secondary is programmed upon failure of the previous active";
        type enumeration {
          enum primary {
            value 1;
          }
          enum secondary {
            value 2;
          }
          enum standby {
            value 3;
          }
        }
        must "boolean(../../policy-type = 'sr-mpls-uncolored')" {
          error-message "segment-list-type is applicable only for uncolored type policies";
        }
      }
      leaf weight {
        if-feature "srl_nokia-feat:segment-routing-colored-te-policies";
        description
          "Weight of this segment list, used for weighted ECMP between segment lists";
        type uint32 {
          range "1..4294967295";
        }
        must "not(../../policy-type = 'sr-mpls-uncolored')" {
          error-message "Weight is only supported for sr-mpls-colored TE policies";
        }
      }
      leaf segment-list-preference {
        description
          "Preference value of this segment-list

           For an sr-mpls-uncolored TE policy one standby segment list is preferred over another if it has a lower preference value. The implicit default value is 100.";
        type uint32 {
          range "1..255";
        }
        must "../segment-list-type = 'standby'" {
          error-message "Only applicable to standby segment lists";
        }
        must "not(../../policy-type = 'sr-mpls-colored')" {
          error-message "standby segment lists are only supported for sr-mpls-uncolored TE policies";
        }
      }
      container priority {
        description
          "Enter the priority context

           Configure setup and hold priorities to be conveyed to the PCE for preemption purposes";
        leaf hold-priority {
          description
            "Hold priority of a TE policy in relation to preemption action";
          type uint8 {
            range "0..7";
          }
          default "0";
        }
        leaf setup-priority {
          description
            "Setup priority of a TE policy in relation to preemption action";
          type uint8 {
            range "0..7";
          }
          default "7";
        }
      }
      leaf pce-control {
        if-feature "srl_nokia-feat:pcep-pcc";
        must "../pce-control = false() or ../../policy-type = 'sr-mpls-uncolored'" {
          error-message "Applies only to sr-mpls-uncolored te-policies";
        }
        description
          "Set to true for a PCE controlled segment-list";
        type boolean;
      }
      leaf pce-report {
        if-feature "srl_nokia-feat:pcep-pcc";
        must "../pce-report = false() or ../../policy-type = 'sr-mpls-uncolored'" {
          error-message "Applies only to sr-mpls-uncolored te-policies";
        }
        description
          "seto to true to enable reporting of the segment-list to the PCE";
        type boolean;
        default "false";
      }
      container dynamic {
        presence "Enable dynamic computation of the segment list";
        description
          "Configuration and state for dynamic segment lists";
        must "../../policy-type = 'sr-mpls-uncolored'" {
          error-message "Applies only to sr-mpls-uncolored te-policies";
        }
        leaf path-algorithm {
          description
            "Path computation method";
          type dynamic-segment-path-computation-type;
          default "local-cspf";
        }
        leaf fallback-path-algorithm {
          if-feature "srl_nokia-feat:te-policy-local-cspf-fallback";
          description
            "Backup path computation algorithm when PCE becomes unavailable; requires dynamic path computation for uncolored sr-mpls Segment-List type to be set to PCE";
          must "(../path-algorithm = 'pce' and ../../../policy-type = 'sr-mpls-uncolored')" {
            error-message "Applies to sr-mpls-uncolored te-policies with PCE based path computation";
          }
          type enumeration {
            enum none {
              value 1;
            }
            enum local-cspf {
              value 2;
            }
          }
        }
        container te-constraints {
          leaf metric-type {
            must "not(../../../pce-control = true() or ../../../pce-report = true() or ../../path-algorithm = 'pce') or not(../metric-type = 'delay')" {
              srl_nokia-ext:if-feature "not srl_nokia-feat:te-policy-pcep-delay-metric-limit";
              error-message "applicable only for local CSPF segment-lists, pce-control or pce-report not allowed";
            }
            description
              "Metric type used for segment-list computation";
            type metric-type;
            default "igp";
          }
          leaf delay-metric-limit {
            if-feature "srl_nokia-feat:te-policy-delay-metric-limit";
            must "not(../../../pce-control = true() or ../../../pce-report = true() or ../../path-algorithm = 'pce') or ../delay-metric-limit = 'no-limit'" {
              srl_nokia-ext:if-feature "not srl_nokia-feat:te-policy-pcep-delay-metric-limit";
              error-message "applicable only for local CSPF segment-lists, pce-control or pce-report not allowed";
            }
            must "../metric-type = 'delay' or ../delay-metric-limit = 'no-limit'" {
              error-message "delay metric limit is applicable only when metric type is delay";
            }
            description
              "The maximum acceptable delay for the segment-list used via local CSPF during path computation";
            type delay-metric-limit;
            default "no-limit";
          }
          leaf hop-limit {
            description
              "The maximum number of hops for the segment-list";
            type uint8 {
              range "2..255";
            }
            default "255";
          }
          container segment-depth {
            description
              "Enter the segment-depth context

               Configuration for the maximum number of SIDs/segments";
            leaf segment-limit {
              description
                "The maximum number of segments in the segment-list";
              type uint8 {
                range "1..14";
              }
              must '. <= 7' {
                error-message "Valid range for segment-depth is 1..7 labels ";
                srl_nokia-ext:if-feature "srl_nokia-feat:ixr-dnx";
              }
              must '. <= 8' {
                error-message "Valid range for segment-depth is 1..8 labels ";
                srl_nokia-ext:if-feature "srl_nokia-feat:fpcx and not srl_nokia-feat:te-policies-increased-label-stack-fpcx";
              }
            }
          }
          leaf local-sr-protection {
            description
              "Protection offered for local CSPF computed segment-lists";
            type local-sr-protection;
            default "preferred";
          }
          leaf label-stack-reduction {
            description
              "Set to true to enable label stack reduction for local CSPF computed segment-lists";
            type boolean;
            default "true";
          }
          leaf-list exclude-hop {
            description
              "Excluded IP addresses from path computation";
            type srl_nokia-comm:ip-address-unicast-without-local;
            max-elements 10;
          }
          leaf-list exclude-admin-group {
            if-feature "srl_nokia-feat:te-policies-admin-groups";
            max-elements 32;
            description
              "Admin Group name to be excluded in path computation for all the segment-lists under the TE-Policy";
            type leafref {
              path "../../../../../../srl_nokia-te:traffic-engineering/srl_nokia-te:admin-groups/srl_nokia-te:group/srl_nokia-te:name";
            }
          }
          leaf-list include-admin-group {
            if-feature "srl_nokia-feat:te-policies-admin-groups";
            max-elements 32;
            description
              "Admin Group name to be included in path computation for all the segment-lists under the TE-Policy";
            type leafref {
              path "../../../../../../srl_nokia-te:traffic-engineering/srl_nokia-te:admin-groups/srl_nokia-te:group/srl_nokia-te:name";
            }
          }
          leaf-list exclude-srlg {
            if-feature "srl_nokia-feat:te-policy-exclude-srlg";
            max-elements 16;
            description
              "Excluded SRLGs during path computation";
            type leafref {
              path "../../../../../../srl_nokia-te:traffic-engineering/srl_nokia-te:shared-risk-link-groups/srl_nokia-te:group/srl_nokia-te:name";
            }
          }
          leaf secondary-srlg {
            description
              "Set to to true to consider SRLG for secondary and standby segment list of uncolored type";
            type boolean;
            default "false";
            must "not(../secondary-srlg = true() and ../../../segment-list-type = 'primary')" {
              error-message "applicable only for standby/secondary segment-lists";
            }
          }
          uses pce-associations-config;
          description
            "Enter the te-constraints context";
        }
      }
    }
  }

  grouping policy-database {
    container policy-database {
      config false;
      description
        "Enter the policy-database context

         Traffic Engineering Policy Database";
      container sr-colored {
        if-feature "srl_nokia-feat:segment-routing-colored-te-policies";
        description
          "Enter the sr-colored context

           SR MPLS Policy colored Traffic Engineering Paths";
        list policy {
          key "color endpoint";
          leaf color {
            srl_nokia-ext:show-importance "high";
            type uint32;
            description
              "Color associated with the SR MPLS (colored) policy";
          }
          leaf endpoint {
            srl_nokia-ext:show-importance "high";
            type srl_nokia-comm:ip-address-unicast-without-local;
            description
              "Policy endpoint IP address";
          }
          leaf policy-type {
            srl_nokia-ext:show-importance "high";
            type srl_nokia-comm:te-policy-type;
            description
              "Colored Traffic Engineering Policy type";
          }
          leaf tunnel-id {
            type uint32;
            description
              "Colored Traffic Engineering Policy unique tunnel identifier";
          }
          leaf metric {
            srl_nokia-ext:show-importance "high";
            type uint32;
            description
              "Colored Traffic Engineering Policy metric";
          }
          leaf created-time {
            description
              "Colored Traffic Engineering Policy creation time";
            type srl_nokia-comm:date-and-time-delta;
          }
          leaf candidate-path-count {
            srl_nokia-ext:show-importance "high";
            description
              "Colored Traffic Engineering Policy candidate-path count";
            type uint32;
          }
          leaf active-candidate-path-name {
            srl_nokia-ext:show-importance "high";
            description
              "Colored Traffic Engineering Policy active candidate path name";
            type srl_nokia-comm:name;
          }
          uses protection-policy-state;
          uses binding-sid-state;
          uses te-policy-state;
          uses colored-te-policy-statistics;
          uses candidate-paths;
        }
      }
      container sr-uncolored {
        description
          "Enter the sr-uncolored context

           Uncolored Traffic Engineering Policy Paths. Also referred to as SR-TE LSPs";
        list policy {
          key "policy-name protocol-origin";
          description
            "Enter the Uncolored Traffic Engineering Policy Path list instance Also refered to as SR-TE LSP list";
          leaf policy-name {
            srl_nokia-ext:show-importance "high";
            type srl_nokia-comm:name;
            description
              "Name of Uncolored Traffic Engineering Policy";
          }
          leaf protocol-origin {
            srl_nokia-ext:show-importance "high";
            description
              "Uncolored Traffic Engineering Policy, origination source. The method Policy path is computed. This list includes Path Computation Engine, explicitly configured paths, etc.";
            type protocol-origin-type;
          }
          leaf endpoint {
            srl_nokia-ext:show-importance "high";
            type srl_nokia-comm:ip-address-unicast-without-local;
            description
              "Uncolored Traffic Engineering Policy endpoint IP address";
          }
          leaf head-end {
            srl_nokia-ext:show-importance "high";
            type srl_nokia-comm:ip-address-unicast-without-local;
            description
              "Uncolored Traffic Engineering Policy headend IP address";
          }
          leaf policy-type {
            type srl_nokia-comm:te-policy-type;
            description
              "Uncolored Traffic Engineering Policy type";
          }
          leaf tunnel-id {
            type uint32;
            description
              "Uncolored Traffic Engineering Policy unique tunnel identifier";
          }
          leaf metric {
            srl_nokia-ext:show-importance "high";
            type uint32;
            description
              "Uncolored Traffic Engineering Policy metric";
          }
          leaf tag-set {
            srl_nokia-ext:show-importance "high";
            if-feature "srl_nokia-feat:internal-tags and srl_nokia-feat:te-policies-tag-set";
            type leafref {
              path "/srl_nokia-routing-pol:routing-policy/srl_nokia-routing-pol:tag-set/srl_nokia-routing-pol:name";
            }
            description
              "Tag-set associated with this uncolored te-policy";
          }
          leaf created-time {
            description
              "Uncolored Traffic Engineering Policy creation time";
            type srl_nokia-comm:date-and-time-delta;
          }
          leaf segment-list-count {
            srl_nokia-ext:show-importance "high";
            description
              "Uncolored Traffic Engineering Policy segment-list count";
            type uint32;
          }
          leaf active-segment-list-index {
            srl_nokia-ext:show-importance "high";
            description
              "Uncolored Traffic Engineering Policy active segment-list index";
            type uint32;
          }
          uses protection-policy-state;
          uses binding-sid-state;
          uses te-policy-state;
          uses uncolored-te-policy-statistics;
          uses uncolored-dynamic-segment-lists;
        }
      }
      uses te-policies-state;
    }
  }

  grouping candidate-paths {
    description
      "SR policy candidate path grouping";
    list candidate-path {
      description
        "SR policy candidate paths. This list includes local static policies, but only those that have both a color and endpoint.";
      key "protocol-origin discriminator originator-asn originator-address";
      leaf protocol-origin {
        srl_nokia-ext:show-importance "high";
        type protocol-origin-type;
        description
          "Instantiation mechanism used to create the candidate path";
      }
      leaf originator-asn {
        srl_nokia-ext:show-importance "high";
        type uint32;
        description
          "Autonomous System (ASN) Identifier of the node that signalled/instantiated the candidate path on headend";
      }
      leaf originator-address {
        srl_nokia-ext:show-importance "high";
        type srl_nokia-comm:ip-address;
        description
          "IP address Identifier of the node that signalled/instantiated the candidate path on headend";
      }
      leaf discriminator {
        srl_nokia-ext:show-importance "high";
        type uint32;
        description
          "Candidate path discriminator";
      }
      uses candidate-path-state;
      uses protection-policy-state;
      uses binding-sid-state;
      uses colored-dynamic-segment-lists;
    }
  }

  grouping ingress-statistics-state {
    container ingress {
      leaf packets {
        type srl_nokia-comm:zero-based-counter64;
        config false;
        description
          "Number of packets received by the TE policy";
      }
      leaf octets {
        type srl_nokia-comm:zero-based-counter64;
        config false;
        units "byte";
        description
          "Number of octets received by the TE policy";
      }
      uses stats-resource-allocation-status;
      description
        "Enter the ingress context";
    }
  }

  grouping egress-statistics-state {
    container egress {
      leaf packets {
        type srl_nokia-comm:zero-based-counter64;
        config false;
        description
          "Number of packets transmitted by the TE policy";
      }
      leaf octets {
        type srl_nokia-comm:zero-based-counter64;
        config false;
        units "byte";
        description
          "Number of octets transmitted by the TE policy";
      }
      uses stats-resource-allocation-status;
      description
        "Enter the egress context";
    }
  }

  grouping uncolored-te-policy-statistics {
    container statistics {
      if-feature "srl_nokia-feat:te-policy-statistics";
      config false;
      uses ingress-statistics-state;
      uses egress-statistics-state;
      description
        "Enter the statistics context";
    }
  }

  grouping colored-te-policy-statistics {
    container statistics {
      if-feature "srl_nokia-feat:te-policy-colored-statistics";
      config false;
      uses ingress-statistics-state;
      description
        "Enter the statistics context";
    }
  }

  grouping segment-list-statistics {
    container statistics {
      if-feature "srl_nokia-feat:te-policy-colored-statistics";
      description
        "Enter the statistics context

         Segment-list egress statistics";
      uses egress-statistics-state;
    }
  }

  grouping te-policy-state {
    leaf oper-state {
      srl_nokia-ext:show-importance "high";
      config false;
      type oper-state;
      description
        "Traffic Engineering policy operational state.";
    }
    leaf oper-down-reason {
      config false;
      type te-policy-oper-down-reason-type;
      description
        "The reason why the Traffic Engineering policy is operationally down.

         One of the following values:
         -  te-policy-admin-disabled: the TE policy is administratively disabled
         -  te-policy-no-valid-segment-list: the TE policy has no valid segment lists";
    }
    leaf oper-state-change-count {
      config false;
      type uint32;
      description
        "Traffic Engineering Policy operational state change count
         Operational status trnasition from up to down, down to up, etc all accounted under this counter";
    }
    leaf last-oper-state-change {
      config false;
      type srl_nokia-comm:date-and-time-delta;
      description
        "Time elapsed since the last operational state change for the Traffic Engineering Policy";
    }
  }

  grouping dynamic-state {
    description
      "Dynamic Segment List state";
    container dynamic {
      config false;
      description
        "Enter the dynamic context

         Dynamic Segment List";
      leaf path-algorithm {
        description
          "Algorithm used for computation of the Segment List";
        type dynamic-segment-path-computation-type;
      }
      container te-constraints {
        description
          "Enter the te-constraints context

           Traffic Engineering constraints for dynamic segment-lists";
        leaf metric-type {
          description
            "Metric type used for segment-list computation";
          type metric-type;
        }
        leaf delay-metric-limit {
          if-feature "srl_nokia-feat:te-policy-delay-metric-limit";
          description
            "The maximum acceptable delay for the segment-list used via local CSPF during path computation";
          type delay-metric-limit;
        }
        leaf hop-limit {
          description
            "Hop limit contraint used for computation of the Segment List";
          type uint8;
        }
        leaf local-sr-protection {
          description
            "Protection offered for local CSPF computed segment-lists";
          type local-sr-protection;
        }
        leaf label-stack-reduction {
          description
            "If label stack reduction is enabled for the given Segment List";
          type boolean;
        }
        leaf secondary-srlg {
          description
            "If SRLG constraints are taken into account while computing Secondary Segment List";
          type boolean;
        }
        leaf-list exclude-hop {
          description
            "Excluded IP addresses from path computation for the given Segment List";
          type srl_nokia-comm:ip-address-unicast-without-local;
        }
        leaf-list exclude-admin-group {
          if-feature "srl_nokia-feat:te-policies-admin-groups";
          description
            "Admin Group name to be excluded in path computation for all the segment-lists under the TE-Policy";
          type string;
        }
        leaf-list include-admin-group {
          if-feature "srl_nokia-feat:te-policies-admin-groups";
          description
            "Admin Group name to be included in path computation for all the segment-lists under the TE-Policy";
          type string;
        }
        leaf-list exclude-srlg {
          if-feature "srl_nokia-feat:te-policy-exclude-srlg";
          description
            "SRLG links excluded during path computation for the given Segment List";
          type string;
        }
        container segment-depth {
          description
            "Enter the segment-depth context

             Configuration for the maximum number of SIDs/segments";
          leaf segment-limit {
            description
              "The maximum number of segments in the segment-list";
            type uint8;
          }
        }
        uses pce-associations-state;
      }
    }
    uses computed-segments;
  }

  grouping protection-policy-state {
    container protection {
      if-feature "srl_nokia-feat:protection-policies";
      description
        "Enter the protection context

         Protection context for TE Policy, hold and wait timers, sBFD, revertive behavior and alike available under this context";
      leaf protection-policy {
        srl_nokia-ext:show-importance "high";
        description
          "The protection policy to use with the TE policy";
        type srl_nokia-comm:name;
      }
      leaf threshold {
        srl_nokia-ext:show-importance "high";
        description
          "Number of operational segment-lists needed for candidate-path to be operational";
        type uint32;
      }
      container return-path {
        if-feature "srl_nokia-feat:sbfd-return-label";
        description
          "Enter the return-path context

           Context for defining return path identifier";
        leaf mpls-label {
          description
            "MPLS label that is used by reflector while responding to the sBFD request. Assigned value should uniquely identify the sender. Binding-SID or a Node-SID are commonly used options";
          type srl_nokia-comm:mpls-label-non-reserved;
        }
      }
    }
  }

  grouping last-pce-update {
    container last-pce-update {
      if-feature "srl_nokia-feat:pcep-pcc";
      leaf time {
        config false;
        description
          "Indicates the system time when the last update occured.";
        type srl_nokia-comm:date-and-time-delta;
      }
      leaf update-id {
        config false;
        description
          "Indicates the last update ID which was processed.";
        type uint32;
      }
      leaf state {
        config false;
        description
          "Indicates whether the last update was successful or failed.";
        type enumeration {
          enum success {
            value 1;
          }
          enum failure {
            value 2;
          }
        }
      }
      leaf failure-reason {
        config false;
        description
          "Indicates the reason code for last MBB failure.";
        type segment-list-failure-reason-type;
      }
      description
        "Enter the last-pce-update context";
    }
  }

  grouping bfd-state {
    container bfd {
      leaf bfd-state {
        config false;
        description
          "The current state of the BFD session on the LSP path.";
        type enumeration {
          enum not-applicable {
            value 1;
          }
          enum down {
            value 2;
          }
          enum up {
            value 3;
          }
        }
      }
      leaf hold-down-timer-expiry {
        config false;
        type srl_nokia-comm:date-and-time-delta;
        description
          "Time remaining on seamless-bfd hold down timer";
      }
      leaf hold-down-timer {
        config false;
        type uint16;
        units "seconds";
        description
          "Specifies a hold-down timer value when seamless-bfd is enabled

           The timer is started when the number of S-BFD sessions that are up drops below the threshold. The TE-policy path is not considered to be up again until the hold-down timer has expired and the number of S-BFD sessions that are up equals or exceeds the threshold.
           A grace preiod after session down such that sBFD session flaps does not impact active path.

           The default is 3 seconds.";
      }
      leaf bfd-wait-for-up-timer {
        config false;
        type uint16;
        units "seconds";
        description
          "Specifies a wait-for-up timer value when seamless-bfd is enabled

           This timer takes effect if BFD does not come up, or BFD goes from up to down. The timer is started when BFD is first enabled on a segment-list or BFD transitions from up to down. When the timer expires if BFD is not yet come up, then the path is torn down by removing it from the TTM and the PI and the retry timer is started.

           The default is 3 seconds.";
      }
      leaf bfd-wait-for-up-expiry {
        config false;
        description
          "The time in seconds left to wait for the bfd session to be up.";
        type srl_nokia-comm:date-and-time-delta;
      }
      description
        "Enter the bfd context";
    }
  }

  grouping computed-segments {
    container computed-segments {
      list segment {
        key "segment-index";
        leaf segment-index {
          type uint8;
          description
            "Index to enumerate the different segments in a segment-list";
        }
        leaf hop-type {
          config false;
          description
            "Hop type.";
          type enumeration {
            enum ipv4 {
              value 1;
            }
            enum ipv6 {
              value 2;
            }
            enum unnum {
              value 3;
            }
          }
        }
        leaf ip-address {
          config false;
          description
            "IP Address for this hop.";
          type srl_nokia-comm:ip-address-unicast-without-local;
        }
        leaf is-loose {
          config false;
          description
            "Indicates if this tunnel hop is loose.";
          type boolean;
        }
        leaf unnumbered-if-id {
          config false;
          description
            "The value of unnumbered interface identifier of this hop.";
          type uint32;
        }
        leaf router-id {
          config false;
          description
            "The value of router ID.";
          type srl_nokia-comm:ip-address;
        }
        container sid-value {
          leaf mpls-label {
            description
              "Label recorded for this hop.";
            type uint32;
          }
          description
            "Enter the sid-value context";
        }
        leaf sid-type {
          config false;
          description
            "Type of Segment Identifier (SID).";
          type enumeration {
            enum not-applicable {
              value 1;
            }
            enum node-sid {
              value 2;
            }
            enum adjacency-sid {
              value 3;
            }
          }
        }
      }
      description
        "Enter the computed-segments context";
    }
  }

  grouping binding-sid-state {
    container binding-sid {
      description
        "Enter the binding-sid context

         Identifier that opaquely represents the Colored Traffic Engineering Policy to upstream routers";
      leaf mpls-label {
        srl_nokia-ext:show-importance "high";
        description
          "MPLS label that represents the Colored Traffic Engineering Policy to upstream routers";
        type srl_nokia-comm:mpls-label-non-reserved;
      }
      leaf allocation-status {
        description
          "If the same BSID is used by another Colored TE-Policy candidate path or by an Uncolored TE-Policy";
        type boolean;
      }
    }
  }

  grouping candidate-path-state {
    leaf candidate-path-preference {
      srl_nokia-ext:show-importance "high";
      type uint32;
      description
        "Candidate path preference";
    }
    container bfd {
      description
        "Enter the bfd context

         BFD hold timer";
      leaf hold-down-timer-expiry {
        config false;
        type srl_nokia-comm:date-and-time-delta;
        description
          "Time remaining on seamless-bfd hold down timer";
      }
      leaf hold-down-timer {
        config false;
        type uint16;
        units "seconds";
        description
          "Specifies a hold-down timer value when seamless-bfd is enabled

           The timer is started when the number of S-BFD sessions that are up drops below the threshold. The TE-policy path is not considered to be up again until the hold-down timer has expired and the number of S-BFD sessions that are up equals or exceeds the threshold.
           A grace preiod after session down such that sBFD session flaps does not impact active path.

           The default is 3 seconds.";
      }
    }
    leaf revert-timer-expiry {
      config false;
      type srl_nokia-comm:date-and-time-delta;
      description
        "Time remanining on revert-timer";
    }
    leaf revert-timer {
      type uint32;
      units "seconds";
      description
        "Revert timer for the candidate path.

         Timer till a revert to best path after it is recovered from a failure.

         The default is 0 seconds.";
    }
    leaf forwarding-state {
      srl_nokia-ext:show-importance "high";
      type forwarding-state;
      description
        "Forwarding state of the candidate-path, tells about the activeness of candidate-path in the data-path.

          active - programmed in data path as best candidate path and enabled for forwarding traffic
          backup - Programmed in data path for uniform fail-over and forwarding sBFD / OAM packets,
          inactive - Programmed in data path as standby and forwarding sBFD / OAM packets.";
    }
    leaf oper-state {
      srl_nokia-ext:show-importance "high";
      config false;
      type oper-state;
      description
        "Candidate path operational state";
    }
    leaf last-oper-state-change {
      config false;
      type srl_nokia-comm:date-and-time-delta;
      description
        "Time elapsed since the last operational state change for the Traffic Engineering Policy";
    }
    leaf oper-down-reason {
      config false;
      type candidate-path-failure-reason-type;
      description
        "The reason why the Candidate path is operationally down.

         One of the following values:

          -   The candidate path does not have enough number of operationally up segment lists that meets or exceeds the threshold
          -   The candidate path does not have any valid segment list
          -   Candidate path with higher preference or protocol-origin, lower value of originator or higher value of discriminator is available
          -   The candidate path is administratively disabled
          -   No free labels in the label-range
          -   Binding SID already in use by another TE-Policy
          -   Protection mode assigned to others CPs within the same TE-Policy do no match";
    }
    leaf oper-state-change-count {
      config false;
      type uint32;
      description
        "Traffic Engineering Policy candidate-path operational state change count
         Operational status transition from up to down, down to up, etc all accounted under this counter";
    }
    leaf candidate-path-name {
      srl_nokia-ext:show-importance "high";
      description
        "Candidate path name";
      type srl_nokia-comm:name;
    }
    leaf segment-list-count {
      srl_nokia-ext:show-importance "high";
      description
        "Segment-list count for Candidate Path";
      type uint32;
    }
    leaf operational-segment-list-count {
      srl_nokia-ext:show-importance "high";
      description
        "Operational segment-list count for Candidate Path";
      type uint32;
    }
  }

  grouping uncolored-dynamic-segment-lists {
    list segment-list {
      key "segment-list-index";
      leaf segment-list-index {
        type uint8 {
          range "1..32";
        }
        description
          "Index to enumerate the different segment lists.";
      }
      uses segment-list-oper-state-group;
      uses segment-list-state;
    }
  }

  grouping colored-dynamic-segment-lists {
    list segment-list {
      key "segment-list-index";
      leaf segment-list-index {
        type uint8 {
          range "1..32";
        }
        description
          "Index to enumerate the different segment lists.";
      }
      uses segment-list-oper-state-group;
      uses segment-list-state;
      uses segment-list-statistics;
    }
  }

  grouping segment-list-oper-state-group {
    leaf oper-state {
      srl_nokia-ext:show-importance "high";
      config false;
      type oper-state;
      description
        "Segment list operational state";
    }
    leaf failed-reason {
      config false;
      type segment-list-failure-reason-type;
      description
        "The reason why the segment list is invalid.

         One of the following values:
         -  unresolved-first-segment: the first SID (MPLS label value) cannot be resolved into one or more outgoing interface(s) and next-hop(s)
         -  unresolved-named-path: the most recent query to TEDB about the named path (triggered by periodic re-optimization or initially) indicated that the named path is not viable";
    }
    leaf forwarding-state {
      srl_nokia-ext:show-importance "high";
      config false;
      type forwarding-state;
      description
        "Forwarding state of the segment-list, tells about the activeness of segment-list in the data-path.
          active - programmed in data path and enabled for forwarding traffic
          backup - Programmed in data path for uniform fail-over and forwarding sBFD / OAM packets,
          inactive - Programmed in data path as standby and forwarding sBFD / OAM packets.";
    }
    leaf last-oper-state-change {
      config false;
      type srl_nokia-comm:date-and-time-delta;
      description
        "Time elapsed since the last operational state change for the segment-list";
    }
    leaf oper-state-change-count {
      config false;
      type uint32;
      description
        "Traffic Engineering Policy segment-list operational state change count
         Operational status trnasition from up to down, down to up, etc all accounted under this counter";
    }
    leaf entropy-label-transmit {
      config false;
      if-feature "srl_nokia-feat:te-policies-entropy-label";
      description
        "True if an entropy label is being inserted after the labels of this segment list";
      type boolean;
    }
  }

  grouping segment-list-state {
    leaf segment-list-type {
      srl_nokia-ext:show-importance "high";
      config false;
      type enumeration {
        enum primary {
          value 1;
        }
        enum secondary {
          value 2;
        }
        enum standby {
          value 3;
        }
      }
      description
        "Segment-list type: primary, standby or secondary
         Standby is programmed in datapath, consumes resources and is ready for a failover any time. Secondary is programmed upon failure of the previous active";
    }
    leaf pce-report {
      if-feature "srl_nokia-feat:pcep-pcc";
      srl_nokia-ext:show-importance "high";
      description
        "PCE Reporting for Traffic Engineering Policy Segment-list";
      type boolean;
    }
    leaf pce-control {
      if-feature "srl_nokia-feat:pcep-pcc";
      srl_nokia-ext:show-importance "high";
      description
        "PCE Control status for Traffic Engineering Policy Segment-list";
      type boolean;
    }
    leaf segment-list-preference {
      srl_nokia-ext:show-importance "high";
      description
        "Segment List preference for a given list under Traffic Engineering Policy";
      type uint8;
    }
    leaf weight {
      srl_nokia-ext:show-importance "high";
      description
        "Weight of this segment list, used for weighted ECMP between segment lists";
      type uint32;
    }
    leaf explicit-path {
      srl_nokia-ext:show-importance "high";
      description
        "Explicit-path used for instantiating Segment List under Traffic Engineering Policy";
      type srl_nokia-comm:name;
    }
    leaf metric {
      srl_nokia-ext:show-importance "high";
      description
        "Metric of a given Segment List";
      type uint32;
    }
    leaf igp-metric {
      srl_nokia-ext:show-importance "high";
      type uint32;
      description
        "IGP metric of given Segment List";
    }
    leaf te-metric {
      srl_nokia-ext:show-importance "high";
      type uint32;
      description
        "TE metric of given Segment List";
    }
    leaf delay-metric {
      srl_nokia-ext:show-importance "high";
      type uint32;
      description
        "Delay metric of given Segment List";
    }
    leaf lsp-id {
      config false;
      type uint32;
      description
        "Unique internal identifier of segment-list";
    }
    leaf retry-attempts {
      config false;
      type uint32;
      description
        "Number of unsuccessful attempts made to signal the segment-list";
    }
    leaf last-retry-attempt {
      config false;
      type srl_nokia-comm:date-and-time-delta;
      description
        "Time elapsed since the last retry attempt to re-established the segment-list";
    }
    leaf last-reoptimization-attempt {
      config false;
      type srl_nokia-comm:date-and-time-delta;
      description
        "Time elapsed since last path re-optimization attempt on the segment-list";
    }
    leaf next-retry-attempt {
      config false;
      type srl_nokia-comm:date-and-time-delta;
      description
        "Time remaining for next retry attempt to re-established the segment-list";
    }
    leaf next-reoptimization-attempt {
      config false;
      type srl_nokia-comm:date-and-time-delta;
      description
        "Time remaining for next path re-optimization attempt on the segment-list";
    }
    leaf path-computation-requests {
      config false;
      type uint32;
      description
        "Number of path computation requests made for the segment-list";
    }
    leaf revert-timer-expiry {
      config false;
      type srl_nokia-comm:date-and-time-delta;
      description
        "Time remanining on revert-timer";
    }
    leaf revert-timer {
      type uint32;
      units "seconds";
      description
        "Revert timer for the segment-list.

         Timer till a revert to primary/best path after it is recovered from a failure. In case of uncolored te-policy, applies to primary segment-list and in case of colored te-policy applies to best candidate path.

         The default is 0 seconds.";
    }
    uses bfd-state;
    uses dynamic-state;
    uses mbb-state;
    uses last-pce-update;
  }

  grouping mbb-state {
    container mbb {
      config false;
      description
        "Enter the mbb context

         The make-before-break operational information.";
      container last-mbb {
        description
          "Enter the last-mbb context

           The last make-before-break operational information.";
        leaf type {
          description
            "Indicates the type of the make-before-break (MBB) that is in progress.";
          type enumeration {
            enum none {
              value 1;
            }
            enum timer-based-reoptimization {
              value 2;
            }
            enum manual-resignal {
              value 3;
            }
            enum pce-update {
              value 4;
            }
          }
        }
        leaf state {
          description
            "Indicates whether the last make-before-break was successful, failed or was not required as path was already optimal.";
          type enumeration {
            enum success {
              value 1;
            }
            enum failure {
              value 2;
            }
            enum path-optimal {
              value 3;
            }
          }
        }
        leaf end-time {
          description
            "Specifies the system time when the last MBB ended.";
          type srl_nokia-comm:date-and-time-delta;
        }
        leaf failed-reason {
          description
            "Indicates the reason code for last MBB failure.";
          type segment-list-failure-reason-type;
        }
        leaf old-metric {
          description
            "Metric of the Segment List prior to last MBB";
          type uint32;
        }
      }
      container in-progress-mbb {
        description
          "Enter the in-progress-mbb context

           The in progress make-before-break operational information.";
        leaf type {
          description
            "Indicates the type of the make-before-break (MBB) that is in progress.";
          type enumeration {
            enum none {
              value 1;
            }
            enum timer-based-reoptimization {
              value 2;
            }
            enum manual-resignal {
              value 3;
            }
            enum pce-update {
              value 4;
            }
          }
        }
        leaf start-time {
          description
            "Indicates the system time when the in-progress MBB started.";
          type srl_nokia-comm:date-and-time-delta;
        }
      }
    }
  }

  grouping te-policies-state {
    leaf active-te-policies {
      config false;
      type uint32;
      description
        "Number of active Traffic Engineering Polices";
    }
    leaf total-te-policies {
      config false;
      type uint32;
      description
        "Number of total Traffic Engineering Policies (irrespective of the operational state)";
    }
  }

  augment "/srl_nokia-netinst:network-instance" {
    uses te-policies-top;
  }
}
