module srl_nokia-igmp-types {
  yang-version 1.1;
  prefix srl_nokia-igmp-types;
  namespace "urn:nokia.com:srlinux:igmp:igmp-types";

  organization
    "Nokia";
  contact
    "Nokia SR Linux Support
     Web: <http://www.nokia.com>";
  description
    "This yang file contains common IGMP and MLD types and identities";

  revision 2021-06-30 {
    description
      "SRLinux 21.6.1";
  }

  typedef learn-type {
    description
      "How this group entry was learned.";
    type enumeration {
      enum static {
        value 1;
        description
          "This group entry was statically configured.";
      }
      enum dynamic {
        value 2;
        description
          "This group entry was learned by the protocol.";
      }
      enum bgp-smet {
        value 3;
        description
          "This group entry was learned from a bgp SMET route.";
      }
      enum bgp-sync {
        value 4;
        description
          "This group entry was learned from a bgp JOIN SYNC route.";
      }
    }
  }

  typedef filter-mode {
    description
      "The type of group membership.";
    type enumeration {
      enum include {
        value 1;
        description
          "In include mode, reception of packets sent
           to the specified multicast address is requested
           only from those IP source addresses listed in the
           source-list parameter";
      }
      enum exclude {
        value 2;
        description
          "In exclude mode, reception of packets sent
           to the given multicast address is requested
           from all IP source addresses except those
           listed in the source-list parameter.";
      }
    }
  }

  typedef mld-version {
    description
      "The MLD protocol version.";
    type enumeration {
      enum 1 {
        value 1;
      }
      enum 2 {
        value 2;
      }
    }
  }

  typedef igmp-version {
    description
      "The IGMP protocol version.";
    type enumeration {
      enum 1 {
        value 1;
      }
      enum 2 {
        value 2;
      }
      enum 3 {
        value 3;
      }
    }
  }

  typedef forwarding-state {
    description
      "Forwarding state.";
    type enumeration {
      enum forward {
        value 1;
      }
      enum block {
        value 2;
      }
    }
  }
}
