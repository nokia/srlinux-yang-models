module srl_nokia-policy-forwarding {
  yang-version 1.1;
  namespace "urn:nokia.com:srlinux:acl:policy-forwarding";
  prefix srl_nokia-pol-fwd;

  import srl_nokia-packet-match-types {
    prefix srl_nokia-pkt-match-types;
  }
  import srl_nokia-network-instance {
    prefix srl_nokia-netinst;
  }
  import srl_nokia-common {
    prefix srl_nokia-comm;
  }
  import srl_nokia-extensions {
    prefix srl_nokia-ext;
  }
  import srl_nokia-features {
    prefix srl_nokia-feat;
  }
  import srl_nokia-interfaces {
    prefix srl_nokia-if;
  }
  import srl_nokia-acl {
    prefix srl_nokia-acl;
  }
  import srl_nokia-static-routes {
    prefix srl_nokia-static-routes;
  }
  import srl_nokia-qos {
    prefix srl_nokia-qos;
  }
  import srl_nokia-qos-global-policers {
    prefix srl_nokia-qos-glb-pol;
  }

  organization
    "Nokia";
  contact
    "Nokia SR Linux Support
     Web: <http://www.nokia.com>";
  description
    "This module defines configuration and operational state data for policy-forwarding related objects.";

  revision 2026-07-31 {
    description
      "SRLinux 26.7.1";
  }
  revision 2026-04-30 {
    description
      "SRLinux 26.3.2";
  }
  revision 2026-03-31 {
    description
      "SRLinux 26.3.1";
  }
  revision 2025-10-31 {
    description
      "SRLinux 25.10.1";
  }
  revision 2025-03-31 {
    description
      "SRLinux 25.3.1";
  }
  revision 2024-10-31 {
    description
      "SRLinux 24.10.1";
  }
  revision 2024-07-31 {
    description
      "SRLinux 24.7.1";
  }
  revision 2024-03-31 {
    description
      "SRLinux 24.3.1";
  }
  revision 2023-07-31 {
    description
      "SRLinux 23.7.1";
  }
  revision 2023-03-31 {
    description
      "SRLinux 23.3.1";
  }
  revision 2022-11-30 {
    description
      "SRLinux 22.11.1";
  }
  revision 2022-06-30 {
    description
      "SRLinux 22.6.1";
  }
  revision 2022-03-31 {
    description
      "SRLinux 22.3.1";
  }
  revision 2021-11-30 {
    description
      "SRLinux 21.11.1";
  }

  grouping pf-decap-actions {
    leaf decap-network-instance {
      type leafref {
        path "/srl_nokia-netinst:network-instance/srl_nokia-netinst:name";
      }
      must '(/srl_nokia-netinst:network-instance[srl_nokia-netinst:name=current()]/srl_nokia-netinst:type = "srl_nokia-netinst:ip-vrf")' {
        error-message "decap network-instance must be of type 'ip-vrf'";
      }
      must 'not(../network-instance)' {
        error-message "decap-network-instance is mutually exclusive with network-instance action";
      }
      must '../decap-fallback-network-instance and ../post-decap-network-instance' {
        error-message "decap-network-instance action is not valid without the other two decap actions";
      }
      must '. != ../decap-fallback-network-instance' {
        error-message "decap-network-instance and decap-fallback-network-instance cannot be the same";
      }
      must 'string(../../../../global-decap-policy) != ../../../policy-id' {
        error-message "action not supported in the global-decap-policy";
      }
      must "../../../type != 'match-action'" {
        error-message "decap-network-instance action is not supported when the policy type is match-action";
      }
      description
        "Matching packets should be looked up in the referenced network-instance that is expected to contain 'routes' that perform IP tunnel decapsulation

         If there is a match, the packet should be decapsulated and route lookup on the new header should happen in the post-decap-network-instance.
         If there is no match, the packet should be looked up in the decap-fallback-network-instance.
         Configuration of this leaf is not valid without configuration for decap-fallback-network-instance and post-decap-network-instance.

         Configuration of this leaf is mutually exclusive with the network-instance action.

         Note: The only entries in the decap-network-instance that are relevant to this PBF action are special decap entries programmed by gRIBI.";
    }
    leaf decap-fallback-network-instance {
      type leafref {
        path "/srl_nokia-netinst:network-instance/srl_nokia-netinst:name";
      }
      must '. != ../decap-network-instance' {
        error-message "decap-network-instance and decap-fallback-network-instance cannot be the same";
      }
      must '. != ../post-decap-network-instance' {
        error-message "post-decap-network-instance and decap-fallback-network-instance cannot be the same";
      }
      must '(/srl_nokia-netinst:network-instance[srl_nokia-netinst:name=current()]/srl_nokia-netinst:type = "srl_nokia-netinst:ip-vrf")' {
        error-message "decap-fallback network-instance must be of type 'ip-vrf'";
      }
      must '../decap-network-instance' {
        error-message "decap-fallback-network-instance action is not valid without decap-network-instance configuration";
      }
      must 'string(../../../../global-decap-policy) != ../../../policy-id' {
        error-message "action not supported in the global-decap-policy";
      }
      must "../../../type != 'match-action'" {
        error-message "decap-network-instance action is not supported when the policy type is match-action";
      }
      description
        "Specifies the network-instance used as a fallback instance for lookup when applying the decap-network-instance action results in no match for the packet";
    }
    leaf post-decap-network-instance {
      type leafref {
        path "/srl_nokia-netinst:network-instance/srl_nokia-netinst:name";
      }
      must "(/srl_nokia-netinst:network-instance[srl_nokia-netinst:name=current()]/srl_nokia-netinst:type = \"srl_nokia-netinst:ip-vrf\") or
                        (/srl_nokia-netinst:network-instance[srl_nokia-netinst:name=current()]/srl_nokia-netinst:type = \"srl_nokia-netinst:default\")" {
        error-message "post-decap network-instance must be of type 'ip-vrf' or 'default'";
      }
      must '../decap-network-instance' {
        error-message "post-decap action is not valid without decap-network-instance configuration";
      }
      must 'string(../../../../global-decap-policy) != ../../../policy-id' {
        error-message "action not supported in the global-decap-policy";
      }
      must "../../../type != 'match-action'" {
        error-message "decap-network-instance action is not supported when the policy type is match-action";
      }
      description
        "Specifies the network-instance used for lookup on the new header when applying the decap-network-instance action results in a match for the packet";
    }
  }

  grouping pf-encap-gre-config {
    container encapsulate-gre {
      if-feature "srl_nokia-feat:policy-based-forwarding-encapsulate-gre";
      description
        "Enter the encapsulate-gre context

         Container for the GRE encapsulation actions to be applied to packets matching the policy forwarding rule.";
      list target {
        key "id";
        max-elements 4;
        description
          "Identifier for the GRE target group.
           Each target specified within this list should be treated as a
           endpoint to which packets should be GRE encapsulated. Where the
           set of destinations described within a single entry expands to
           more than one destination IP address, packets should be load
           shared across the destination using the local system's ECMP hashing
           mechanisms.";
        leaf id {
          type string {
            length "0..64";
          }
          description
            "A unique identifier for the target.";
        }
        leaf source {
          type srl_nokia-comm:ip-address;
          description
            "The source IP address that should be used when encapsulating
             packets from the local system.";
          must "(contains(., '.') and not(starts-with(., '0.') or starts-with(., '127.') or (number(substring-before(., '.')) >= 224))) or (contains(., ':') and not(re-match(., '[0:]+') or re-match(., '[0:]+:0*1') or re-match(., '[fF][fF].*') or re-match(., '[fF][eE]8.*') or re-match(., '[fF][eE]9.*') or re-match(., '[fF][eE][aA].*') or re-match(., '[fF][eE][bB].*')))" {
            error-message "Not a valid unicast address";
          }
        }
        leaf destination {
          type srl_nokia-comm:ip-prefix;
          description
            "The set of destination addresses that should be encapsulated towards.
             Where a subnet is specified, each address within the subnet should be
             treated as an independent destination for encapsulated traffic. Packets
             should be distributed with ECMP across the set of tunnel destination
             addresses.";
          must "(contains(., '.') and not(starts-with(., '0.') or starts-with(., '127.') or (number(substring-before(., '.')) >= 224))) or (contains(., ':') and not(re-match(., '[0:]+') or re-match(., '[0:]+:0*1') or re-match(., '[fF][fF].*') or re-match(., '[fF][eE]8.*') or re-match(., '[fF][eE]9.*') or re-match(., '[fF][eE][aA].*') or re-match(., '[fF][eE][bB].*')))" {
            error-message "Not a valid unicast address";
          }
        }
        leaf ip-ttl {
          type uint8;
          description
            "The TTL that should be specified in the IP header of the GRE packet
             encapsulating the packet matching the rule.";
        }
        must "../../../../type = 'pbr-policy'" {
          error-message "encapsulate-gre is only supported when type is pbr-policy";
        }
        must "(string(../../network-instance) = '')" {
          error-message "When policy type is pbr-policy, network-instance must not be set with encapsulate-gre.";
        }
        must "(string(../../next-hop) = '')" {
          error-message "When policy type is pbr-policy, next-hop and encapsulate-gre must not be both set.";
        }
        must "(string(../../next-hop-group) = '')" {
          error-message "When policy type is pbr-policy, next-hop-group and encapsulate-gre must not be both set.";
        }
        must 'string(../../../../../global-decap-policy) != ../../../../policy-id' {
          error-message "action not supported in the global-decap-policy";
        }
      }
    }
  }

  grouping pf-action-config {
    container action {
      description
        "Enter the action context

         Container for the actions to be applied to packets matching the policy forwarding rule.";
      leaf network-instance {
        type leafref {
          path "/srl_nokia-netinst:network-instance/srl_nokia-netinst:name";
        }
        must '(/srl_nokia-netinst:network-instance[srl_nokia-netinst:name=current()]/srl_nokia-netinst:type = "srl_nokia-netinst:ip-vrf") or (/srl_nokia-netinst:network-instance[srl_nokia-netinst:name=current()]/srl_nokia-netinst:type = "srl_nokia-netinst:default")' {
          error-message "PBF is not supported into a network-instance type other than 'ip-vrf' or 'default'";
        }
        must "../../../type = 'pbr-policy' and ../next-hop != ''" {
          error-message "On the current platform, network-instance is only supported if policy type is pbr-policy and next-hop is configured";
          srl_nokia-ext:if-feature "srl_nokia-feat:trident4";
        }
        must 'string(../../../../global-decap-policy) != ../../../policy-id' {
          error-message "action not supported in the global-decap-policy";
        }
        must "../../../type != 'match-action'" {
          error-message "network-instance redirect action is not supported when the policy type is match-action";
        }
        must "string(current()) = '' or string(../next-hop-group) = ''" {
          error-message "Action network-instance is not supported with action next-hop-group";
        }
        description
          "When this leaf is set, packets matching the match criteria for the forwarding rule should be looked up in the network-instance that is referenced rather than the network-instance with which the interface is associated.";
      }
      uses pf-encap-gre-config;
      uses pf-decap-actions {
        if-feature "srl_nokia-feat:policy-based-forwarding-decap-actions";
      }
      leaf next-hop {
        if-feature "srl_nokia-feat:policy-based-forwarding-nh-transport";
        must "../../../type = 'pbr-policy'" {
          error-message "next-hop is only supported when type is pbr-policy";
        }
        must 'string(../../../../global-decap-policy) != ../../../policy-id' {
          error-message "action not supported in the global-decap-policy";
        }
        type srl_nokia-comm:ip-address;
        description
          "When this leaf is set, packets matching the match criteria for the forwarding rule will be routed as if their destination address had been the specified next-hop.";
      }
      leaf decapsulate-gue {
        if-feature "srl_nokia-feat:policy-based-forwarding-decapsulate-gue";
        must "../../../type = 'pbr-policy'" {
          error-message "decapsulate-gue is only supported when type is pbr-policy";
        }
        must 'string(../../../../global-decap-policy) = ../../../policy-id' {
          error-message "action is only supported in the global-decap-policy";
        }
        must "/srl_nokia-netinst:network-instance[srl_nokia-netinst:name=current()/../../../../../srl_nokia-netinst:name]/srl_nokia-netinst:type = 'srl_nokia-netinst:default'" {
          error-message "decapsulate actions are only supported in a pbr-policy associated with the default network-instance";
        }
        must "not (current() = true()) or string(../../match/ipv4/protocol) = '' or string (../../match/ipv4/protocol) = '17' or string(../../match/ipv4/protocol) = 'udp'" {
          error-message "protocol must be unset or udp if decapsulate-gue action is configured";
        }
        must "not(current() = true()) or string(../../match/ipv4/destination-ip/prefix) != '' or string(../../match/ipv4/destination-ip/prefix-list) != '' or
              string(../../match/ipv6/destination-ip/prefix) != '' or string(../../match/ipv6/destination-ip/prefix-list) != ''" {
          error-message "destination-ip must be configured if decapsulate-gue action is configured";
        }
        must "not(current() = true()) or string(../../match/transport/destination-port) = '' or string(../../match/transport/destination-port) = '6080'" {
          error-message "when decapsulate-gue is true, destination-port must be 6080";
        }
        type boolean;
        description
          "Remove the Generic UDP Encapsulation (GUE) IP-UDP headers from packets matching the rule";
      }
      leaf decapsulate-gre {
        if-feature "srl_nokia-feat:policy-based-forwarding-decapsulate-gre";
        must "../../../type = 'pbr-policy'" {
          error-message "decapsulate-gre is only supported when type is pbr-policy";
        }
        must 'string(../../../../global-decap-policy) = ../../../policy-id' {
          error-message "action is only supported in the global-decap-policy";
        }
        must "/srl_nokia-netinst:network-instance[srl_nokia-netinst:name=current()/../../../../../srl_nokia-netinst:name]/srl_nokia-netinst:type = 'srl_nokia-netinst:default'" {
          error-message "decapsulate actions are only supported in a pbr-policy associated with the default network-instance";
        }
        must "not (current() = true()) or
              ( (string(../../match/ipv4/protocol) = '' or string (../../match/ipv4/protocol) = '47' or string(../../match/ipv4/protocol) = 'gre')) " {
          error-message "protocol must be unset or gre if decapsulate-gre action is configured";
        }
        must "not (current() = true()) or
              ( (string(../../match/ipv6/next-header) = '' or string (../../match/ipv6/next-header) = '47' or string(../../match/ipv6/next-header) = 'gre'))" {
          error-message "next-header must be unset or gre if decapsulate-gre action is configured";
        }
        type boolean;
        description
          "Remove the Generic Routing Encapsulation (GRE) header from packets matching the rule";
      }
      must 'not(../../../global-decap-policy = ../../policy-id) or decapsulate-gre = true() or decapsulate-gue = true() or decapsulate-mpls-in-udp = true() or decapsulate-ip-in-ip = true()' {
        error-message "every rule of the global-decap-policy must have a decapsulate-x action";
      }
      leaf decapsulate-mpls-in-udp {
        if-feature "srl_nokia-feat:policy-based-forwarding-decapsulate-mpls-udp";
        must "../../../type = 'pbr-policy'" {
          error-message "decapsulate-mpls-in-udp is only supported when type is pbr-policy";
        }
        must 'string(../../../../global-decap-policy) = ../../../policy-id' {
          error-message "action is only supported in the global-decap-policy";
        }
        must "/srl_nokia-netinst:network-instance[srl_nokia-netinst:name=current()/../../../../../srl_nokia-netinst:name]/srl_nokia-netinst:type = 'srl_nokia-netinst:default'" {
          error-message "decapsulate actions are only supported in a pbr-policy associated with the default network-instance";
        }
        must "not (current() = true()) or string(../../match/ipv4/protocol) = '' or string (../../match/ipv4/protocol) = '17' or string(../../match/ipv4/protocol) = 'udp'" {
          error-message "protocol must be unset or udp if decapsulate-mpls-in-udp action is configured";
        }
        must "not(current() = true()) or string(../../match/ipv4/destination-ip/prefix) != '' or string(../../match/ipv4/destination-ip/prefix-list) != '' or
              string(../../match/ipv6/destination-ip/prefix) != '' or string(../../match/ipv6/destination-ip/prefix-list) != ''" {
          error-message "destination-ip must be configured if decapsulate-mpls-in-udp action is configured";
        }
        must "not(current() = true()) or string(../../match/transport/destination-port) = '' or string(../../match/transport/destination-port) = '6635'" {
          error-message "when decapsulate-mpls-in-udp is true, destination-port must be 6635";
        }
        type boolean;
        description
          "Remove the IP-UDP encapsulation when it encapsulates an MPLS packet";
      }
      leaf decapsulate-ip-in-ip {
        if-feature "srl_nokia-feat:policy-based-forwarding-decapsulate-ip-in-ip";
        must "../../../type = 'pbr-policy'" {
          error-message "decapsulate-ip-in-ip is only supported when type is pbr-policy";
        }
        must 'string(../../../../global-decap-policy) = ../../../policy-id' {
          error-message "action is only supported in the global-decap-policy";
        }
        must "/srl_nokia-netinst:network-instance[srl_nokia-netinst:name=current()/../../../../../srl_nokia-netinst:name]/srl_nokia-netinst:type = 'srl_nokia-netinst:default'" {
          error-message "decapsulate actions are only supported in a pbr-policy associated with the default network-instance";
        }
        must 'not(current() = true()) or not(../decapsulate-gre = true())' {
          error-message "decapsulate-ip-in-ip cannot be combined with decapsulate-gre";
        }
        must 'not(current() = true()) or not(../decapsulate-gue = true())' {
          error-message "decapsulate-ip-in-ip cannot be combined with decapsulate-gue";
        }
        must 'not(current() = true()) or not(../decapsulate-mpls-in-udp = true())' {
          error-message "decapsulate-ip-in-ip cannot be combined with decapsulate-mpls-in-udp";
        }
        must "not (current() = true()) or
              string(../../match/ipv4/protocol) = '' or string(../../match/ipv4/protocol) = '4' or string(../../match/ipv4/protocol) = '41'" {
          error-message "protocol must be unset, 4 (ipv4) or 41 (ipv6) if decapsulate-ip-in-ip action is configured";
        }
        must "not (current() = true()) or
              string(../../match/ipv6/next-header) = '' or string(../../match/ipv6/next-header) = '4' or string(../../match/ipv6/next-header) = '41'" {
          error-message "next-header must be unset, 4 (ipv4) or 41 (ipv6) if decapsulate-ip-in-ip action is configured";
        }
        must "not(current() = true()) or
              string(../../match/ipv4/source-ip/prefix) = ''" {
          error-message "ipv4 source-ip match is not supported with decapsulate-ip-in-ip action";
        }
        must "not(current() = true()) or
              string(../../match/ipv4/dscp-set) = ''" {
          error-message "ipv4 dscp-set match is not supported with decapsulate-ip-in-ip action";
        }
        must "not(current() = true()) or
              string(../../match/ipv6/source-ip/prefix) = ''" {
          error-message "ipv6 source-ip match is not supported with decapsulate-ip-in-ip action";
        }
        must "not(current() = true()) or
              string(../../match/ipv6/dscp-set) = ''" {
          error-message "ipv6 dscp-set match is not supported with decapsulate-ip-in-ip action";
        }
        must "not(current() = true()) or
              string(../../match/transport/source-port) = ''" {
          error-message "transport source-port match is not supported with decapsulate-ip-in-ip action";
        }
        must "not(current() = true()) or
              string(../../match/transport/destination-port) = ''" {
          error-message "transport destination-port match is not supported with decapsulate-ip-in-ip action";
        }
        type boolean;
        description
          "Remove the outer IP header from IP-in-IP encapsulated packets matching the rule";
      }
      leaf next-hop-group {
        if-feature "srl_nokia-feat:policy-based-forwarding-nhg";
        description
          "When this leaf is set, packets matching the rule will be routed towards the next-hops of the configured group.";
        must "../../../type = 'pbr-policy' or ../../../type = 'match-action'" {
          error-message "action only supported when type is pbr-policy or match-action";
        }
        must 'string(../../../../global-decap-policy) != ../../../policy-id' {
          error-message "action not supported in the global-decap-policy";
        }
        must "(string(../next-hop) = '')" {
          error-message "Next-hop and next-hop-group must not be both set.";
        }
        must "not(../forwarding-action = 'drop' or ../forwarding-action = 'reject')" {
          error-message "unsupported action combination with drop or reject";
        }
        type leafref {
          path "../../../../../srl_nokia-static-routes:static/srl_nokia-static-routes:next-hop-group/srl_nokia-static-routes:name";
        }
      }
      leaf down-override {
        if-feature "srl_nokia-feat:policy-based-forwarding-down-override";
        must "string(../next-hop) != '' or string(../next-hop-group) != ''" {
          error-message "Not applicable to configured action.";
        }
        must "string(../next-hop) = ''" {
          error-message "Not applicable to action next-hop.";
          srl_nokia-ext:if-feature "not srl_nokia-feat:policy-based-forwarding-down-override-action-nh";
        }
        must "string(../next-hop-group) = ''" {
          error-message "Not applicable to action next-hop-group.";
          srl_nokia-ext:if-feature "not srl_nokia-feat:policy-based-forwarding-down-override-action-nhg";
        }
        description
          "Configure the behavior of the system when the configured redirection cannot be performed.";
        type enumeration {
          enum drop {
            description
              "Program the system such that packets matching this rule will be droped in case the configured redirection cannot be performed.";
          }
          enum forward {
            description
              "Program the system such that packets matching this rule will simply be forwarded in case the configured redirection cannot be performed.";
          }
          enum skip {
            description
              "Do not program the rule in case the configured redirection cannot be performed.";
          }
        }
      }
      container count {
        if-feature "srl_nokia-feat:policy-based-forwarding-match-action-type";
        description
          "Enter the count context

           Count matching packets";
        leaf counter-name {
          description
            "Count matching packets using the named counter";
          type leafref {
            path "../../../../counter/name";
          }
          must "../../../../type = 'match-action'" {
            error-message "count is only supported when type is match-action";
          }
        }
      }
      leaf forwarding-action {
        if-feature "srl_nokia-feat:policy-based-forwarding-match-action-type";
        description
          "Apply the specified forwarding action

           The implicit default is accept.";
        type enumeration {
          enum accept {
            description
              "Accept and forward matching packets according to other actions";
          }
          enum drop {
            description
              "Drop matching packets and do not send any ICMP unreachable messages";
          }
          enum reject {
            description
              "Drop matching packets and send ICMP unreachable messages";
          }
        }
        must "../../../type = 'match-action'" {
          error-message "count is only supported when type is match-action";
        }
      }
      leaf ip-ttl {
        if-feature "srl_nokia-feat:policy-based-forwarding-match-action-type";
        description
          "Rewrite the imcoming IPv4 TTL or IPv6 hop-limit to the specified value";
        type uint8;
        must "string(.) = '2'" {
          error-message "only ip-ttl value 2 is supported";
        }
        must "../../../type = 'match-action'" {
          error-message "ip-ttl action is only supported when type is match-action";
        }
        must "not(../forwarding-action = 'drop' or ../forwarding-action = 'reject')" {
          error-message "unsupported action combination with drop or reject";
        }
      }
      leaf policer {
        if-feature "srl_nokia-feat:policy-based-forwarding-match-action-type and srl_nokia-feat:qos and srl_nokia-feat:qos-policers-subtree and srl_nokia-feat:qos-global-policers";
        description
          "Send matching packets to the specified global policer";
        type leafref {
          path "/srl_nokia-qos:qos/srl_nokia-qos-glb-pol:policers/srl_nokia-qos-glb-pol:policer/srl_nokia-qos-glb-pol:name";
        }
        must "../../../type = 'match-action'" {
          error-message "policer action is only supported when type is match-action";
        }
        must "not(../forwarding-action = 'drop' or ../forwarding-action = 'reject')" {
          error-message "unsupported action combination with drop or reject";
        }
      }
      leaf forwarding-class {
        if-feature "srl_nokia-feat:policy-based-forwarding-match-action-type and srl_nokia-feat:qos";
        description
          "Classify matching packets to the specified forwarding-class";
        type leafref {
          path "/srl_nokia-qos:qos/srl_nokia-qos:forwarding-classes/srl_nokia-qos:forwarding-class/srl_nokia-qos:name";
        }
        must "../../../type = 'match-action'" {
          error-message "forwarding-class action is only supported when type is match-action";
        }
        must "not(../forwarding-action = 'drop' or ../forwarding-action = 'reject')" {
          error-message "unsupported action combination with drop or reject";
        }
      }
    }
  }

  grouping pf-match-config {
    container match {
      description
        "Enter the match context

         Container for the conditions that determine whether a packet matches this entry";
      leaf address-family {
        if-feature "srl_nokia-feat:policy-based-forwarding-match-address-family";
        description
          "Address-family selector for packet matching

           When set to 'ipv4', only IPv4 match conditions are permitted under the ipv4 container. When set to 'ipv6', only IPv6 match conditions are permitted under the ipv6 container. When not set, match conditions may be configured under both containers simultaneously.";
        type enumeration {
          enum ipv4 {
            description
              "Match IPv4 packets only";
          }
          enum ipv6 {
            description
              "Match IPv6 packets only";
          }
        }
        must "../../../type = 'match-action'" {
          error-message "address-family is only supported when type is match-action";
        }
      }
      container ipv4 {
        description
          "Enter the ipv4 context

           Container for match conditions associated with IPv4 header fields";
        must "../../../type != 'match-action' or
              not(../address-family = 'ipv6') or
              (not(next-hop-group-id) and not(next-hop-group-network-instance) and
              not(ttl) and not(protocol) and not(dscp-set[1]) and
              not(source-ip/prefix) and not(destination-ip/prefix) and
              not(destination-ip/prefix-list) and not(icmp/type) and not(icmp/code[1]))" {
          error-message "IPv4 match conditions cannot be configured when address-family is 'ipv6'";
        }
        leaf next-hop-group-id {
          if-feature "srl_nokia-feat:policy-based-forwarding-match-action-type";
          description
            "Match an IPv4 packet if it is forwarded by the specified NHG";
          type uint64;
          must "../../../../type = 'match-action'" {
            error-message "NHG match is only supported when the policy type is match-action";
          }
        }
        leaf next-hop-group-network-instance {
          if-feature "srl_nokia-feat:policy-based-forwarding-match-action-type";
          description
            "Specify the network-instance scope of the next-hop-group-id

             If not specified, the implied scope is the same as the one where the policy is defined.";
          type leafref {
            path "/srl_nokia-netinst:network-instance/srl_nokia-netinst:name";
          }
          must "../../../../type = 'match-action'" {
            error-message "NHG match is only supported when the policy type is match-action";
          }
          must '../next-hop-group-id' {
            error-message "network-instance scope is applicable only to matching NHG ID";
          }
        }
        leaf ttl {
          if-feature "srl_nokia-feat:policy-based-forwarding-match-action-type";
          description
            "match an IPv4 packet if its IP TTL (Time to Live) is equal to the specified value";
          type uint8;
          must "string(.) = '1'" {
            error-message "the only TTL value that can be matched is the value 1";
          }
          must "../../../../type = 'match-action'" {
            error-message "ttl match is only supported when the policy type is match-action";
          }
        }
        leaf protocol {
          description
            "An IPv4 packet matches this condition if its IP protocol type field matches the specified value";
          type srl_nokia-pkt-match-types:ip-protocol-type;
        }
        leaf-list dscp-set {
          type srl_nokia-comm:dscp;
          description
            "A list of DSCP values to be matched for incoming packets. An OR match should be performed, such that a packet must match one of the values defined in this list. If the field is left empty then any DSCP value matches.";
          must 'string(../../../../../global-decap-policy) != ../../../../policy-id' {
            error-message "match is not supported in the global-decap-policy";
          }
        }
        container source-ip {
          description
            "Enter the source-ip context

             Packet matching criteria based on source IPv4 address";
          leaf prefix {
            description
              "Match a packet if its source IPv4 address is within the specified IPv4 prefix";
            type srl_nokia-comm:ipv4-prefix;
            must 'string(../../../../../../global-decap-policy) != ../../../../../policy-id' {
              error-message "match is not supported in the global-decap-policy";
            }
            must "../../../../../type != 'match-action'" {
              error-message "source IP match is not supported when the policy type is match-action";
            }
          }
        }
        container destination-ip {
          description
            "Enter the destination-ip context

             Packet matching criteria based on destination IPv4 address";
          leaf prefix {
            description
              "Match a packet if its destination IPv4 address is within the specified IPv4 prefix";
            type srl_nokia-comm:ipv4-prefix;
            must 'not(../../../../action/decap-network-instance)' {
              error-message "On the current platform, ipv4 destination prefix is not supported when policy action has decap-network-instance";
            }
          }
          leaf prefix-list {
            if-feature "srl_nokia-feat:policy-based-forwarding-match-ipv4-prefix-list and srl_nokia-feat:acl-ip-prefix-list";
            description
              "Match a packet if its destination IPv4 address is matched by one of the prefixes in the referenced list";
            type leafref {
              path "/srl_nokia-acl:acl/srl_nokia-acl:match-list/srl_nokia-acl:ipv4-prefix-list/srl_nokia-acl:name";
            }
            must 'not(../prefix)' {
              error-message "prefix-list is mutually exclusive with prefix";
            }
            must '../../../../action/decapsulate-gue = true() or ../../../../action/decapsulate-mpls-in-udp = true() or ../../../../action/decapsulate-gre = true() or ../../../../action/decapsulate-ip-in-ip = true() or ../../../../../type = "match-action"' {
              error-message "match is not supported with the specified action or policy type";
            }
            must 'not(../../../../action/decapsulate-gre)' {
              error-message "match is not supported with the specified action";
              srl_nokia-ext:if-feature "not srl_nokia-feat:policy-based-forwarding-decapsulate-gre-ipv4-prefix-list";
            }
          }
        }
        container icmp {
          description
            "Enter the icmp context

             Match ICMP packets";
          leaf type {
            if-feature "srl_nokia-feat:policy-based-forwarding-match-action-type";
            description
              "Match an IPv4 packet if its ICMP type matches the specified value";
            type uint8;
            must "string(../../protocol) = '1' or string(../../protocol) = 'icmp'" {
              error-message "The protocol should be 1 or icmp to use ICMP type";
            }
            must "../../../../../type = 'match-action'" {
              error-message "ICMP type match is only supported when the policy type is match-action";
            }
          }
          leaf-list code {
            if-feature "srl_nokia-feat:policy-based-forwarding-match-action-type";
            description
              "Match an IPv4 packet if its ICMP code matches the specified value";
            type uint8;
            must "string(../../protocol) = '1' or string(../../protocol) = 'icmp'" {
              error-message "The protocol should be 1 or icmp to use ICMP code";
            }
            must "../../../../../type = 'match-action'" {
              error-message "ICMP code match is only supported when the policy type is match-action";
            }
          }
        }
      }
      container transport {
        if-feature "srl_nokia-feat:policy-based-forwarding-nh-transport";
        description
          "Enter the transport context

           Container for match conditions associated with transport-layer packet fields";
        leaf source-port {
          type srl_nokia-pkt-match-types:port-range;
          description
            "Source port or range";
          must "string(../../ipv4/protocol) = '6' or string(../../ipv6/next-header) = '6' or
                string(../../ipv4/protocol) = '17' or string(../../ipv6/next-header) = '17' or
                string(../../ipv4/protocol) = 'tcp' or string(../../ipv6/next-header) = 'tcp' or
                string(../../ipv4/protocol) = 'udp' or string(../../ipv6/next-header) = 'udp'" {
            error-message "The protocol or next-header must be TCP or UDP to use source-port";
          }
          must "not(contains(., '..')) or not(../../../action/network-instance) or
                ../../../action/next-hop or not(../../../../type = 'vrf-selection-policy')" {
            error-message "On the current platform, range for source-port cannot be used with action network-instance only";
            srl_nokia-ext:if-feature "srl_nokia-feat:ixr-dnx";
          }
          must 'string(../../../../../global-decap-policy) != ../../../../policy-id' {
            error-message "match is not supported in the global-decap-policy";
          }
        }
        leaf destination-port {
          type srl_nokia-pkt-match-types:port-range;
          description
            "Destination port or range";
          must "string(../../ipv4/protocol) = '6' or string(../../ipv6/next-header) = '6' or
                string(../../ipv4/protocol) = '17' or string(../../ipv6/next-header) = '17' or
                string(../../ipv4/protocol) = 'tcp' or string(../../ipv6/next-header) = 'tcp' or
                string(../../ipv4/protocol) = 'udp' or string(../../ipv6/next-header) = 'udp'" {
            error-message "The protocol or next-header must be TCP or UDP to use destination-port";
          }
          must "not(contains(., '..')) or not(../../../action/network-instance) or
                ../../../action/next-hop or not(../../../../type = 'vrf-selection-policy')" {
            error-message "On the current platform, range for destination-port cannot be used with action network-instance only";
            srl_nokia-ext:if-feature "srl_nokia-feat:ixr-dnx";
          }
          must 'not(../../../action/decapsulate-gre) and not(../../../action/decapsulate-ip-in-ip)' {
            error-message "match is not supported with the specified action";
          }
        }
      }
      container ipv6 {
        if-feature "srl_nokia-feat:policy-based-forwarding-match-ipv6-conditions or srl_nokia-feat:policy-based-forwarding-nh-transport";
        description
          "Enter the ipv6 context

           Container for match conditions associated with IPv6 header fields";
        must "../../../type != 'match-action' or
              not(../address-family = 'ipv4') or
              (not(next-hop-group-id) and not(next-hop-group-network-instance) and
              not(hop-limit) and not(next-header) and not(dscp-set[1]) and
              not(source-ip/prefix) and not(destination-ip/prefix) and
              not(destination-ip/prefix-list) and not(icmp6/type) and not(icmp6/code[1]))" {
          error-message "IPv6 match conditions cannot be configured when address-family is 'ipv4'";
        }
        leaf next-hop-group-id {
          if-feature "srl_nokia-feat:policy-based-forwarding-match-action-type";
          description
            "Match an IPv6 packet if it is forwarded by the specified NHG";
          type uint64;
          must "../../../../type = 'match-action'" {
            error-message "NHG match is only supported when the policy type is match-action";
          }
        }
        leaf next-hop-group-network-instance {
          if-feature "srl_nokia-feat:policy-based-forwarding-match-action-type";
          description
            "Specify the network-instance scope of the next-hop-group-id

             If not specified, the implied scope is the same as the one where the policy is defined.";
          type leafref {
            path "/srl_nokia-netinst:network-instance/srl_nokia-netinst:name";
          }
          must "../../../../type = 'match-action'" {
            error-message "NHG match is only supported when the policy type is match-action";
          }
          must '../next-hop-group-id' {
            error-message "network-instance scope is applicable only to matching NHG ID";
          }
        }
        leaf hop-limit {
          if-feature "srl_nokia-feat:policy-based-forwarding-match-action-type";
          description
            "match an IPv6 packet if its IPv6 header Hop Limit is equal to the specified value";
          type uint8;
          must '. = 1' {
            error-message "only supported hop-limit match is the value 1";
          }
          must "../../../../type = 'match-action'" {
            error-message "ttl match is only supported when the policy type is match-action";
          }
        }
        leaf next-header {
          description
            "An IPv6 packet matches this condition if its Next-Header type field matches the specified value";
          type srl_nokia-pkt-match-types:ip-protocol-type;
          must "../../../../type = 'pbr-policy'" {
            error-message "On the current platform, ipv6 match conditions are only supported when policy type is pbr-policy";
            srl_nokia-ext:if-feature "not srl_nokia-feat:policy-based-forwarding-decap-actions and (srl_nokia-feat:ixr-dnx)";
          }
          must 'string(../../../../../global-decap-policy) != ../../../../policy-id or ../../../action/decapsulate-mpls-in-udp or ../../../action/decapsulate-gre or ../../../action/decapsulate-gue = true() ' {
            error-message "match is not supported in the global-decap-policy";
          }
          must 'not(../../../action/decapsulate-gue)' {
            error-message "match is not supported with the specified action";
            srl_nokia-ext:if-feature "not srl_nokia-feat:policy-based-forwarding-decapsulate-gue-ipv6";
          }
        }
        leaf-list dscp-set {
          type srl_nokia-comm:dscp;
          description
            "A list of DSCP values to be matched for incoming packets. An OR match should be performed, such that a packet must match one of the values defined in this list. If the field is left empty then any DSCP value matches.";
          must "../../../../type = 'pbr-policy'" {
            error-message "On the current platform, ipv6 match conditions are only supported when policy type is pbr-policy";
            srl_nokia-ext:if-feature "not srl_nokia-feat:policy-based-forwarding-decap-actions and (srl_nokia-feat:ixr-dnx)";
          }
          must 'string(../../../../../global-decap-policy) != ../../../../policy-id or ../../../action/decapsulate-ip-in-ip = true()' {
            error-message "match is not supported in the global-decap-policy";
          }
        }
        container source-ip {
          description
            "Enter the source-ip context

             Packet matching criteria based on source IPv6 address";
          leaf prefix {
            description
              "Match a packet if its source IPv6 address is within the specified IPv6 prefix";
            type srl_nokia-comm:ipv6-prefix;
            must "../../../../../type = 'pbr-policy'" {
              error-message "On the current platform, ipv6 match conditions are only supported when policy type is pbr-policy";
              srl_nokia-ext:if-feature "not srl_nokia-feat:policy-based-forwarding-decap-actions and (srl_nokia-feat:ixr-dnx)";
            }
            must 'string(../../../../../../global-decap-policy) != ../../../../../policy-id' {
              error-message "match is not supported in the global-decap-policy";
            }
            must "../../../../../type != 'match-action'" {
              error-message "source IP match is not supported when the policy type is match-action";
            }
          }
        }
        container destination-ip {
          if-feature "srl_nokia-feat:policy-based-forwarding-nh-transport";
          description
            "Enter the destination-ip context

             Packet matching criteria based on destination IPv6 address";
          leaf prefix {
            description
              "Match a packet if its destination IPv6 address is within the specified IPv6 prefix";
            type srl_nokia-comm:ipv6-prefix;
            must "../../../../../type = 'pbr-policy' or ../../../../../type = 'match-action'" {
              error-message "On the current platform, ipv6 match condition destination-ip is only supported when policy type is pbr-policy";
              srl_nokia-ext:if-feature "srl_nokia-feat:ixr-dnx";
            }
            must 'not(../../../../action/decap-network-instance)' {
              error-message "match is not supported with the specified action";
            }
            must 'not(../../../../action/decapsulate-gue)' {
              error-message "match is not supported with the specified action";
              srl_nokia-ext:if-feature "not srl_nokia-feat:policy-based-forwarding-decapsulate-gue-ipv6";
            }
          }
          leaf prefix-list {
            if-feature "srl_nokia-feat:policy-based-forwarding-match-ipv6-prefix-list and srl_nokia-feat:acl-ip-prefix-list";
            description
              "Match a packet if its destination IPv6 address is matched by one of the prefixes in the referenced list";
            type leafref {
              path "/srl_nokia-acl:acl/srl_nokia-acl:match-list/srl_nokia-acl:ipv6-prefix-list/srl_nokia-acl:name";
            }
            must 'not(../prefix)' {
              error-message "prefix-list is mutually exclusive with prefix";
            }
            must '../../../../action/decapsulate-gue = true() or ../../../../action/decapsulate-mpls-in-udp = true() or ../../../../action/decapsulate-gre = true() or ../../../../../type = "match-action"' {
              error-message "match is not supported with the specified action or policy type";
            }
            must 'not(../../../../action/decapsulate-gre)' {
              error-message "match is not supported with the specified action";
              srl_nokia-ext:if-feature "not srl_nokia-feat:policy-based-forwarding-decapsulate-gre-ipv6-prefix-list";
            }
            must 'not(../../../../action/decapsulate-gue)' {
              error-message "match is not supported with the specified action";
              srl_nokia-ext:if-feature "not srl_nokia-feat:policy-based-forwarding-decapsulate-gue-ipv6-prefix-list";
            }
            must 'not(../../../../action/decapsulate-mpls-in-udp)' {
              error-message "match is not supported with the specified action";
              srl_nokia-ext:if-feature "not srl_nokia-feat:policy-based-forwarding-decapsulate-mpls-udp-ipv6-prefix-list";
            }
          }
        }
        container icmp6 {
          description
            "Enter the icmp6 context

             Match ICMPv6 packets";
          leaf type {
            if-feature "srl_nokia-feat:policy-based-forwarding-match-action-type";
            description
              "Match an IPv6 packet if its ICMPv6 type matches the specified value";
            type uint8;
            must "string(../../next-header) = '58' or string(../../next-header) = 'icmp6'" {
              error-message "The next-header should be 58 or icmp6 to use icmp6 type";
            }
            must "../../../../../type = 'match-action'" {
              error-message "ICMPv6 type match is only supported when the policy type is match-action";
            }
          }
          leaf-list code {
            if-feature "srl_nokia-feat:policy-based-forwarding-match-action-type";
            description
              "Match an IPv6 packet if its ICMPv6 code matches the specified value";
            type uint8;
            must "string(../../next-header) = '58' or string(../../next-header) = 'icmp6'" {
              error-message "The next-header should be 58 or icmp6 to use icmp6 code";
            }
            must "../../../../../type = 'match-action'" {
              error-message "ICMPv6 code match is only supported when the policy type is match-action";
            }
          }
        }
      }
    }
  }

  grouping pf-policies {
    list policy {
      max-elements 2048;
      key "policy-id";
      description
        "A forwarding policy is defined to have a set of match criteria, allowing particular fields of a packet's header to be matched, and a set of forwarding actions which determines how the local system should forward the packet.";
      leaf policy-id {
        type srl_nokia-comm:name;
        description
          "A unique name identifying the forwarding policy. This name is used when applying the policy to a particular interface.";
      }
      leaf description {
        type srl_nokia-comm:description;
        description
          "Description string for the policy";
      }
      leaf type {
        type enumeration {
          enum pbr-policy {
            value 1;
            description
              "The policy reflects a policy-based routing policy that supports generic PBR actions.";
          }
          enum vrf-selection-policy {
            value 2;
            description
              "The policy is used only to classify incoming packets into corresponding network instances.";
          }
          enum match-action {
            if-feature "srl_nokia-feat:policy-based-forwarding-match-action-type";
            value 3;
            description
              "The policy supports a superset of ACL, QoS and PBR actions";
          }
        }
        default "vrf-selection-policy";
        description
          "The type of the policy";
        must "current() = 'pbr-policy' or string(../../global-decap-policy) = ''" {
          error-message "vrf-selection-policies not supported when global-decap-policy is configured";
        }
      }
      uses user-counters-top {
        if-feature "srl_nokia-feat:policy-based-forwarding-match-action-type";
      }
      list rule {
        description
          "List of policy forwarding rules.";
        key "sequence-id";
        leaf sequence-id {
          type srl_nokia-comm:rule-sequence-id;
          description
            "A number to indicate the relative evaluation order of the different entries; lower numbered entries are evaluated before higher numbered entries";
        }
        leaf description {
          type srl_nokia-comm:description;
          description
            "Description string for the rule";
        }
        container tcam-entries {
          description
            "Enter the tcam-entries context

             Information about the TCAM entries used to implement the policy forwarding rule";
          config false;
          list forwarding-complex {
            description
              "List of forwarding complexes in the system";
            key "complex-identifier";
            leaf complex-identifier {
              description
                "A forwarding complex in the format (slot-number,complex-number).";
              type string;
            }
            leaf tcam-entries {
              config false;
              type uint16;
              description
                "The number of TCAM entries required to implement this rule.";
            }
          }
        }
        uses pf-action-config;
        uses pf-match-config;
        must "not(../type = 'vrf-selection-policy') or (../type = 'vrf-selection-policy' and
              (string(action/network-instance) != '' or
              (string(action/decap-network-instance) != '' and
              string(action/decap-fallback-network-instance) != '' and
              string(action/post-decap-network-instance) != '') ))" {
          error-message "When policy type is vrf-selection-policy, network-instance must be set.";
        }
        must "(string(action/decap-network-instance) = \"\" or
                            (/srl_nokia-netinst:network-instance[srl_nokia-netinst:name=current()/../../../srl_nokia-netinst:name]/srl_nokia-netinst:type = \"srl_nokia-netinst:default\"))" {
          error-message "Policy with decap-network-instance and related actions can only be used in a network-isntance with type 'default'";
        }
      }
    }
  }

  grouping pf-interfaces {
    list interface {
      key "subinterface";
      description
        "List of subinterfaces that use the policy forwarding policy.";
      leaf subinterface {
        type srl_nokia-netinst:network-instance-subintf-name;
        description
          "Name of the subinterface.";
      }
      container interface-ref {
        if-feature "srl_nokia-feat:interface-references";
        description
          "Enter the interface-ref context

           Reference to a subinterface";
        leaf interface {
          type leafref {
            path "/srl_nokia-if:interface/srl_nokia-if:name";
          }
          description
            "Reference to a base interface, for example a port or LAG";
          must '../subinterface >= 0' {
            error-message "subinterface must be configured when interface is set";
          }
        }
        leaf subinterface {
          type leafref {
            path "/srl_nokia-if:interface[srl_nokia-if:name=current()/../interface]/srl_nokia-if:subinterface/srl_nokia-if:index";
          }
          description
            "Reference to a subinterface
             This requires the base interface to be specified using the interface leaf in this container.";
          must '../interface' {
            error-message "interface must be configured when subinterface is set";
          }
        }
      }
      leaf apply-forwarding-policy {
        type leafref {
          path "../../policy/policy-id";
        }
        description
          "The policy to be applied on the interface. Packets ingress on the referenced interface should be compared to the match criteria within the specified policy, and in the case that these criteria are met, the forwarding actions specified applied.";
        must ". = '' or not(../../global-decap-policy = current())" {
          error-message "policy referenced as global-decap-policy cannot be applied on an interface";
        }
      }
    }
  }

  grouping policy-forwarding-top {
    container policy-forwarding {
      if-feature "srl_nokia-feat:policy-based-forwarding-dscp-ip-protocol or srl_nokia-feat:policy-based-forwarding-nh-transport";
      presence "Enable support for policy-based forwarding in the network instance.";
      description
        "Configuration and operational state relating to policy-forwarding within a network instance.";
      leaf global-decap-policy {
        if-feature
          "srl_nokia-feat:policy-based-forwarding-decapsulate-gue or
           srl_nokia-feat:policy-based-forwarding-decapsulate-gre or
           srl_nokia-feat:policy-based-forwarding-decapsulate-mpls-udp or
           srl_nokia-feat:policy-based-forwarding-decapsulate-ip-in-ip";
        description
          "Reference to a pbr-policy with decapsulation rules that are automatically installed on all interfaces";
        type leafref {
          path "../policy/policy-id";
        }
        must '(../../srl_nokia-netinst:type = "srl_nokia-netinst:default")' {
          error-message "global-decap-policy must be associated with network-instance of type 'default'";
        }
      }
      uses pf-policies;
      uses pf-interfaces;
      must 'not(../type = "mac-vrf")' {
        error-message "Policy-forwarding cannot be configured within network-instance of type 'mac-vrf'";
      }
    }
  }

  grouping user-counters-top {
    list counter {
      description
        "Named counters in this policy for counting packets matching certain policy-forwarding match-action rules";
      key "name";
      leaf name {
        description
          "Name of the user-defined counter";
        type srl_nokia-comm:name;
      }
      leaf total-packets {
        config false;
        description
          "Total number of packets sent to this counter for counting";
        type srl_nokia-comm:zero-based-counter64;
      }
      leaf total-octets {
        config false;
        description
          "Total number of octets in packets sent to this counter for counting";
        type srl_nokia-comm:zero-based-counter64;
      }
    }
  }

  augment "/srl_nokia-netinst:network-instance" {
    uses policy-forwarding-top;
  }
}
