module srl_nokia-mpls {
  yang-version 1.1;
  namespace "urn:nokia.com:srlinux:mpls:mpls";
  prefix srl_nokia-mpls;

  import srl_nokia-common {
    prefix srl_nokia-comm;
  }
  import srl_nokia-network-instance {
    prefix srl_nokia-netinst;
  }
  import srl_nokia-next-hop-groups {
    prefix srl_nokia-nhg;
  }
  import srl_nokia-ip-route-tables {
    prefix srl_nokia-ip-table;
  }
  import srl_nokia-features {
    prefix srl-feat;
  }
  import srl_nokia-system {
    prefix srl_nokia-system;
  }
  import srl_nokia-mpls-label-management {
    prefix srl_nokia-mplslbl;
  }

  organization
    "Nokia";
  contact
    "Nokia SR Linux Support
     Web: <http://www.nokia.com>";
  description
    "This yang file adds support for basic MPLS configuration and state at the network instance level.";

  revision 2026-07-31 {
    description
      "SRLinux 26.7.1";
  }
  revision 2021-11-30 {
    description
      "SRLinux 21.11.1";
  }
  revision 2021-06-30 {
    description
      "SRLinux 21.6.1";
  }
  revision 2021-03-31 {
    description
      "SRLinux 21.3.1";
  }
  revision 2020-06-30 {
    description
      "SRLinux 20.6.1";
  }
  revision 2019-11-30 {
    description
      "SRLinux 19.11.1";
  }

  typedef label-block-status {
    type enumeration {
      enum available;
      enum unavailable;
    }
    description
      "Status of a label block.";
  }

  grouping mpls-top {
    container mpls {
      if-feature "srl-feat:mpls";
      must "current()/../srl_nokia-netinst:type = 'srl_nokia-netinst:default'" {
        error-message "MPLS configuration only supported with network instance type default";
      }
      presence "Configure MPLS";
      leaf icmp-tunneling {
        type boolean;
        description
          "When enabled, ICMP messages generated by the router acting in the role of a transit LSR are injected in the forward direction of the LSP, to be turned around and sent back to the sender of the IP payload by the egress LER.

           If a transit LSR receives an MPLS packet that cannot be forwarded (e.g. label TTL has expired, or the egress subinterface MPLS MTU was exceeded) and the MPLS packet has an IP payload, the router will generate an appropriate ICMP error message. When icmp-tunneling is 'false' the ICMP error message is dropped if there is no IP route back to the source in the network-instance that received the MPLS packet.";
      }
      leaf static-label-block {
        if-feature "srl-feat:label-management";
        type leafref {
          path "/srl_nokia-system:system/srl_nokia-mplslbl:mpls/srl_nokia-mplslbl:label-ranges/srl_nokia-mplslbl:static/srl_nokia-mplslbl:name";
        }
        must 'not(/srl_nokia-system:system/srl_nokia-mplslbl:mpls/srl_nokia-mplslbl:label-ranges/srl_nokia-mplslbl:static[srl_nokia-mplslbl:name=current()]/srl_nokia-mplslbl:shared)' {
          error-message "Static label block for MPLS should be exclusive (not shared)";
        }
      }
      leaf static-label-block-status {
        config false;
        if-feature "srl-feat:label-management";
        type label-block-status;
        description
          "Status of the label block.

           The label block may show as unavailable if there is pending cleanup.";
      }
      list ndk-label-block {
        key "application-name";
        if-feature "srl-feat:mpls-ndk";
        leaf application-name {
          type string;
        }
        leaf static-label-block {
          if-feature "srl-feat:label-management";
          type leafref {
            path "/srl_nokia-system:system/srl_nokia-mplslbl:mpls/srl_nokia-mplslbl:label-ranges/srl_nokia-mplslbl:static/srl_nokia-mplslbl:name";
          }
          must 'not(/srl_nokia-system:system/srl_nokia-mplslbl:mpls/srl_nokia-mplslbl:label-ranges/srl_nokia-mplslbl:static[srl_nokia-mplslbl:name=current()]/srl_nokia-mplslbl:shared)' {
            error-message "Static label block for NDKs should be exclusive (not shared)";
          }
          must '. != ../../static-label-block' {
            error-message "This NDK's static label block is already in use as config MPLS static-label-block";
          }
        }
        leaf static-label-block-status {
          config false;
          if-feature "srl-feat:label-management";
          type label-block-status;
          description
            "Status of the label block.

             The label block may show as unavailable if there is pending cleanup.";
        }
      }
      list static-entry {
        key "top-label preference";
        leaf top-label {
          type srl_nokia-comm:mpls-label-non-reserved;
          description
            "A received MPLS packet, received on any subinterface, matches this static entry if its top label stack entry contains the label value specified by this leaf.";
          must '(current() >= /srl_nokia-system:system/srl_nokia-mplslbl:mpls/srl_nokia-mplslbl:label-ranges/srl_nokia-mplslbl:static[srl_nokia-mplslbl:name=current()/../../static-label-block]/srl_nokia-mplslbl:start-label)'
             + ' and (current() <= /srl_nokia-system:system/srl_nokia-mplslbl:mpls/srl_nokia-mplslbl:label-ranges/srl_nokia-mplslbl:static[srl_nokia-mplslbl:name=current()/../../static-label-block]/srl_nokia-mplslbl:end-label)' {
            error-message "static-label-block is not configured or top-label is out of static-label-block's range";
          }
        }
        leaf preference {
          type uint8 {
            range "0..255";
          }
          description
            "For a given top label value the entry with the lowest preference is selected as the active entry";
        }
        leaf admin-state {
          type srl_nokia-comm:admin-state;
          default "enable";
          description
            "Used to disable the entire static route and all its next-hops.";
        }
        leaf operation {
          type enumeration {
            enum pop {
              value 1;
            }
            enum swap {
              value 2;
            }
          }
          default "swap";
          description
            "The operation to be performed with the top label.";
          must 'not(current() != "pop" and not(../next-hop-group))' {
            error-message "Swap operation needs a next-hop-group";
          }
          must 'not(current() = "pop" and ../next-hop-group)' {
            error-message "No next-hop-group needed for pop operation";
          }
        }
        leaf collect-stats {
          type boolean;
          default "false";
          description
            "When set to true, stats resources are used to count the number of incoming packets matching the top label value of this static MPLS route";
        }
        leaf installed {
          config false;
          type boolean;
          description
            "Indicates whether the MPLS route entry was programmed in the data path.";
        }
        leaf next-hop-group {
          type leafref {
            path "../../../srl_nokia-nhg:next-hop-groups/srl_nokia-nhg:group/srl_nokia-nhg:name";
          }
        }
        leaf resolved-next-hop-group-id {
          config false;
          type leafref {
            path "../../../srl_nokia-netinst:route-table/srl_nokia-ip-table:next-hop-group/srl_nokia-ip-table:index";
          }
        }
      }
      container lsps {
        if-feature "srl-feat:mpls-static-lsp or srl-feat:rsvp";
        description
          "Enter the lsps context

           Configuration and state related to MPLS label switched paths";
        list static-lsp {
          if-feature "srl-feat:mpls-static-lsp";
          description
            "List of stically configured label switched paths";
          key "name";
          leaf name {
            description
              "Name of the label-switched path";
            type srl_nokia-comm:name;
          }
          leaf oper-state {
            config false;
            description
              "Operational state of the static LSP";
            type enumeration {
              enum up {
                description
                  "LSP is operational and capable of carrying traffic";
              }
              enum down {
                description
                  "LSP is down and not capable of carrying traffic";
              }
            }
          }
          leaf oper-down-reason {
            config false;
            description
              "The reason why the static MPLS LSP has a down oper-state";
            type enumeration {
              enum label-unavailable {
                description
                  "The incoming label cannot be allocated because it is already in use";
              }
              enum next-hops-unresolved {
                description
                  "There is no valid next-hop to use for forwarding";
              }
            }
          }
          leaf payload-type {
            description
              "Specifies the payload type of traffic carried by this static MPLS LSP";
            type enumeration {
              enum unicast {
                description
                  "The LSP carries unicast traffic";
              }
              enum multicast {
                description
                  "The LSP carries multicast traffic";
              }
            }
            default "unicast";
          }
          container egress {
            description
              "Enter the egress context

               Static LSPs for which the router is an egress node and therefore the incoming label should be popped";
            leaf incoming-label {
              description
                "Incoming label value to associate with the static LSP

                 When the top-label stack entry matches this value the router knows the packet belongs to this LSP";
              type srl_nokia-comm:mpls-label-non-reserved;
              must "not(../../../../static-label-block and
                                            ((current() < /srl_nokia-system:system/srl_nokia-mplslbl:mpls/srl_nokia-mplslbl:label-ranges/srl_nokia-mplslbl:static[srl_nokia-mplslbl:name=current()/../../../../static-label-block]/srl_nokia-mplslbl:start-label) or
                                             (current() > /srl_nokia-system:system/srl_nokia-mplslbl:mpls/srl_nokia-mplslbl:label-ranges/srl_nokia-mplslbl:static[srl_nokia-mplslbl:name=current()/../../../../static-label-block]/srl_nokia-mplslbl:end-label)))" {
                error-message "label is out of static-label-block's range";
              }
            }
            list next-hop {
              max-elements 1;
              description
                "List of next-hops to consider for forwarding after the incoming label is popped

                 More than 1 next-hop implies ECMP behavior.";
              key "index";
              leaf index {
                type uint32;
                description
                  "A user-specified identifier that uniquely references a next-hop entry in the next-hop list";
              }
              leaf ip-address {
                type srl_nokia-comm:ip-address;
                description
                  "Next hop IP address for the LSP";
              }
            }
            leaf network-instance {
              description
                "The network-instance that applies to all the configured next-hops

                 Optional. If not specified next-hops are assumed to exist in the same network-instance where the static LSP is configured.";
              type leafref {
                path "/srl_nokia-netinst:network-instance/srl_nokia-netinst:name";
              }
              must "/srl_nokia-netinst:network-instance[srl_nokia-netinst:name=current()]/srl_nokia-netinst:type = 'srl_nokia-netinst:ip-vrf'" {
                error-message "network-instance must be an ip-vrf";
              }
            }
            leaf pipe-mode {
              description
                "When true, the MPLS LSP operates in pipe mode

                 In pipe mode, the MPLS traffic-class and MPLS TTL are not copied into the DSCP and IP-TTL fields of the IP packet exposed by the pop operation.

                 When false, the MPLS LSP operates in uniform mode. In uniform mode, the MPLS traffic-class and MPLS TTL are copied into the DSCP and IP-TTL fields of the IP packet exposed by the pop operation.";
              type boolean;
              default "true";
              must '. = true()' {
                error-message "Only pipe mode is supported";
              }
            }
          }
        }
      }
    }
  }

  augment "/srl_nokia-netinst:network-instance" {
    uses mpls-top;
  }
}
