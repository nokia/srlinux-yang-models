module srl_nokia-isis {
  yang-version 1.1;
  namespace "urn:nokia.com:srlinux:isis:isis";
  prefix srl_nokia-isis;

  import ietf-yang-types {
    prefix yang;
  }
  import srl_nokia-common {
    prefix srl_nokia-comm;
  }
  import srl_nokia-network-instance {
    prefix srl_nokia-netinst;
  }
  import srl_nokia-interfaces {
    prefix srl_nokia-if;
  }
  import srl_nokia-extensions {
    prefix srl_nokia-ext;
  }
  import srl_nokia-routing-policy {
    prefix srl-rpol;
  }
  import srl_nokia-system {
    prefix srl-system;
  }
  import srl_nokia-keychains {
    prefix srl-keychain;
  }
  import srl_nokia-traffic-engineering {
    prefix srl_nokia-te;
  }
  import srl_nokia-features {
    prefix srl-feat;
  }
  import srl_nokia-mpls-label-management {
    prefix srl_nokia-mplslbl;
  }
  import srl_nokia-segment-routing {
    prefix srl_nokia-segrt;
  }
  import srl_nokia-ldp {
    prefix srl_nokia-ldp;
  }
  import srl_nokia-isis-lsdb {
    prefix srl_nokia-isis-lsdb;
  }
  import srl_nokia-isis-types {
    prefix srl_nokia-isis-types;
  }

  organization
    "Nokia";
  contact
    "Nokia SR Linux Support
     Web: <http://www.nokia.com>";
  description
    "This yang file models configuration and state of the IS-IS protocol";

  revision 2026-07-31 {
    description
      "SRLinux 26.7.1";
  }
  revision 2026-03-31 {
    description
      "SRLinux 26.3.1";
  }
  revision 2025-10-31 {
    description
      "SRLinux 25.10.1";
  }
  revision 2025-07-31 {
    description
      "SRLinux 25.7.1";
  }
  revision 2025-03-31 {
    description
      "SRLinux 25.3.1";
  }
  revision 2024-10-31 {
    description
      "SRLinux 24.10.1";
  }
  revision 2024-07-31 {
    description
      "SRLinux 24.7.1";
  }
  revision 2024-03-31 {
    description
      "SRLinux 24.3.1";
  }
  revision 2023-10-31 {
    description
      "SRLinux 23.10.1";
  }
  revision 2023-07-31 {
    description
      "SRLinux 23.7.1";
  }
  revision 2023-03-31 {
    description
      "SRLinux 23.3.1";
  }
  revision 2022-11-30 {
    description
      "SRLinux 22.11.1";
  }
  revision 2022-06-30 {
    description
      "SRLinux 22.6.1";
  }
  revision 2022-03-31 {
    description
      "SRLinux 22.3.1";
  }
  revision 2021-11-30 {
    description
      "SRLinux 21.11.1";
  }
  revision 2021-06-30 {
    description
      "SRLinux 21.6.1";
  }
  revision 2021-03-31 {
    description
      "SRLinux 21.3.1";
  }
  revision 2020-06-30 {
    description
      "SRLinux 20.6.1";
  }

  grouping isis-inst-key {
    leaf name {
      description
        "The name of the IS-IS instance";
      type srl_nokia-comm:name;
    }
  }

  grouping isis-level-key {
    leaf level-number {
      description
        "Specifies the IS-IS protocol level to which these attributes are applied.";
      type srl_nokia-isis-types:isis-level-number;
    }
  }

  grouping isis-interface-key {
    leaf interface-name {
      description
        "Name of the IS-IS interface";
      type srl_nokia-netinst:network-instance-subintf-name;
    }
  }

  grouping isis-summary-prefix-key {
    leaf ip-prefix {
      description
        "Summary ip prefix.";
      type srl_nokia-comm:ip-prefix;
    }
  }

  grouping isis-adjacency-key {
    leaf neighbor-system-id {
      description
        "The neighbor router's system ID.";
      type srl_nokia-comm:isis-system-id;
    }
    leaf adjacency-level {
      description
        "The level of the adjacency that is formed.";
      type srl_nokia-isis-types:isis-adj-level;
    }
  }

  grouping isis-authentication-pdu-options {
    leaf generate {
      type boolean;
      description
        "When set to true, IS-IS is instructed to add an authentication TLV to every transmitted PDU of the specified type";
      must '(. = false()) or boolean(../../keychain) or boolean(../../key/crypto-algorithm)' {
        error-message "keychain or key must be configured to send authentication TLV with this PDU";
      }
    }
    leaf check-received {
      type srl_nokia-isis-types:isis-auth-check-type;
      description
        "Specifies the type of authentication checks done for received PDUs of the specified type.";
      must "(. = 'disable')  or boolean(../../keychain) or boolean(../../key/crypto-algorithm)" {
        error-message "keychain or key must be configured to check authentication for this PDU";
      }
    }
  }

  grouping isis-instance-level-authentication {
    container authentication {
      description
        "Enter the authentication context

         Container for specifying authentication options that apply to the entire IS-IS instance or to an entire level.

         The settings in this container only apply to PDUs without an authentication behavior specified at a more granular level.";
      container csnp-authentication {
        description
          "Enter the csnp-authentication context

           Container with options to control the authentication of CSNP PDUs";
        uses isis-authentication-pdu-options;
      }
      container psnp-authentication {
        description
          "Enter the psnp-authentication context

           Container with options to control the authentication of PSNP PDUs";
        uses isis-authentication-pdu-options;
      }
      container hello-authentication {
        description
          "Enter the hello-authentication context

           Container with options to control the authentication of Hello PDUs";
        uses isis-authentication-pdu-options;
      }
      container lsp-authentication {
        description
          "Enter the lsp-authentication context

           Container with options to control the authentication of Link State PDUs";
        uses isis-authentication-pdu-options;
      }
      choice auth-type {
        case keychain {
          leaf keychain {
            description
              "Specifies a keychain to use for the authentication of PDUs when the behavior is controlled at this level of the configuration hierarchy.";
            type leafref {
              path "/srl-system:system/srl-keychain:authentication/srl-keychain:keychain/srl-keychain:name";
            }
            must '/srl-system:system/srl-keychain:authentication/srl-keychain:keychain[srl-keychain:name = current()]'
               + '/srl-keychain:type = "isis"' {
              error-message "Only keychain of type isis can be assigned";
            }
          }
        }
        case direct-key {
          container key {
            description
              "Enter the key context

               Container to specify the secret key and crypto algorithm to use for the authentication of PDUs when the behavior is controlled at this level of the configuration hierarchy";
            leaf crypto-algorithm {
              description
                "The cryptographic algorithm used with the keying material to secure the messages.";
              type srl_nokia-isis-types:isis-auth-type;
              mandatory true;
            }
            leaf auth-password {
              description
                "The secret key to use for authentication of PDUs";
              type srl_nokia-comm:routing-password;
              mandatory true;
            }
          }
        }
      }
    }
  }

  grouping isis-instance-lfa {
    container loopfree-alternate {
      description
        "Enter the loopfree-alternate context

         Loopfree-alternate related context for the instance.";
      leaf admin-state {
        description
          "When set, loopfree-alternate protection is enabled for
           the ISIS instance. Enables ability to seek for LFA,
           doesn't guarantee LFA protection.";
        type srl_nokia-comm:admin-state;
        default "disable";
        must "(. = 'disable') or (../../../../../srl_nokia-netinst:type = 'srl_nokia-netinst:default')" {
          error-message "LFA is supported only in the default network instance";
        }
      }
      leaf augment-route-table {
        if-feature "srl-feat:ldp-rlfa";
        description
          "Extend remote LFA next-hop resolution path entry to RTM
           such that tunnel can be used in SPF decisions";
        type boolean;
        default "false";
        must "(. = false()) or (../../../../../srl_nokia-netinst:type = 'srl_nokia-netinst:default')" {
          error-message "LFA config is supported only in the default network instance";
        }
      }
      container exclude {
        description
          "Enter the exclude context

           Set the exclude context for LFA SPF computation";
        leaf-list prefix-policy {
          description
            "Policy to exclude prefixes from LFA SPF calculation";
          type leafref {
            path "/srl-rpol:routing-policy/srl-rpol:policy/srl-rpol:name";
          }
          max-elements 5;
          ordered-by user;
        }
      }
      container multi-homed-prefix {
        description
          "Enter the multi-homed-prefix context

           Multi-homed-prefix context";
        leaf admin-state {
          description
            "When set, multi-homed prefix context is enabled for
             the ISIS instance";
          type srl_nokia-comm:admin-state;
          default "disable";
          must "(. = 'disable') or (../../../../../../srl_nokia-netinst:type = 'srl_nokia-netinst:default')" {
            error-message "LFA related configuration is only supported in the default network instance";
          }
        }
        leaf preference {
          description
            "Backup preference of a multi-homed prefix";
          type enumeration {
            enum none {
              value 0;
            }
            enum all {
              value 1;
            }
          }
          default "none";
          must "(. = 'none') or (../../../../../../srl_nokia-netinst:type = 'srl_nokia-netinst:default')" {
            error-message "LFA preference configuration is only supported in the default network instance";
          }
        }
      }
      container remote-lfa {
        description
          "Enter the remote-lfa context

           Remote LFA context";
        leaf admin-state {
          description
            "When set, remote lfa protection is enabled for the
             ISIS instance. Enables ability to seek for an eligible
             remote-LFA node (P,Q intersection), doesn't guarantee
             existance of remote-LFA protection.";
          type srl_nokia-comm:admin-state;
          default "disable";
          must "(. = 'disable') or (../../../../../../srl_nokia-netinst:type = 'srl_nokia-netinst:default')" {
            error-message "RLFA is supported only in the default network instance";
          }
          must "not((. = 'enable') and (../../admin-state = 'disable'))" {
            error-message "RLFA is supported only if loopfree-alternate is admin enabled";
          }
        }
        leaf max-pq-cost {
          description
            "Maximum cost of destination node during reverse SPF calculation";
          type uint32;
          default "4261412864";
        }
        container node-protect {
          description
            "Enter the node-protect context

             Node protect context";
          leaf admin-state {
            description
              "When set, the IS-IS instance enables node protection
               using remote lfa. Remote LFA seeks for a viable P,Q
               intersection that can protect against node failures.";
            type srl_nokia-comm:admin-state;
            default "disable";
            must "(. = 'disable') or (../../../../../../../srl_nokia-netinst:type = 'srl_nokia-netinst:default')" {
              error-message "RLFA Node Protection is supported only in the default network instance";
            }
          }
          leaf max-pq-nodes {
            description
              "Maximum number of PQ nodes found in the LFA SPFs.
               Value 0 disables node protect";
            type uint32 {
              range "0..32";
            }
            default "16";
            must "not((. = 0) and (../admin-state = 'enable'))" {
              error-message "Max PQ Nodes cannot be zero if node protection is enabled";
            }
          }
        }
      }
      container ti-lfa {
        description
          "Enter the ti-lfa context

           ti-lfa context";
        leaf admin-state {
          description
            "When set, ti-lfa protection is enabled for the ISIS instance.
             ti-LFA seeks for a viable P,Q intersection based on
             constraints including max ti-lfa labels.";
          type srl_nokia-comm:admin-state;
          default "disable";
          must "(. = 'disable') or (../../../../../../srl_nokia-netinst:type = 'srl_nokia-netinst:default')" {
            error-message "TI-LFA is supported only in the default network instance";
          }
          must "not((. = 'enable') and (../../admin-state = 'disable'))" {
            error-message "TI-LFA is supported only if loopfree-alternate is admin enabled";
          }
        }
        leaf max-sr-policy-lfa-labels {
          description
            "Maximum number of labels the TI-LFA backup path can use";
          type uint32 {
            range "0..3";
          }
          default "2";
          must "(. = 2) or (../admin-state = 'enable')" {
            error-message "TI-LFA max-labels must be set to default value if it is disabled";
          }
        }
        container node-protect {
          description
            "Enter the node-protect context

             Node-protect context";
          leaf admin-state {
            description
              "When set to enabled, the IS-IS instance
               enables ti-lfa node protection.";
            type srl_nokia-comm:admin-state;
            default "disable";
            must "(. = 'disable') or (../../../../../../../srl_nokia-netinst:type = 'srl_nokia-netinst:default')" {
              error-message "TI-LFA protection config is supported only in the default network instance";
            }
          }
        }
      }
    }
  }

  grouping isis-interface-authentication {
    container authentication {
      description
        "Enter the authentication context

         Container for specifying authentication options that apply to the IS-IS instance.";
      container hello-authentication {
        description
          "Enter the hello-authentication context

           Container with options to control the authentication of Hello PDUs";
        uses isis-authentication-pdu-options;
      }
      choice auth-type {
        case keychain {
          leaf keychain {
            description
              "Specifies a keychain to use for the authentication of Hello PDUs on this interface.";
            type leafref {
              path "/srl-system:system/srl-keychain:authentication/srl-keychain:keychain/srl-keychain:name";
            }
            must '/srl-system:system/srl-keychain:authentication/srl-keychain:keychain[srl-keychain:name = current()]'
               + '/srl-keychain:type = "isis"' {
              error-message "Only keychain of type isis can be assigned";
            }
          }
        }
        case direct-key {
          container key {
            description
              "Enter the key context

               Container to specify the secret key and crypto algorithm to use for the authentication of Hello PDUs on this interface";
            leaf crypto-algorithm {
              description
                "The cryptographic algorithm used with the keying material to secure the messages.";
              type srl_nokia-isis-types:isis-auth-type;
              mandatory true;
            }
            leaf auth-password {
              description
                "The secret key to use for authentication of Hello PDUs";
              type srl_nokia-comm:routing-password;
              mandatory true;
            }
          }
        }
      }
    }
  }

  grouping isis-interface-level-config {
    leaf disable {
      description
        "Disable the Level for the interface.";
      type boolean;
      default "false";
    }
    leaf ipv6-unicast-metric {
      description
        "Specifies the interface metric associated with the IPv6-unicast multi-topology.
         The default is based on reference-bandwidth, or else if this is not configured the default is 10.";
      type srl_nokia-isis-types:isis-wide-metric;
    }
    leaf metric {
      description
        "Specifies the interface metric associated with the native routing topology.
         The default is based on reference-bandwidth, or else if this is not configured the default is 10.";
      type srl_nokia-isis-types:isis-wide-metric;
    }
    leaf priority {
      description
        "ISIS neighbor priority for becoming Designated IS (LAN hello PDU only).";
      type uint8 {
        range "0..127";
      }
      default "64";
    }
    leaf passive {
      if-feature "srl-feat:isis-level-passive";
      description
        "When set to true the interface is configured as a passive interface for this level and does not send IIH PDUs or try to form an adjacency with other routers.";
      type boolean;
    }
    container timers {
      description
        "Enter the timers context

         Container for IS-IS hello timers applicable at interface level";
      leaf hello-interval {
        description
          "ISIS hello-interval value.
           The default is 3 seconds on Designated IS interfaces and 9 seconds for non-DIS and p2p interfaces";
        type uint32 {
          range "1..20000";
        }
        units "seconds";
        default "9";
      }
      leaf hello-multiplier {
        description
          "ISIS hello-multiplier value.

           The neighbor hold time is (hello multiplier x hello interval) on non-designated intermediate system broadcast interfaces and point-to-point interfaces and (hello multiplier x hello interval / 3) on designated intermediate system broadcast interfaces.

           The hold time is the time in which the neighbor expects to receive the next Hello PDU. If the neighbor receives a Hello within this time, the hold time is reset. If the neighbor does not receive a Hello within the hold time, it brings the adjacency down.";
        type uint8 {
          range "2..100";
        }
        default "3";
      }
    }
    leaf ipv4-unicast {
      if-feature "srl-feat:isis-interface-afi-safi-enable";
      description
        "Placeholder leaf for OC mapping of IPv4 enable flag.

         Currently forced to true; false is not supported.";
      type boolean;
      default "true";
      must '. = true()' {
        error-message "The 'ipv4' leaf must be true.";
      }
    }
    leaf ipv6-unicast {
      if-feature "srl-feat:isis-interface-afi-safi-enable";
      description
        "Placeholder leaf for OC mapping of IPv6 enable flag.

         Currently forced to true; false is not supported.";
      type boolean;
      default "true";
      must '. = true()' {
        error-message "The 'ipv6' leaf must be true.";
      }
    }
    uses isis-interface-authentication;
  }

  grouping isis-interface-level-stats {
    container statistics {
      config false;
      description
        "Enter the statistics context

         Interface per level statistics";
      list pdu {
        config false;
        description
          "List of PDUs processed by the IS-IS instance since the IS-IS manager restarted";
        key "pdu-name";
        leaf pdu-name {
          type srl_nokia-isis-types:isis-pdu-type;
          description
            "The PDU type that was processed";
        }
        uses isis-pdu-statistics;
      }
    }
  }

  grouping isis-interface-config {
    container interface-ref {
      if-feature "srl-feat:interface-references";
      description
        "Enter the interface-ref context

         Reference to a subinterface";
      leaf interface {
        type leafref {
          path "/srl_nokia-if:interface/srl_nokia-if:name";
        }
        description
          "Reference to a base interface, for example a port or LAG";
        must '../subinterface >= 0' {
          error-message "subinterface must be configured when interface is set";
        }
      }
      leaf subinterface {
        type leafref {
          path "/srl_nokia-if:interface[srl_nokia-if:name=current()/../interface]/srl_nokia-if:subinterface/srl_nokia-if:index";
        }
        description
          "Reference to a subinterface

           This requires the base interface to be specified using the interface leaf in this container.";
        must '../interface' {
          error-message "interface must be configured when subinterface is set";
        }
      }
    }
    leaf admin-state {
      description
        "Used to administratively enable or disable the IS-IS protocol on a
         routed subinterface";
      type srl_nokia-comm:admin-state;
      default "enable";
    }
    leaf circuit-type {
      description
        "Specifies the circuit type as either point-to-point or broadcast";
      type srl_nokia-isis-types:isis-circuit-type;
    }
    container delay {
      if-feature "srl-feat:isis-dyn-delay";
      description
        "Enter the delay context";
      leaf delay-selection {
        description
          "Delay source advertised by IGP for the interface";
        type enumeration {
          enum static {
            value 1;
          }
          enum dynamic {
            value 2;
          }
          enum static-preferred {
            value 3;
          }
          enum dynamic-preferred {
            value 4;
          }
        }
        default "static-preferred";
      }
      leaf unidirectional-minimum-link-delay {
        config false;
        type union {
          type uint32 {
            range "1..4294967295";
          }
          type enumeration {
            enum none {
              value 0;
            }
          }
        }
        units "microseconds";
        description
          "Operational Unidirectional link delay advertised by ISIS";
      }
      container normalization {
        if-feature "srl-feat:isis-delay-normalization";
        description
          "Enter the normalization context";
        leaf admin-state {
          description
            "Enable or disable delay-normalization";
          type srl_nokia-comm:admin-state;
          default "disable";
          must '(. = "disable") or (../../../../../../../srl_nokia-netinst:type = "srl_nokia-netinst:default")' {
            error-message "Delay normalization is only supported in the default network instance";
          }
        }
        leaf minimum-delay {
          description
            "Represents the minimal delay on an interface in usec";
          type uint32 {
            range "1..10000000";
          }
          default "1";
          units "microseconds";
          must '(. = 1) or (../../../../../../../srl_nokia-netinst:type = "srl_nokia-netinst:default")' {
            error-message "Delay normalization is only supported in the default network instance";
          }
        }
        leaf delay-tolerance-interval {
          description
            "The interval between two delay values on the interface";
          type uint32 {
            range "1..10000000";
          }
          default "10";
          units "microseconds";
          must '(. = 10) or (../../../../../../../srl_nokia-netinst:type = "srl_nokia-netinst:default")' {
            error-message "Delay normalization is only supported in the default network instance";
          }
        }
      }
    }
    leaf hello-padding {
      description
        "Specifies the use of IS-IS Hello PDU padding on the interface";
      type srl_nokia-isis-types:isis-hello-padding-type;
    }
    leaf passive {
      description
        "When set to true the interface is configured as a passive interface and does not send IIH PDUs or try to form an adjacency with other routers.";
      type boolean;
      default "false";
    }
    leaf loopfree-alternate-exclude {
      if-feature "srl-feat:isis-lfa";
      description
        "Enable/disable Loopfree Alternative at interface level.";
      type boolean;
      default "false";
      must "(. = false()) or (../../../../../srl_nokia-netinst:type = 'srl_nokia-netinst:default')" {
        error-message "LFA Configuration is supported only in the default network instance";
      }
    }
    container timers {
      description
        "Enter the timers context

         Container to specify IS-IS interface-level timers for LSP generation and sequence-number PDUs";
      leaf csnp-interval {
        description
          "The interval, specified in seconds, at which periodic CSNP packets should be transmitted by the local IS on this interface.";
        type uint16 {
          range "1..65535";
        }
        default "10";
        units "seconds";
      }
      leaf lsp-pacing-interval {
        description
          "Controls the interval between (bursts of) LSPs sent from the interface.
           The interval applies to all LSPs: LSPs generated by the router, and LSPs received from other routers and re-flooded.

           The burst interval is 100 ms if the lsp-pacing-interval < 100 ms and otherwise it is 1 second. For example, if the lsp-pacing-interval is 2 ms, at most 50 LSPs are sent every 100 ms. On the other hand, if the
           lsp-pacing-interval is 100 ms, at most 10 LSPs are sent every 1 second.

           If a value of 0 is configured, no LSPs are sent from the interface.

           The default pacing interval of 100 milliseconds means that a maximum of 10 LSPs are sent in a burst every second.";
        type uint64 {
          range "0..100000";
        }
        units "milliseconds";
        default "100";
      }
    }
    container ipv4-unicast {
      leaf admin-state {
        description
          "When set to true, the interface and level supports IPv4 unicast routing";
        type srl_nokia-comm:admin-state;
        default "enable";
      }
      leaf enable-bfd {
        if-feature "srl-feat:bfd";
        description
          "Enable BFD for IPv4";
        type boolean;
        default "false";
      }
      leaf include-bfd-tlv {
        if-feature "srl-feat:bfd";
        description
          "Specifies whether a BFD-enabled TLV is included for IPv4 on this IS-IS interface.";
        type boolean;
        default "false";
        must 'not(../enable-bfd = false() and . = true())' {
          error-message "include-bfd-tlv can be set only if enable-bfd is set to true.";
        }
      }
      description
        "Enter the ipv4-unicast context";
    }
    container ipv6-unicast {
      leaf admin-state {
        description
          "When set to true, the interface and level supports IPv6 unicast routing";
        type srl_nokia-comm:admin-state;
        default "enable";
      }
      leaf enable-bfd {
        if-feature "srl-feat:bfd";
        description
          "Enable BFD for IPv6";
        type boolean;
        default "false";
      }
      leaf include-bfd-tlv {
        if-feature "srl-feat:bfd";
        description
          "Specifies whether a BFD-enabled TLV is included for IPv6 on this IS-IS interface.";
        type boolean;
        default "false";
        must 'not(../enable-bfd = false() and . = true())' {
          error-message "include-bfd-tlv can be set only if enable-bfd is set to true.";
        }
      }
      description
        "Enter the ipv6-unicast context";
    }
    container trace-options {
      description
        "Enter the trace-options context

         Interface level debug trace options for IS-IS";
      leaf-list trace {
        description
          "List of tracing options";
        type enumeration {
          enum adjacencies;
          enum packets-all;
          enum packets-p2p-hello;
          enum packets-l1-hello;
          enum packets-l2-hello;
          enum packets-l1-psnp;
          enum packets-l2-psnp;
          enum packets-l1-csnp;
          enum packets-l2-csnp;
          enum packets-l1-lsp;
          enum packets-l2-lsp;
        }
      }
    }
    container segment-routing {
      if-feature "srl-feat:segment-routing";
      presence "Enable SR-MPLS extensions in IS-IS interface";
      must '../../segment-routing/mpls' {
        error-message "Segment routing must be configured at the instance level";
      }
      description
        "Container with interface-specific segment routing options";
      container mpls {
        description
          "Enter the mpls context

           SR-MPLS interface options";
        container ipv4-node-sid {
          presence "IPv4 Node SID Container.";
          description
            "Configuration of IPv4 node SID.

             The (primary) IPv4 address of this interface is advertised as a prefix SID with the node-SID flag set. The associated label is derived from the label index configured in this container.";
          must "(../../../srl_nokia-isis:interface-ref/srl_nokia-isis:interface and ((../../../srl_nokia-isis:interface-ref/srl_nokia-isis:interface = 'system0') or (starts-with(../../../srl_nokia-isis:interface-ref/srl_nokia-isis:interface, 'lo')))) or (not(../../../srl_nokia-isis:interface-ref/srl_nokia-isis:interface) and ((../../../srl_nokia-isis:interface-name = 'system0.0') or (starts-with(../../../srl_nokia-isis:interface-name, 'lo'))))" {
            error-message "The node SID can only be associated with the system0.0 or loopback subinterface";
          }
          leaf index {
            description
              "Label index to add to SRGB base.

               This causes the V-flag and L-flag in the prefix SID subTLV to be set to zero.";
            type uint32 {
              range "0..1048575";
            }
            must '(current() <= ((/srl-system:system/srl_nokia-mplslbl:mpls/srl_nokia-mplslbl:label-ranges/srl_nokia-mplslbl:static[srl_nokia-mplslbl:name=current()/../../../../../../../../srl_nokia-segrt:segment-routing/srl_nokia-segrt:mpls/srl_nokia-segrt:global-block/srl_nokia-segrt:label-range]/srl_nokia-mplslbl:end-label) - (/srl-system:system/srl_nokia-mplslbl:mpls/srl_nokia-mplslbl:label-ranges/srl_nokia-mplslbl:static[srl_nokia-mplslbl:name=current()/../../../../../../../../srl_nokia-segrt:segment-routing/srl_nokia-segrt:mpls/srl_nokia-segrt:global-block/srl_nokia-segrt:label-range]/srl_nokia-mplslbl:start-label)))' {
              error-message "Label index is out of global label block's range";
            }
          }
        }
        container ipv6-node-sid {
          presence "IPv6 Node SID Container.";
          description
            "Configuration of IPv6 node SID.

             The (primary) IPv6 address of this interface is advertised as a prefix SID with the node-SID flag set. The associated label is derived from the label index configured in this container.";
          must "(../../../srl_nokia-isis:interface-ref/srl_nokia-isis:interface and ((../../../srl_nokia-isis:interface-ref/srl_nokia-isis:interface = 'system0') or (starts-with(../../../srl_nokia-isis:interface-ref/srl_nokia-isis:interface, 'lo')))) or (not(../../../srl_nokia-isis:interface-ref/srl_nokia-isis:interface) and ((../../../srl_nokia-isis:interface-name = 'system0.0') or (starts-with(../../../srl_nokia-isis:interface-name, 'lo'))))" {
            error-message "The node SID can only be associated with the system0.0 or loopback subinterface";
          }
          leaf index {
            description
              "Label index to add to SRGB base.

               This causes the V-flag and L-flag in the prefix SID subTLV to be set to zero.";
            type uint32 {
              range "0..1048575";
            }
            must '(current() <= ((/srl-system:system/srl_nokia-mplslbl:mpls/srl_nokia-mplslbl:label-ranges/srl_nokia-mplslbl:static[srl_nokia-mplslbl:name=current()/../../../../../../../../srl_nokia-segrt:segment-routing/srl_nokia-segrt:mpls/srl_nokia-segrt:global-block/srl_nokia-segrt:label-range]/srl_nokia-mplslbl:end-label) - (/srl-system:system/srl_nokia-mplslbl:mpls/srl_nokia-mplslbl:label-ranges/srl_nokia-mplslbl:static[srl_nokia-mplslbl:name=current()/../../../../../../../../srl_nokia-segrt:segment-routing/srl_nokia-segrt:mpls/srl_nokia-segrt:global-block/srl_nokia-segrt:label-range]/srl_nokia-mplslbl:start-label)))' {
              error-message "Label index is out of global label block's range";
            }
          }
        }
        container ipv4-adjacency-sid {
          presence "IPv4 adjacency SID Container.";
          if-feature "srl-feat:segment-routing-adjacency-sid";
          description
            "The IPv4 adjacency SID associated with the interface";
          uses adj-sid-common;
          must "not((../../../srl_nokia-isis:interface-ref/srl_nokia-isis:interface and ((../../../srl_nokia-isis:interface-ref/srl_nokia-isis:interface = 'system0') or (starts-with(../../../srl_nokia-isis:interface-ref/srl_nokia-isis:interface, 'lo')))) or (not(../../../srl_nokia-isis:interface-ref/srl_nokia-isis:interface) and ((../../../srl_nokia-isis:interface-name = 'system0.0') or (starts-with(../../../srl_nokia-isis:interface-name, 'lo')))))" {
            error-message "The adjacency sid cannot be associated with the system0.0 or loopback subinterface";
          }
        }
        container ipv6-adjacency-sid {
          presence "IPv6 adjacency SID Container.";
          if-feature "srl-feat:segment-routing-adjacency-sid";
          description
            "The IPv6 adjacency SID associated with the interface";
          uses adj-sid-common;
          must "not((../../../srl_nokia-isis:interface-ref/srl_nokia-isis:interface and ((../../../srl_nokia-isis:interface-ref/srl_nokia-isis:interface = 'system0') or (starts-with(../../../srl_nokia-isis:interface-ref/srl_nokia-isis:interface, 'lo')))) or (not(../../../srl_nokia-isis:interface-ref/srl_nokia-isis:interface) and ((../../../srl_nokia-isis:interface-name = 'system0.0') or (starts-with(../../../srl_nokia-isis:interface-name, 'lo')))))" {
            error-message "The adjacency sid cannot be associated with the system0.0 or loopback subinterface";
          }
        }
      }
    }
    container weighted-ecmp {
      if-feature "srl-feat:isis-ucmp";
      leaf load-balancing-weight {
        description
          "The load-balancing weight of the interface, which applies when weighted ECMP is enabled and the interface is part of a multipath set.";
        type union {
          type uint32 {
            range "1..4294967295";
          }
          type enumeration {
            enum auto {
              description
                "Load-balancing weight is based on the bandwidth of the parent interface (port or LAG)";
            }
            enum none {
              description
                "The interface should not participate in weighted ECMP";
            }
          }
        }
        default "auto";
      }
      description
        "Enter the weighted-ecmp context";
    }
    list level {
      description
        "List of IS-IS levels supported by this interface";
      max-elements 2;
      key "level-number";
      uses isis-level-key;
      uses isis-interface-level-config;
      uses isis-interface-level-stats;
    }
    uses isis-interface-authentication;
  }

  grouping multi-part-tlv {
    container multi-part-tlv {
      description
        "Enter the multi-part-tlv context

         Enable/disable Multi-Part TLV behavior and view stats.";
      leaf neighbor {
        description
          "Enable/disable Multi-Part for Neighbor TLVs (e.g., 22 / 222).";
        type boolean;
        default "true";
      }
      leaf srlg {
        description
          "Enable/disable Multi-Part for SRLG TLVs (e.g., 138 / 238).

           note that ipv6-srlg (e.g. 139) based upon rfc6119 is not allowed to be a multi-part-tlv.";
        type boolean;
        default "true";
      }
      container statistics {
        config false;
        description
          "Enter the statistics context

           Per-level, per-TLV counters for Multi-Part handling.";
        list tlv {
          key "tlv-type level-number";
          description
            "Statistics keyed by IS-IS level and TLV type.";
          leaf tlv-type {
            description
              "TLV type (e.g., 22, 222, 138, 238).";
            type uint16;
          }
          leaf level-number {
            description
              "IS-IS level for these counters.";
            type srl_nokia-isis-types:isis-level-number;
          }
          leaf mp-tlv-truncated {
            description
              "Number of times the TLV payload was truncated.";
            type srl_nokia-comm:zero-based-counter32;
          }
          leaf mp-tlv-originated {
            description
              "Number of Multi-Part TLVs originated.";
            type srl_nokia-comm:zero-based-counter32;
          }
        }
      }
    }
  }

  grouping isis-inst-common-config {
    leaf admin-state {
      description
        "Used to administratively enable or disable the IS-IS instance";
      type srl_nokia-comm:admin-state;
      default "disable";
    }
    leaf instance-id {
      if-feature "srl-feat:isis-mi";
      description
        "ISIS instance number";
      type uint32 {
        range "0..127";
      }
      default "0";
    }
    leaf-list net {
      max-elements 1;
      description
        "ISIS network entity title (NET)";
      reference
        "International Organization for Standardization,
         Information technology - Open Systems Interconnection-Network service Definition - ISO/ IEC 8348:2002.";
      type srl_nokia-isis-types:isis-net-id;
    }
    leaf level-capability {
      description
        "The level-capability of the intermediate system (router)";
      type srl_nokia-isis-types:isis-level;
      default "L2";
    }
    leaf max-ecmp-paths {
      description
        "The maximum number of ECMP next-hops to program into the FIB for every IP prefix";
      type srl_nokia-isis-types:isis-ecmp;
      default "1";
      must '. <= 8' {
        error-message "Max ECMP paths cannot be greater than 8 on 7215 A1 platform.";
        srl_nokia-ext:if-feature "srl_nokia-features:platform-7215-a1";
      }
      must '(. <= 16)' {
        srl_nokia-ext:if-feature "srl_nokia-features:platform-vsrl";
        error-message "Max ECMP paths cannot be greater than 16 on the VSRL platform.";
      }
    }
    container weighted-ecmp {
      if-feature "srl-feat:isis-ucmp";
      leaf admin-state {
        description
          "Setting enable triggers weighted ECMP programming for all eligible multipath IS-IS routes associated with the instance

           An IS-IS route is eligible for weighted ECMP if all the next-hop interfaces in the multipath set have a load-balancing-weight other than 'none'.

           When weighted ECMP is disabled in an IS-IS instance all IS-IS multipath routes are programmed as normal ECMP, even if some or all of the next-hop interfaces in any particular multipath set have a load-balancing-weight other than 'none'.";
        type srl_nokia-comm:admin-state;
        default "disable";
      }
      leaf max-ecmp-hash-buckets-per-next-hop-group {
        description
          "Specifies the maximum number of ECMP hash buckets per next-hop-group.

           Weighted ECMP weights are normalized based on this number of hash buckets.";
        type uint16 {
          range "1..256";
        }
        must '. >= ../../max-ecmp-paths' {
          error-message "Hash buckets per ECMP next-hop-group cannot be less than the ECMP limit";
        }
        must '. <= 256' {
          error-message "Hash buckets per ECMP next-hop-group cannot be greater than 256 on J2 and J2C+ platforms.";
          srl_nokia-ext:if-feature "srl_nokia-features:ixr-dnx";
        }
        must '. <= 64' {
          error-message "Hash buckets per ECMP next-hop-group cannot be greater than 64 on SRX platforms.";
          srl_nokia-ext:if-feature "srl_nokia-features:fpcx";
        }
      }
      description
        "Enter the weighted-ecmp context";
    }
    leaf poi-tlv {
      description
        "When set to true, a TLV is added to purge to record the system ID of the IS generating the purge.";
      reference
        "RFC6232: Purge Originator Identification TLV for IS-IS.  TLV 13.";
      type boolean;
      default "false";
    }
    leaf iid-tlv {
      if-feature "srl-feat:isis-mi";
      description
        "ISIS Instance Identifier TLV

         When set to true, IID-TLV identifies the unique instance as well as the topology/topologies to which the PDU applies.";
      reference
        "RFC6822: IS-IS Multi-Instance. TLV 7";
      type boolean;
      default "false";
    }
    leaf advertise-router-capability {
      if-feature "srl-feat:isis-rtr-capability";
      description
        "Allow router advertisement capabilities";
      type boolean;
      default "true";
    }
    leaf prefix-attributes-tlv {
      if-feature "srl-feat:isis-rtr-capability";
      description
        "Use IS-IS Prefix Attributes TLV to exchange extended IPv4 and IPv6 reachability information";
      type boolean;
      default "true";
    }
    leaf export-policy {
      description
        "Apply an export policy to redistribute non-ISIS routes into ISIS";
      type leafref {
        path "/srl-rpol:routing-policy/srl-rpol:policy/srl-rpol:name";
      }
    }
    leaf hello-padding {
      description
        "Specifies the use of IS-IS Hello PDU padding all interfaces

         This can be overridden by interface configuration.";
      type srl_nokia-isis-types:isis-hello-padding-type;
      default "disable";
    }
    leaf enable-csnp-on-p2p-links {
      description
        "Enable/disable the transmission of periodic CSNP PDUs on point-to-point interfaces

         When this is set to false, CSNP PDUs will only be sent on a P2P interface when the adjacency is initialized. This setting has no effect on broadcast interfaces.";
      type boolean;
      default "true";
    }
    container attached-bit {
      description
        "Enter the attached-bit context

         This container provides option for handling the ATTached bit in L1 LSPs";
      leaf ignore {
        description
          "When set to true, if the attached bit is set on an incoming Level 1 LSP, the local system ignores it.
           In this case the local system does not set a default route to the L1L2 router advertising the PDU with the attached bit set.";
        type boolean;
        default "false";
      }
      leaf suppress {
        description
          "When set to true, if the local IS acts as a L1L2 router, then the attached bit is not advertised in locally generated L1 LSPs.";
        type boolean;
        default "false";
      }
    }
    container overload {
      description
        "Enter the overload context

         Specifies isis routing instance behavior regarding overload";
      leaf advertise-interlevel {
        description
          "When set to true, L1->L2 and L2->L1 inter-level routes continue to be advertised when the router is in overload.";
        type boolean;
        default "false";
      }
      leaf advertise-external {
        description
          "When set to true, external (non-ISIS) routes continue to be advertised when the router is in overload.";
        type boolean;
        default "false";
      }
      container immediate {
        description
          "Enter the immediate context

           Options for advertising an overloaded state immediately";
        leaf set-bit {
          description
            "When set to true, the Overload bit is set";
          type boolean;
          default "false";
        }
        leaf max-metric {
          description
            "When set to true transit links are advertised with a wide metric of 0xffffffe and a narrow metric of 0x3f";
          type boolean;
          default "false";
          must 'not(../set-bit = false() and . = true())' {
            error-message "max-metric can be set only if set-bit to true.";
          }
        }
      }
      container on-boot {
        description
          "Enter the on-boot context

           Options for advertising an overloaded state whenever the IS-IS process restarts";
        leaf set-bit {
          description
            "When set to true, the Overload bit is set";
          type boolean;
          must "not(../../../../non-stop-forwarding/admin-state = 'enable')" {
            error-message "overload on-boot can be enabled only when no graceful restart is enabled.";
          }
        }
        leaf max-metric {
          description
            "When set to true transit links are advertised with a wide metric of 0xffffffe and a narrow metric of 0x3f";
          type boolean;
        }
        leaf timeout {
          description
            "Specifies the time that the router should remain in overload state after the IS-IS process restarts";
          type uint16 {
            range "60..1800";
          }
          units "seconds";
        }
      }
      leaf instance-is-in-overload {
        description
          "When set to true the IS-IS instance is currently in overload state.";
        config false;
        type boolean;
      }
      leaf overload-rem-interval {
        config false;
        description
          "the value of overload-rem-interval indicates the time for which the system will be in overload state if ISIS is in overload state. the value of 0 implies that the system is indefinitely in overload state.";
        type int32 {
          range "0..65535";
        }
        units "seconds";
      }
      leaf last-overload-entered-time {
        config false;
        description
          "the value of last-overload-entrd-time indicates the time at which the system last went into overload state.";
        type srl_nokia-comm:date-and-time-delta;
      }
      leaf last-overload-exit-time {
        config false;
        description
          "the value of last-overload-exit-time indicates the time at which the system last came out of overload state.";
        type srl_nokia-comm:date-and-time-delta;
      }
      leaf last-overload-enter-code {
        config false;
        description
          "the value of last-overload-enter-code indicates the condition which caused ISIS to get into overload.";
        type enumeration {
          enum none {
            value 1;
          }
          enum dynamic {
            value 2;
          }
          enum boot-overload {
            value 3;
          }
          enum manual-overload {
            value 4;
          }
          enum prefix-limit {
            value 5;
          }
          enum fib-add-fail {
            value 6;
          }
          enum rtm-add-fail {
            value 7;
          }
        }
      }
      leaf last-overload-exit-code {
        config false;
        description
          "the value of last-overload-exit-code indicates the reason why ISIS came out of overload state the last time, since reset.";
        type enumeration {
          enum none {
            value 1;
          }
          enum dynamic {
            value 2;
          }
          enum timer-expired {
            value 3;
          }
          enum manual-exit {
            value 4;
          }
        }
      }
    }
    container timers {
      description
        "Enter the timers context

         Container for IS-IS timers applicable at the instance level";
      leaf lsp-lifetime {
        description
          "Time interval in seconds that the LSPs originated by this IS (router) remain valid in the LSDB before they must be refreshed or else they are purged.";
        type uint16 {
          range "350..65535";
        }
        default "1200";
        units "seconds";
      }
      container lsp-refresh {
        description
          "Enter the lsp-refresh context

           Configure LSP refresh timers.";
        leaf interval {
          description
            "Time interval in seconds since the last advertisement of its LSP when the router attempts to refresh the LSP.
             Must not exceed 90% of the lsp-lifetime.
             This value is ignored when half-lifetime is set to true.";
          type uint16 {
            range "150..65535";
          }
          units "seconds";
          default "600";
        }
        leaf half-lifetime {
          description
            "When set to true, the LSP refresh interval is half the lsp-lifetime";
          type boolean;
          default "true";
        }
      }
      container spf {
        description
          "Enter the spf context

           Container with options for specifying SPF timer values";
        leaf initial-wait {
          description
            "Time interval between the detection of topology change and when the SPF algorithm runs.

             The timer granularity is 100 ms. Timer values are rounded down to the nearest granularity, for example a configured value of 550 ms is internally rounded down to 500 ms";
          type uint64 {
            range "10..100000";
          }
          units "milliseconds";
          default "1000";
        }
        leaf second-wait {
          description
            "Time interval between the the first and second SPF run.

             The timer granularity is 100 ms. Timer values are rounded down to the nearest granularity, for example a configured value of 550 ms is internally rounded down to 500 ms";
          type uint64 {
            range "10..100000";
          }
          units "milliseconds";
          default "1000";
        }
        leaf max-wait {
          description
            "Specifies the maximum interval between two consecutive SPF calculations in milliseconds.

             The timer granularity is 100 ms. Timer values are rounded down to the nearest granularity, for example a configured value of 550 ms is internally rounded down to 500 ms";
          type uint64 {
            range "10..120000";
          }
          units "milliseconds";
          default "10000";
        }
      }
      container lsp-generation {
        description
          "Enter the lsp-generation context

           Container with options for specifying LSP generation timer values";
        leaf initial-wait {
          description
            "Time interval between the detection of topology change and when the new LSP is generated.

             The timer granularity is 100 ms. Timer values are rounded down to the nearest granularity, for example a configured value of 550 ms is internally rounded down to 500 ms";
          type uint64 {
            range "10..100000";
          }
          units "milliseconds";
          default "10";
        }
        leaf second-wait {
          description
            "Time interval between the the first and second LSP generation.

             The timer granularity is 100 ms. Timer values are rounded down to the nearest granularity, for example a configured value of 550 ms is internally rounded down to 500 ms";
          type uint64 {
            range "10..100000";
          }
          units "milliseconds";
          default "1000";
        }
        leaf max-wait {
          description
            "Specifies the maximum interval between two consecutive generations of an LSP.

             The timer granularity is 100 ms. Timer values are rounded down to the nearest granularity, for example a configured value of 550 ms is internally rounded down to 500 ms";
          type uint64 {
            range "10..120000";
          }
          units "milliseconds";
          default "5000";
        }
      }
    }
    container trace-options {
      description
        "Enter the trace-options context

         Instance level debug trace options for IS-IS";
      leaf-list trace {
        description
          "List of tracing options";
        type enumeration {
          enum adjacencies;
          enum graceful-restart;
          enum interfaces;
          enum packets-all;
          enum packets-p2p-hello;
          enum packets-l1-hello;
          enum packets-l2-hello;
          enum packets-l1-psnp;
          enum packets-l2-psnp;
          enum packets-l1-csnp;
          enum packets-l2-csnp;
          enum packets-l1-lsp;
          enum packets-l2-lsp;
          enum routes;
          enum summary-addresses;
        }
      }
    }
    container transport {
      description
        "Enter the transport context

         This container defines ISIS transport.";
      leaf lsp-mtu-size {
        description
          "Sets the maximum size of LSPs generated by this router";
        type uint16 {
          range "490..9490";
        }
        units "bytes";
        default "1492";
      }
    }
    container ipv4-unicast {
      description
        "Enter the ipv4-unicast context

         Enables/disables IPv4 routing in this ISIS instance.";
      leaf admin-state {
        description
          "When set to true, the IS-IS instance supports IPv4 unicast routing";
        type srl_nokia-comm:admin-state;
        default "enable";
      }
      leaf suppress-interface-ip {
        if-feature "srl-feat:isis-advertise-passive-only";
        description
          "Suppress advertisement of IPv4 interface prefixes

           When set to non-passive, IS-IS must suppress LSP PDU advertisement of IPv4 prefixes that correspond to any IS-IS interface not configured as passive.";
        type enumeration {
          enum none;
          enum non-passive;
        }
        default "none";
      }
    }
    container ipv6-unicast {
      description
        "Enter the ipv6-unicast context

         Enables/disables IPv6 routing in this ISIS instance.";
      leaf admin-state {
        description
          "When set to true, the IS-IS instance supports IPv6 unicast routing";
        type srl_nokia-comm:admin-state;
        default "enable";
      }
      leaf multi-topology {
        if-feature "srl-feat:isis-mt";
        description
          "When set to true, IS-IS multi-topology TLVs are used for IPv6 routing and support for native IPv6 TLVs is disabled.";
        type boolean;
        default "false";
        must "not(../admin-state = 'disable' and . = true())" {
          error-message "multi-topology can be set only if ipv6 is enabled.";
        }
      }
      leaf suppress-interface-ip {
        if-feature "srl-feat:isis-advertise-passive-only";
        description
          "Suppress advertisement of IPv6 interface prefixes

           When set to non-passive, IS-IS must suppress LSP PDU advertisement of IPv6 prefixes that correspond to any IS-IS interface not configured as passive.";
        type enumeration {
          enum none;
          enum non-passive;
        }
        default "none";
      }
    }
    container graceful-restart {
      description
        "Enter the graceful-restart context

         Container for options related to IS-IS graceful restart";
      reference
        "RFC 5306: Restart Signaling for IS-IS.";
      leaf helper-mode {
        description
          "Enable or disable the IS-IS graceful restart helper function

           When this leaf is set, the local system supports retaining forwarding information during a neighbor router's restart.";
        type boolean;
        default "false";
      }
      leaf acceptable-duration {
        if-feature "srl-feat:isis-nsf";
        description
          "Initial value of the Remaining Time that is advertised in the Restart TLV with Restart Acknowledgement flag set when this router starts to help another router that has just (re)entered Restart mode.";
        type uint32 {
          range "1..20000";
        }
        units "seconds";
        default "60";
      }
    }
    container auto-cost {
      description
        "Enter the auto-cost context

         Container for options related to automated and derived interface metrics";
      leaf reference-bandwidth {
        description
          "Configures the reference bandwidth that provides the basis for interface metrics based on link bandwidth.

           If the reference bandwidth is defined, then the cost is calculated using the following formula:
               cost = reference-bandwidth / bandwidth

           When a large reference-bandwidth value is configured, a metric calculation may result in a value higher than the supported protocol cost value. If this occurs, IS-IS automatically reverts to the maximum configurable cost metric.

           If the reference bandwidth is not configured then all interfaces have a default metric of 10.

           Note: To use metrics in excess of 63, wide metrics must be deployed";
        type uint64 {
          range "1..8000000000";
        }
        units "kbps";
      }
    }
    uses multi-part-tlv {
      if-feature "srl-feat:isis-multi-part-tlv";
    }
    uses isis-instance-lfa {
      if-feature "srl-feat:isis-lfa";
    }
    uses srl_nokia-te:protocol-instance-tedb {
      if-feature "srl-feat:traffic-engineering-isis-tedb-install";
    }
  }

  grouping inst-traffic-engineering-config {
    container traffic-engineering {
      description
        "Enter the traffic-engineering context

         container for traffic engineering information";
      uses srl_nokia-te:igp-instance-te-advertisement {
        if-feature "srl-feat:traffic-engineering";
      }
      leaf legacy-link-attribute-advertisement {
        if-feature "srl-feat:traffic-engineering";
        description
          "The advertisement mode for TE link attributes.

           A setting of true means that TE properties should be advertised in legacy mode as defined in RFC 8919 and RFC 8920.";
        type boolean;
        default "true";
      }
      leaf ipv4-te-router-id {
        description
          "A routable IPv4 address to identify the router uniquely in a TE domain. TLV = 134.

           The ipv4-te-router-id contains the 4-octet router ID of the router originating the LSP.
           The ipv4-te-router-id guarantees a single stable address that can always be referenced
           in a path that will be reachable from multiple hops away, regardless of the state
           of the node's interfaces.

           The configured ipv4-te-router-id address must be active and reachable within the routing
           instance and must be associated to either a system or loopback interface. The state
           value represents the operational advertised of ipv4-te-router-id";
        type srl_nokia-comm:ipv4-address-unicast;
      }
      leaf ipv6-te-router-id {
        description
          "A routable IPv6 address to identify the router uniquely in a TE domain. TLV = 140.

           The ipv6-te-router-id contains the 4-octet router ID of the router originating the LSP.
           The ipv6-te-router-id guarantees a single stable address that can always be referenced
           in a path that will be reachable from multiple hops away, regardless of the state
           of the node's interfaces.

           The configured ipv6-te-router-id address must be active and reachable within the routing
           instance and must be associated to either a system or loopback interface. The state
           value represents the operational advertised of ipv6-te-router-id";
        type srl_nokia-comm:ipv6-address-unicast-without-local;
      }
    }
  }

  grouping isis-level-config {
    leaf metric-style {
      description
        "Specifies the metric style to be wide or narrow for the level";
      type srl_nokia-isis-types:isis-metric-style;
      default "wide";
    }
    leaf loopfree-alternate-exclude {
      if-feature "srl-feat:isis-lfa";
      description
        "Enable/disable LFA at ISIS level.";
      type boolean;
      default "false";
      must "(. = false()) or (../../../../../srl_nokia-netinst:type = 'srl_nokia-netinst:default')" {
        error-message "LFA Configuration is supported only in the default network instance";
      }
    }
    container route-preference {
      description
        "Enter the route-preference context

         Specify the route preference (admin distance) for IP routes asssociated with the level";
      leaf external {
        description
          "Specify the route preference of external routes carried in this level.
           By default the route preference of external L1 routes is 160.
           By default the route preference of external L2 routes is 165.";
        type uint8 {
          range "1..255";
        }
      }
      leaf internal {
        description
          "Specify the route preference of internal routes carried in this level.
           By default the route preference of internal L1 routes is 15.
           By default the route preference of internal L2 routes is 18.";
        type uint8 {
          range "1..255";
        }
      }
    }
    container trace-options {
      description
        "Enter the trace-options context

         Level debug trace options for IS-IS";
      leaf-list trace {
        description
          "List of tracing options";
        type enumeration {
          enum adjacencies;
          enum lsdb;
          enum routes;
          enum spf;
        }
      }
    }
    uses isis-instance-level-authentication;
    uses srl_nokia-te:igp-area-level-tedb {
      if-feature "srl-feat:traffic-engineering-bgpls";
    }
  }

  grouping isis-level-stats {
    container statistics {
      config false;
      description
        "Enter the statistics context

         Per level statistics in an ISIS instance";
      leaf authentication-failures {
        description
          "Number of times an IS-IS control PDU associated with this level had the correct auth type but failed to pass authentication validation";
        type srl_nokia-comm:zero-based-counter32;
      }
      leaf authentication-type-failures {
        description
          "Number of times an IS-IS control PDU associated with this level had an auth type field different from that for this system";
        type srl_nokia-comm:zero-based-counter32;
      }
      leaf total-lsps {
        description
          "Number of LSPs in the database at the system level";
        type srl_nokia-comm:zero-based-counter32;
      }
      leaf corrupted-lsps {
        description
          "Number of corrupted in-memory LSPs detected. LSPs received from the wire with a bad checksum are silently dropped and not counted. LSPs received from the wire with parse errors are counted by lsp-errors";
        type srl_nokia-comm:zero-based-counter32;
      }
      leaf database-overloads {
        description
          "Number of times the database has become overloaded";
        type srl_nokia-comm:zero-based-counter32;
      }
      leaf exceeded-max-sequence-number {
        description
          "Number of times the system has attempted to exceed the maximum sequence number";
        type srl_nokia-comm:zero-based-counter32;
      }
      leaf system-id-length-mismatches {
        description
          "Number of times an IS-IS control PDU associated with this level was received with a system ID field length different from that for this system";
        type srl_nokia-comm:zero-based-counter32;
      }
      leaf lsp-errors {
        description
          "Number of received LSPs with parse errors";
        type srl_nokia-comm:zero-based-counter32;
      }
      leaf manual-address-drop-from-area {
        description
          "number of times a manual address has been dropped from area";
        type srl_nokia-comm:zero-based-counter32;
      }
      leaf max-area-address-mismatches {
        description
          "Number of times an IS-IS control PDU associated with this level was received with a max area address field different from that for this system";
        type srl_nokia-comm:zero-based-counter32;
      }
      leaf own-lsp-purges {
        description
          "Number of times a zero-aged copy of the system's own LSP is received from some other node";
        type srl_nokia-comm:zero-based-counter32;
      }
      leaf sequence-number-skips {
        description
          "Number of times a sequence number skip has occurred";
        type srl_nokia-comm:zero-based-counter32;
      }
      leaf spf-runs {
        description
          "number of times a full SPF run has been performed on the level LSDB since the IS-IS manager restarted";
        type srl_nokia-comm:zero-based-counter32;
      }
    }
  }

  grouping isis-interlevel-import-export-config {
    container inter-level-propagation-policies {
      description
        "Enter the inter-level-propagation-policies context

         Container with options to control the propagation of prefixes between levels";
      container level1-to-level2 {
        description
          "Enter the level1-to-level2 context

           Container with options to control the propagation of prefixes from level 1 to level 2.

           By default all L1 prefixes are propagated without summarizarion into L2.";
        list summary-address {
          description
            "List of summarization prefixes";
          key "ip-prefix";
          leaf ip-prefix {
            description
              "An IP prefix advertised into L2 that summarizes one or more L1 prefixes and causes them to be suppressed";
            type srl_nokia-comm:ip-prefix;
          }
          leaf route-tag {
            description
              "Specifies route tag value to assign to the summary route";
            type srl_nokia-isis-types:isis-admin-tag;
          }
        }
      }
    }
  }

  grouping isis-protocol-segment-routing {
    leaf dynamic-label-block {
      if-feature "srl-feat:label-management";
      type leafref {
        path "/srl-system:system/srl_nokia-mplslbl:mpls/srl_nokia-mplslbl:label-ranges/srl_nokia-mplslbl:dynamic/srl_nokia-mplslbl:name";
      }
      description
        "Reference to a dynamic label block

         Configuration of this label block is mandatory in order to enable segment routing MPLS (SR-MPLS) in IS-IS. Dynamic adjacency SID labels come from this label block.

         This label block is not advertised as an SRLB in the router capabilities TLV.";
    }
    leaf dynamic-label-block-status {
      config false;
      if-feature "srl-feat:label-management";
      type enumeration {
        enum available;
        enum unavailable;
      }
      description
        "Status of the label block.

         The label block may show as unavailable if there is pending cleanup.";
    }
  }

  grouping isis-inst-entropy-label {
    container entropy-label {
      if-feature "srl-feat:entropy-bgp-sr";
      description
        "Enter the entropy-label context

         Options for configuring control and data plane aspects of entropy label";
      leaf advertise-capability {
        description
          "Advertise the Entropy Label Capability";
        type boolean;
        default "false";
      }
      leaf transmit {
        description
          "Specify conditions for adding ELI/EL when pushing isis label";
        type enumeration {
          enum enable;
          enum disable;
        }
        default "disable";
      }
    }
  }

  grouping isis-inst-maximum-segment-depth {
    container maximum-sid-depth {
      if-feature "srl-feat:traffic-engineering";
      description
        "Enter the maximum-sid-depth context

         Container to configure advertise multiple types of Maximum SID Depths (MSDs).

         maximum-sid-depth advertisements allow entities (e.g., centralized controllers) to
         determine whether a particular Segment ID (SID) stack can be
         supported in a given network";
      leaf override-bmi {
        description
          "Value to override the announced node MSD-BMI value";
        type int32 {
          range "0..25";
        }
        must '. <= 10' {
          error-message "Max labels that can be imposed cannot be greater than 10 on IXR DNX platforms.";
          srl_nokia-ext:if-feature "srl_nokia-features:ixr-dnx";
        }
        must '. <= 25' {
          error-message "Max labels that can be imposed cannot be greater than 25 on IXR SRX platforms.";
          srl_nokia-ext:if-feature "srl_nokia-features:fpcx";
        }
      }
      leaf override-erld {
        if-feature "srl-feat:entropy-bgp-sr";
        description
          "Value to override the announced node MSD-ERLD value";
        type int32 {
          range "0..14";
        }
      }
    }
  }

  grouping isis-inst-mpls-segment-routing {
    container segment-routing {
      if-feature "srl-feat:segment-routing";
      description
        "Enter the segment-routing context

         Container used to configure segment-routing";
      container mpls {
        presence "Enable SR-MPLS extensions in IS-IS";
        must "../../../../../srl_nokia-netinst:type = 'srl_nokia-netinst:default'" {
          error-message "Segment routing is only supported in the default network instance";
        }
        must 'boolean(../../../../../srl_nokia-segrt:segment-routing/srl_nokia-segrt:mpls/srl_nokia-segrt:global-block) and boolean(../../../../../srl_nokia-segrt:segment-routing/srl_nokia-segrt:mpls)' {
          error-message "Segment routing can be supported only when network instance has segment routing enabled along with a SRGB.";
        }
        description
          "Context used to configure SR-MPLS options";
        container dynamic-adjacency-sids {
          if-feature "srl-feat:segment-routing-adjacency-sid";
          leaf all-interfaces {
            type boolean;
            description
              "When true, IS-IS is instructed to assign a dynamic adjacency SID to all IS-IS interfaces in all levels, except for the interfaces configured with an adjacency SID assignment of 'none' or 'static'.";
            default "false";
            must 'boolean(../../../../../dynamic-label-block) or (. != true())' {
              error-message "Dynamic adj sid-s can be enabled on all interfaces only when the Dynamic SRLB is configured.";
            }
          }
          description
            "Enter the dynamic-adjacency-sids context";
        }
        uses isis-inst-entropy-label;
        uses isis-inst-maximum-segment-depth;
        leaf static-label-block {
          if-feature "srl-feat:label-management";
          if-feature "srl-feat:segment-routing-adjacency-sid";
          type leafref {
            path "/srl-system:system/srl_nokia-mplslbl:mpls/srl_nokia-mplslbl:label-ranges/srl_nokia-mplslbl:static/srl_nokia-mplslbl:name";
          }
          must 'not ((/srl-system:system/srl_nokia-mplslbl:mpls/srl_nokia-mplslbl:label-ranges/srl_nokia-mplslbl:static[srl_nokia-mplslbl:name=current()]/shared) = true())' {
            error-message "Static label block must not be shareable";
          }
          description
            "Reference to a static label block to use an SRLB.

             Configuration of this label block is mandatory in order to assign static adjacency SID labels.

             This label block is advertised as an SRLB in the router capabilities TLV.";
        }
        leaf static-label-block-status {
          config false;
          if-feature "srl-feat:label-management";
          if-feature "srl-feat:segment-routing-adjacency-sid";
          type enumeration {
            enum available;
            enum unavailable;
          }
          description
            "Status of the label block.

             The label block may show as unavailable if there is pending cleanup.";
        }
        leaf adjacency-sid-hold-time {
          if-feature "srl-feat:isis-adjsid-holdtime";
          description
            "Timer to maintain the operational state of the adjacency SID following a failure of the adjacency.";
          type union {
            type enumeration {
              enum none;
            }
            type uint16 {
              range "1..300";
            }
          }
          units "seconds";
          default "15";
        }
        container ingress-statistics {
          if-feature "srl-feat:segment-routing-isis-lsp-stats";
          description
            "Enter the ingress-statistics context";
          leaf adj-sid {
            type boolean;
            default "false";
            description
              "Enable the allocation of statistics on adjacency SIDs";
          }
          leaf node-sid {
            type boolean;
            default "false";
            description
              "Enable the allocation of statistics on node SIDs";
          }
        }
        container egress-statistics {
          if-feature "srl-feat:segment-routing-isis-lsp-stats";
          description
            "Enter the egress-statistics context";
          leaf adj-sid {
            type boolean;
            default "false";
            description
              "Enable the allocation of statistics on adjacency SIDs";
          }
          leaf node-sid {
            type boolean;
            default "false";
            description
              "Enable the allocation of statistics on node SIDs";
          }
        }
        container sid-statistics {
          if-feature "srl-feat:segment-routing-isis-lsp-stats";
          config false;
          description
            "Enter the sid-statistics context

             SID statistics";
          list label {
            key "label";
            description
              "Enter the sid-statistics list instance";
            leaf label {
              type srl_nokia-comm:mpls-label-non-reserved;
              description
                "The value specifies the SID label";
            }
            leaf type {
              type enumeration {
                enum node {
                  value 0;
                }
                enum adjacency {
                  value 1;
                }
              }
              description
                "The type of SID for which statistics are collected";
            }
            leaf prefix {
              type srl_nokia-comm:ipv4-prefix;
              description
                "The IP address type";
            }
            leaf interface {
              type srl_nokia-comm:subinterface-all;
              description
                "Ougoing subinterface";
            }
            leaf algorithm {
              type uint8;
              description
                "The value indicates the algorithm related to the prefix SID.

                 The value can indicate a defined IGP Algorithm (value 0 is SPF)";
            }
            container egress {
              description
                "Enter the egress context";
              leaf oper-state {
                type enumeration {
                  enum enabled {
                    value 1;
                  }
                  enum disabled {
                    value 2;
                  }
                }
                description
                  "The statistics operational state of this SID for this direction";
              }
              leaf octets {
                type srl_nokia-comm:zero-based-counter64;
                description
                  "The number of octets";
              }
              leaf packets {
                type srl_nokia-comm:zero-based-counter64;
                description
                  "The number of packets";
              }
              uses lsp-stats-resource-allocation-status;
            }
            container ingress {
              description
                "Enter the ingress context";
              leaf oper-state {
                type enumeration {
                  enum enabled {
                    value 1;
                  }
                  enum disabled {
                    value 2;
                  }
                }
                description
                  "The statistics operational state of this SID for this direction";
              }
              leaf octets {
                type srl_nokia-comm:zero-based-counter64;
                description
                  "The number of octets";
              }
              leaf packets {
                type srl_nokia-comm:zero-based-counter64;
                description
                  "The number of packets";
              }
              uses lsp-stats-resource-allocation-status;
            }
          }
        }
        uses isis-sid-database;
      }
      uses micro-loop-avoidance {
        if-feature "srl-feat:isis-micro-loop-avoidance";
      }
    }
  }

  grouping isis-inst-config {
    uses isis-inst-common-config;
    uses isis-instance-level-authentication;
    uses isis-interlevel-import-export-config;
    uses srl_nokia-ldp:ldp-sync-global-config;
  }

  grouping isis-statistics-state {
    leaf lsp-regenerations {
      config false;
      description
        "Indicates the count of LSP regenerations.";
      type yang:zero-based-counter64;
    }
    leaf initiated-purges {
      config false;
      description
        "Indicates the number of times purges have been initiated.";
      type yang:zero-based-counter64;
    }
    leaf corrupted-lsps {
      config false;
      description
        "Indicates the number of corrupted LSPs detected.";
      type yang:zero-based-counter64;
    }
    leaf lsp-l1-db-overloads {
      config false;
      description
        "Indicates the number of times the LSP L1 database has become overloaded.";
      type yang:zero-based-counter64;
    }
    leaf lsp-l2-db-overloads {
      config false;
      description
        "Indicates the number of times the Level 2 LSP database has become overloaded.";
      type yang:zero-based-counter64;
    }
    leaf manual-address-dropped-from-areas {
      config false;
      description
        "Indicates the number of times a manual address has been dropped from the area.";
      type yang:zero-based-counter64;
    }
    leaf attempt-to-exceed-max-sequence-numbers {
      config false;
      description
        "Indicates the number of times the IS has attempted to exceed the maximum sequence number.";
      type yang:zero-based-counter64;
    }
    leaf sequence-number-skips {
      config false;
      description
        "Indicates the number of times a sequence number skip has occurred.";
      type yang:zero-based-counter64;
    }
    leaf own-lsp-purges {
      config false;
      description
        "Indicates the number of times a zero-aged copy of the system's own LSP is received from some other node.";
      type yang:zero-based-counter64;
    }
    leaf id-field-length-mismatches {
      config false;
      description
        "Indicates the number of times a PDU is received with a different value for ID field length to that of the receiving system.";
      type yang:zero-based-counter64;
    }
    leaf max-area-address-mismatches {
      config false;
      description
        "Indicates the number of times a PDU is received with a different value for maximum area addresses from that of the receiving system.";
      type yang:zero-based-counter64;
    }
    leaf partition-changes {
      config false;
      description
        "indicates the number of partition changes.";
      type yang:zero-based-counter64;
    }
  }

  grouping isis-pdu-statistics {
    leaf received {
      config false;
      description
        "The number of PDUs that were received";
      type srl_nokia-comm:zero-based-counter32;
    }
    leaf processed {
      config false;
      description
        "The number of PDUs that were received and processed";
      type srl_nokia-comm:zero-based-counter32;
    }
    leaf dropped {
      config false;
      description
        "The number of PDUs that were received and dropped";
      type srl_nokia-comm:zero-based-counter32;
    }
    leaf sent {
      config false;
      description
        "The number of PDUs that were transmitted";
      type srl_nokia-comm:zero-based-counter32;
    }
  }

  grouping isis-instance-statistics {
    container statistics {
      config false;
      description
        "Enter the statistics context

         Instance level statistics";
      leaf spf-runs {
        config false;
        description
          "The number of times a full SPF run has been performed on either the L1 or L2 LSDB since the IS-IS manager restarted";
        type srl_nokia-comm:zero-based-counter32;
      }
      leaf last-spf {
        config false;
        description
          "The elapsed time since the last time a full SPF run was run on either the L1 or L2 LSDB";
        type srl_nokia-comm:date-and-time-delta;
      }
      leaf partial-spf-runs {
        config false;
        description
          "The number of times a partial SPF run has been performed on either the L1 or L2 LSDB since the IS-IS manager restarted";
        type srl_nokia-comm:zero-based-counter32;
      }
      leaf last-partial-spf {
        config false;
        description
          "The elapsed time since the last time a partial SPF run was run on either the L1 or L2 LSDB";
        type srl_nokia-comm:date-and-time-delta;
      }
      list pdu {
        config false;
        description
          "List of PDUs processed by the IS-IS instance since the IS-IS manager restarted";
        key "pdu-name";
        leaf pdu-name {
          type srl_nokia-isis-types:isis-pdu-type;
          description
            "The PDU type that was processed";
        }
        uses isis-pdu-statistics;
      }
    }
  }

  grouping isis-inst-common-state {
    leaf oper-state {
      config false;
      description
        "The value of the this object indicates the operational state of the destination.";
      type srl_nokia-comm:oper-state;
    }
    leaf-list oper-area-id {
      config false;
      description
        "The list of area IDs associated with this IS router";
      type srl_nokia-isis-types:isis-area-address;
    }
    leaf oper-system-id {
      config false;
      description
        "The ID for this instance of the Integrated IS-IS protocol.";
      type srl_nokia-comm:isis-system-id;
    }
    container restarting-neighbor-list {
      config false;
      description
        "Enter the restarting-neighbor-list context

         The list of neighbors that have restarted recently and that are currently being helped.";
      list neighbor {
        description
          "The list of neighbors that have restarted recently and that are currently being helped.";
        key "system-id";
        leaf system-id {
          description
            "The neighbor router's system ID.";
          type srl_nokia-comm:isis-system-id;
        }
        leaf hostname {
          description
            "The hostname of the neighbor, as learned by TLV 137.";
          type string;
        }
      }
    }
    uses isis-instance-statistics;
    uses isis-topology-state {
      if-feature "srl-feat:isis-topology-state";
    }
  }

  grouping neighbor-sub-tlvs {
    container sub-tlvs {
      description
        "Enter the sub-tlvs context

         SubTLVs of TLV 22 and TLV 222";
      leaf admin-group {
        if-feature "srl-feat:traffic-engineering";
        description
          "A bit mask representing the administrative groups to which the interface belongs. Sub-TLV = 3.";
        type uint32;
      }
      leaf ipv4-interface-address {
        description
          "The IPv4 address of the interface to the neighbor. Sub-TLV = 6.";
        type srl_nokia-comm:ipv4-address;
      }
      leaf ipv4-neighbor-address {
        description
          "The IPv4 address of the neighbor. Sub-TLV = 8.";
        type srl_nokia-comm:ipv4-address;
      }
      leaf maximum-link-bandwidth {
        if-feature "srl-feat:traffic-engineering";
        description
          "The (LAG aware) bandwidth of the interface to the neighbor. Sub-TLV = 9.";
        type uint32;
        units "bytes-per-second";
      }
      leaf ipv6-interface-address {
        description
          "The IPv6 address of the interface to the neighbor. Sub-TLV = 12.";
        type srl_nokia-comm:ipv6-address;
      }
      leaf ipv6-neighbor-address {
        description
          "The IPv4 address of the neighbor. Sub-TLV = 13.";
        type srl_nokia-comm:ipv6-address;
      }
      container link-msd {
        if-feature "srl-feat:segment-routing";
        description
          "Enter the link-msd context

           The maximum segment depth of the link to the neighbor. Sub-TLV = 15.";
        list msd-info {
          description
            "List of MSD entries";
          key "msd-type msd-value";
          leaf msd-type {
            description
              "MSD type";
            type union {
              type enumeration {
                enum base-mpls-imposition-msd {
                  value 1;
                }
              }
              type uint8 {
                range "2..254";
              }
            }
          }
          leaf msd-value {
            description
              "A number in the range of 0-255 representing the maximum SID depth; for all MSD-Types, 0 represents the lack of ability to support a SID stack of any depth";
            type uint8;
          }
        }
      }
      container application-specific-link-attributes {
        if-feature "srl-feat:traffic-engineering";
        description
          "Enter the application-specific-link-attributes context

           Application Specific Link Attributes. Sub-TLV = 16.";
        reference
          "RFC8919";
        leaf legacy {
          description
            "When the legacy flag is set, all of the applications specified in the bit mask MUST use the legacy advertisements for the corresponding link found in TLVs 22, 23, 25, 141, 222, and 223, in TLV 138, or in TLV 139 as appropriate.";
          type boolean;
        }
        leaf rsvp-te {
          description
            "R bit is set in the Standard Application Identifier Bit Mask";
          type boolean;
        }
        leaf sr-policy {
          description
            "S bit is set in the Standard Application Identifier Bit Mask";
          type boolean;
        }
        leaf loop-free-alternate {
          description
            "F bit is set in the Standard Application Identifier Bit Mask";
          type boolean;
        }
        container sub-sub-tlvs {
          leaf admin-group {
            description
              "A bit mask representing the administrative groups to which the interface belongs. Sub-Sub-TLV = 3.";
            type uint32;
          }
          leaf maximum-link-bandwidth {
            description
              "The (LAG aware) bandwidth of the interface to the neighbor. Sub-Sub-TLV = 9.";
            type uint32;
            units "bytes-per-second";
          }
          leaf te-default-metric {
            description
              "An administratively assigned metric used as an alternative to the normal SPF metric based (typically) on link bandwidth.";
            type uint32 {
              range "0..16777215";
            }
          }
          container min-max-unidirectional-link-delay {
            description
              "Enter the min-max-unidirectional-link-delay context

               The minimum and maximum delay between two directly connected IS-IS neighbors.";
            leaf anomolous {
              description
                "If the A bit is cleared, the values represent steady-state link performance.";
              type boolean;
            }
            leaf min-delay {
              description
                "Minimum forward-path delay (from the advertising router to the remote neighbor)";
              type uint32;
              units "microseconds";
            }
            leaf max-delay {
              description
                "Maximum forward-path delay (from the advertising router to the remote neighbor)";
              type uint32;
              units "microseconds";
            }
          }
          description
            "Enter the sub-sub-tlvs context";
        }
      }
      leaf te-default-metric {
        if-feature "srl-feat:traffic-engineering";
        description
          "An administratively assigned metric used as an alternative to the normal SPF metric based (typically) on link bandwidth. Sub-TLV = 18.";
        type uint32 {
          range "0..16777215";
        }
      }
      list segment-routing-adjacency-sid {
        if-feature "srl-feat:segment-routing";
        description
          "List of Adj-SID sub-TLVs associated with the neighbor. Sub-TLV = 31.";
        key "sr-index-or-label";
        leaf sr-index-or-label {
          description
            "An index representing an offset in the SID/label space advertised by the router or else a direct encoding of an MPLS label value.";
          type uint32;
        }
        leaf ipv6-family {
          description
            "If set, then the Adj-SID is used for forwarding IPv6 traffic to the neighbor; else the Adj-SID is used for forwarding IPv4 traffic.";
          type boolean;
        }
        leaf backup {
          description
            "If set, the Adj-SID is eligible for protection";
          type boolean;
        }
        leaf value {
          description
            "If set then the Adj-SID carries a value";
          type boolean;
        }
        leaf local {
          description
            "If set, then the value/index carried by the Adj-SID has local significance.";
          type boolean;
        }
        leaf adj-set {
          description
            "When set, the S-Flag indicates that the Adj-SID refers to a set of adjacencies.";
          type boolean;
        }
        leaf persistent {
          description
            "When set, the P-Flag indicates that the Adj-SID is persistently allocated, i.e., the Adj-SID value remains consistent across router restart and/or interface flap";
          type boolean;
        }
        leaf weight {
          description
            "The value represents the weight of the Adj-SID for the purpose of load balancing";
          type uint8;
        }
      }
      list segment-routing-lan-adjacency-sid {
        if-feature "srl-feat:segment-routing";
        description
          "List of LAN Adj-SID sub-TLVs. Each describes the set of Adj-SIDs the router assigned to each of its LAN neighbors. Sub-TLV = 32.";
        key "sr-index-or-label";
        leaf sr-index-or-label {
          description
            "An index representing an offset in the SID/label space advertised by the router or else a direct encoding of an MPLS label value.";
          type uint32;
        }
        leaf neighbor-system-id {
          description
            "IS-IS system-ID of the LAN neighbor";
          type srl_nokia-comm:isis-system-id;
        }
        leaf ipv6-family {
          description
            "If set, then the Adj-SID is used for forwarding IPv6 traffic to the neighbor; else the Adj-SID is used for forwarding IPv4 traffic.";
          type boolean;
        }
        leaf backup {
          description
            "If set, the Adj-SID is eligible for protection";
          type boolean;
        }
        leaf value {
          description
            "If set then the Adj-SID carries a value";
          type boolean;
        }
        leaf local {
          description
            "If set, then the value/index carried by the Adj-SID has local significance.";
          type boolean;
        }
        leaf adj-set {
          description
            "When set, the S-Flag indicates that the Adj-SID refers to a set of adjacencies.";
          type boolean;
        }
        leaf persistent {
          description
            "When set, the P-Flag indicates that the Adj-SID is persistently allocated, i.e., the Adj-SID value remains consistent across router restart and/or interface flap";
          type boolean;
        }
        leaf weight {
          description
            "The value represents the weight of the Adj-SID for the purpose of load balancing";
          type uint8;
        }
      }
      container min-max-unidirectional-link-delay {
        if-feature "srl-feat:traffic-engineering";
        description
          "Enter the min-max-unidirectional-link-delay context

           The minimum and maximum delay between two directly connected IS-IS neighbors. Sub-TLV = 34.";
        leaf anomolous {
          description
            "If the A bit is cleared, the values represent steady-state link performance.";
          type boolean;
        }
        leaf min-delay {
          description
            "Minimum forward-path delay (from the advertising router to the remote neighbor)";
          type uint32;
          units "microseconds";
        }
        leaf max-delay {
          description
            "Maximum forward-path delay (from the advertising router to the remote neighbor)";
          type uint32;
          units "microseconds";
        }
      }
    }
  }

  grouping prefix-sub-tlvs {
    container sub-tlvs {
      description
        "Enter the sub-tlvs context

         SubTLVs of TLV 135, TLV 235, TLV 236 and TLV 237";
      leaf-list route-tag-32bit {
        description
          "List of 32-bit administrative tag values associated with the IPv4 prefix.";
        type uint32 {
          range "1..4294967295";
        }
      }
      leaf-list route-tag-64bit {
        description
          "List of 64-bit administrative tag values associated with the IPv4 prefix.";
        type uint64;
      }
      container segment-routing-prefix-sid {
        if-feature "srl-feat:segment-routing";
        description
          "Enter the segment-routing-prefix-sid context

           Carries a segment routing prefix SID";
        leaf re-advertised {
          description
            "If set the prefix to which this Prefix-SID is attached has been propagated by the router from either another level or from another protocol.";
          type boolean;
        }
        leaf node-sid {
          description
            "If set the prefix SID refers to the router identified by the prefix.";
          type boolean;
        }
        leaf penultimate-hop-popping {
          description
            "If set the penultimate hop MUST NOT pop the Prefix-SID before delivering the packet to the node that advertised the Prefix-SID.";
          type boolean;
        }
        leaf explicit-null {
          description
            "If set any upstream neighbor of the Prefix-SID originator MUST replace the Prefix-SID with a Prefix-SID that has an Explicit NULL value (0 for IPv4 and 2 for IPv6) before forwarding the packet";
          type boolean;
        }
        leaf value {
          description
            "If set then the Prefix-SID carries a value";
          type boolean;
        }
        leaf local {
          description
            "If set, then the value/index carried by the Prefix-SID has local significance.";
          type boolean;
        }
        leaf algorithm {
          description
            "Contains the identifier of the algorithm the router uses to compute the reachability of the prefix to which the Prefix-SID is associated";
          type enumeration {
            enum spf;
            enum strict-spf;
          }
        }
        leaf sr-index-or-label {
          description
            "An index representing an offset in the SID/label space advertised by the router or else a direct encoding of an MPLS label value.";
          type uint32;
        }
      }
      container prefix-attribute-flags {
        if-feature "srl-feat:traffic-engineering";
        description
          "Enter the prefix-attribute-flags context

           This sub-TLV supports the advertisement of additional flags associated with a given prefix advertisement.";
        leaf external-prefix {
          description
            "Set if the prefix has been redistributed from another protocol (or another IS-IS instance).";
          type boolean;
        }
        leaf re-advertised {
          description
            "Set when the prefix has been leaked from one level to another (upwards or downwards).";
          type boolean;
        }
        leaf node-identifier {
          description
            "Set when the prefix identifies the advertising router; i.e. it is a host prefix advertising a globally reachable address typically associated with a loopback address.";
          type boolean;
        }
      }
    }
  }

  grouping isis-adjacency-state {
    leaf neighbor-hostname {
      description
        "The hostname of the neighbor, as learned by TLV 137.";
      type string;
    }
    leaf-list area-address {
      description
        "Area address of the neighbor.";
      type srl_nokia-isis-types:isis-area-address;
    }
    leaf designated-is-system-id {
      description
        "System id of the designated IS router.";
      type srl_nokia-comm:isis-system-id;
    }
    leaf state {
      description
        "The current state of the adjacency.";
      type srl_nokia-isis-types:isis-interface-adj-state;
    }
    leaf down-reason {
      description
        "The reason why the adjacency is down.";
      type srl_nokia-isis-types:isis-adjacency-down-reason;
    }
    leaf remaining-holdtime {
      description
        "The time remaining until the hold timer will expire.";
      type uint16;
      units "seconds";
    }
    leaf remaining-adj-sid-holdtime {
      description
        "The remaining holding time for this adjacency-sid.";
      type uint16;
      units "seconds";
    }
    list adjacency-sid {
      description
        "List of adjacency Segment IDs.";
      config false;
      key "value";
      leaf value {
        description
          "Value of the Adj-SID.";
        type uint32;
      }
      leaf address-family {
        description
          "Address-family associated with the segment ID.";
        type srl_nokia-isis-types:isis-address-family;
      }
      leaf backup {
        description
          "Backup flag. When set, the Adj-SID refers to an adjacency being protected (e.g.: using IPFRR or MPLS-FRR).";
        type boolean;
      }
      leaf local {
        description
          "Local flag. When set, the value carried by the SID has local significance. By default the flag is SET.";
        type boolean;
      }
      leaf persistent {
        description
          "Persistent Flag. When set, the P-Flag indicates that the Adj-SID is persistently allocated.

           i.e., the Adj-SID value remains consistent across router restart and/or interface flap.";
        type boolean;
      }
      leaf set {
        description
          "Set flag. When set, the S-Flag indicates that the Adj-SID refers to a set of adjacencies.";
        type boolean;
      }
      leaf weight {
        description
          "Weight associated with the adjacency SID.";
        type uint8;
      }
    }
    leaf last-up-down-transition {
      description
        "The last time when the adjacency entered the up or down state.";
      type srl_nokia-comm:date-and-time-delta;
    }
    leaf up-down-transitions {
      description
        "The total number of transitions from Up state to a lower state, since the last clear.";
      type srl_nokia-comm:zero-based-counter32;
    }
    leaf neighbor-priority {
      description
        "The priority signalled by the neighbor to become the DIS on a LAN";
      type uint8 {
        range "0..127";
      }
    }
    leaf neighbor-circuit-type {
      description
        "The circuit type signalled by the neighbor.";
      type srl_nokia-isis-types:isis-level;
    }
    leaf neighbor-extended-circuit-id {
      description
        "Extended circuit ID assigned by the neighbor.";
      type srl_nokia-isis-types:isis-extended-circuit-id;
    }
    leaf neighbor-snpa {
      description
        "The SNPA of the neighbor.";
      type srl_nokia-isis-types:isis-snpa;
    }
    leaf local-extended-circuit-id {
      description
        "Local extended circuit ID.";
      type srl_nokia-isis-types:isis-extended-circuit-id;
    }
    leaf neighbor-ipv4 {
      description
        "The IPv4 address of the neighbor.";
      type srl_nokia-comm:ipv4-address;
    }
    leaf neighbor-ipv6 {
      description
        "The IPv6 address of the neighbor.";
      type srl_nokia-comm:ipv6-address;
    }
    leaf neighbor-restart-capable {
      description
        "Reads true when the neighbor has signalled that it is restart capable.";
      type boolean;
    }
    leaf neighbor-restart-status {
      description
        "The status of the neighbor with respect to graceful restart";
      type enumeration {
        enum not-helping;
        enum helping;
      }
    }
    leaf neighbor-restarts {
      description
        "The number of times the neighbor has restarted under protection of graceful restart.";
      type uint32;
    }
    leaf neighbor-last-restart {
      description
        "The last time the neighbor restarted under protection of graceful restart.";
      type union {
        type enumeration {
          enum never;
        }
        type srl_nokia-comm:date-and-time-delta;
      }
    }
    leaf-list nlpid {
      description
        "List of protocols supported by the adjacency.";
      type srl_nokia-isis-types:isis-protocols-supported;
    }
    leaf internal-idx {
      description
        "Extended circuit ID assigned by the neighbor.";
      type srl_nokia-isis-types:isis-internal-idx;
    }
  }

  grouping isis-interface-state {
    leaf oper-state {
      config false;
      description
        "The operational state of the IS-IS interface. This simply tracks the operational state of the subinterface.";
      type srl_nokia-comm:oper-state;
    }
    leaf circuit-id {
      config false;
      description
        "The circuit ID assigned by this IS-IS router to its interface.";
      type srl_nokia-isis-types:isis-extended-circuit-id;
    }
    container statistics {
      config false;
      description
        "Enter the statistics context

         Statistics associated with this IS-IS interface.";
      leaf adjacency-changes {
        description
          "Number of times an adjacency state change has occurred on this circuit(summed across all adjacencies).";
        type srl_nokia-comm:zero-based-counter32;
      }
      leaf adjacency-number {
        description
          "Number of adjacencies on this circuit.";
        type srl_nokia-comm:zero-based-counter32;
      }
      leaf authentication-failures {
        description
          "Number of times an IS-IS control PDU with the correct auth type has failed to pass authentication validation on the interface.";
        type srl_nokia-comm:zero-based-counter32;
      }
      leaf authentication-type-failures {
        description
          "Number of times an IS-IS control PDU with an auth type field different from that for this system has been received on the interface.";
        type srl_nokia-comm:zero-based-counter32;
      }
      leaf system-id-length-mismatches {
        description
          "Number of times an IS-IS control PDU with a system ID field length different from that for this system has been received on the interface.";
        type srl_nokia-comm:zero-based-counter32;
      }
      leaf designated-is-changes {
        description
          "Number of times the Designated IS has changed on this circuit.";
        type srl_nokia-comm:zero-based-counter32;
      }
      leaf max-area-address-mismatches {
        description
          "Number of times an IS-IS control PDU with a max area address field different from that for this system has been received on the interface.";
        type srl_nokia-comm:zero-based-counter32;
      }
      leaf rejected-adjacencies {
        description
          "Number of times an adjacency has been rejected on this circuit.";
        type srl_nokia-comm:zero-based-counter32;
      }
      leaf area-address-mismatches {
        description
          "Number of times an IS-IS L1 hello was received on this circuit with a area address field different from that for this system";
        type srl_nokia-comm:zero-based-counter32;
      }
    }
    list adjacency {
      config false;
      description
        "List of adjacencies formed through this interface.";
      key "neighbor-system-id adjacency-level";
      uses isis-adjacency-key;
      uses isis-adjacency-state;
    }
  }

  grouping isis-nsf-config {
    container non-stop-forwarding {
      description
        "Enter the non-stop-forwarding context

         Container to configure non-stop-forwarding";
      leaf admin-state {
        description
          "Used to administratively enable or disable the IS-IS non-stop forwarding functionality.";
        type srl_nokia-comm:admin-state;
        default "disable";
      }
    }
  }

  grouping isis-top {
    container isis {
      presence "Configure ISIS";
      must "not(../../srl_nokia-netinst:type = 'srl_nokia-netinst:mac-vrf')" {
        error-message "ISIS routing configuration is not possible on network-instance of type mac-vrf";
      }
      must "../../srl_nokia-netinst:type != 'srl_nokia-netinst:host'" {
        error-message "ISIS routing configuration is not possible on network-instance of type host";
      }
      uses isis-nsf-config {
        if-feature "srl-feat:isis-nsf";
      }
      uses isis-protocol-segment-routing {
        if-feature "srl-feat:label-management";
      }
      description
        "Top-level configuration and operational state for Intermediate System to Intermediate System (ISIS)";
      list instance {
        description
          "List of IS-IS protocol instances associated with this network-instance

           Multiple IS-ISIS instances are supported";
        key "name";
        uses isis-inst-key;
        uses isis-inst-config;
        uses isis-inst-common-state;
        uses isis-inst-mpls-segment-routing {
          if-feature "srl-feat:label-management";
        }
        uses inst-traffic-engineering-config {
          if-feature "srl-feat:traffic-engineering";
        }
        list interface {
          description
            "List of IS-IS interfaces";
          key "interface-name";
          unique "segment-routing/mpls/ipv4-node-sid/index";
          unique "segment-routing/mpls/ipv6-node-sid/index";
          uses isis-interface-key;
          uses isis-interface-config;
          uses isis-interface-state;
          uses srl_nokia-ldp:ldp-sync-interface;
        }
        list level {
          description
            "List of IS-IS levels supported by this IS (router)";
          max-elements 2;
          key "level-number";
          uses isis-level-key;
          uses isis-level-config;
          uses isis-level-stats;
          must "(((level-number = 1) and (../level-capability != 'L2')) or
                 ((level-number = 2) and (../level-capability != 'L1')))" {
            error-message "Level configuration must match the instance level-capability";
          }
          uses srl_nokia-isis-lsdb:new-link-state-database;
        }
        container hostnames {
          description
            "Enter the hostnames context

             Container to list hostnames along with their associated system ID";
          config false;
          list system-id {
            description
              "List of system IDs that have discovered hostnames.";
            key "host-system-id";
            leaf host-system-id {
              description
                "The system ID";
              type srl_nokia-comm:isis-system-id;
            }
            leaf hostname {
              description
                "The hostname of the system.";
              type string;
            }
          }
        }
      }
    }
  }

  grouping adj-sid-common {
    leaf assignment {
      description
        "The method that should be used to allocate an adjacency SID or multiple adjacency SIDs for this interface.

         This overrides the top level configuration to assign dynamic adjacency SIDs to all interfaces.";
      type enumeration {
        enum static {
          description
            "The user will statically configure an adjacency SID for the interface. This option is not available if the interface type is not point-to-point.";
        }
        enum dynamic {
          description
            "IS-IS should dynamically allocate one or more dynamic adjacency SIDs for this interface.";
        }
        enum none {
          description
            "No adjacency SIDs should be allocated for this interface.";
        }
      }
      must "boolean(../../../../../../dynamic-label-block) or (. != 'dynamic')" {
        error-message "Dynamic adj sid-s can be supported only when the Dynamic SRLB is configured.";
      }
      must "boolean(../static) or (. != 'static')" {
        error-message "Static Label must be allocated if assignment type is static.";
      }
    }
    leaf static {
      description
        "Configure a static adjacency SID represented by an MPLS label value.";
      type srl_nokia-comm:mpls-label-non-reserved;
      must "../assignment = 'static'" {
        error-message "Static value not permitted unless assignment method is configured as static.";
      }
      must '(current() <= (/srl-system:system/srl_nokia-mplslbl:mpls/srl_nokia-mplslbl:label-ranges/srl_nokia-mplslbl:static[srl_nokia-mplslbl:name=current()/../../../../../segment-routing/mpls/static-label-block]/srl_nokia-mplslbl:end-label))' {
        error-message "Label value is out of static label block's range";
      }
      must '(current() >= (/srl-system:system/srl_nokia-mplslbl:mpls/srl_nokia-mplslbl:label-ranges/srl_nokia-mplslbl:static[srl_nokia-mplslbl:name=current()/../../../../../segment-routing/mpls/static-label-block]/srl_nokia-mplslbl:start-label))' {
        error-message "Label value is out of static label block's range";
      }
      must "../../../../circuit-type = 'point-to-point'" {
        error-message "Static Adjacency SID configuration is allowed only on p2p interfaces";
      }
    }
  }

  grouping isis-sid-database {
    container sid-database {
      config false;
      description
        "Enter the sid-database context

         Database of all prefix SIDs associated with the IS-IS instance.";
      list prefix-sid {
        description
          "List of prefix SIDs";
        key "prefix sid-label-value multi-topology-id algorithm";
        leaf prefix {
          description
            "The IPv4 or IPv6 prefix associated with the SID.";
          type srl_nokia-comm:ip-prefix;
        }
        leaf sid-label-value {
          description
            "The MPLS label value associated with the SID.";
          type srl_nokia-comm:mpls-label-non-reserved;
        }
        leaf multi-topology-id {
          description
            "The multi-topology ID that provided the prefix SID";
          type uint16 {
            range "0..4095";
          }
        }
        leaf algorithm {
          description
            "Contains the identifier of the algorithm the router uses to compute the reachability of the prefix to which the Prefix-SID is associated";
          type uint8;
        }
        leaf active {
          description
            "When false, the prefix SID is inactive.

             It could be inactive for any of these reasons:
             -  it is involved in a prefix or SID conflict and lost to some other entry in the scope of this IS-IS instance
             -  its SID index or label is out of range of the locally defined SRGB";
          type boolean;
        }
        leaf prefix-conflict {
          type boolean;
          description
            "Reads true when the prefix SID entry is involved in a prefix conflict within the scope of this IS-IS instance. This occurs when there are multiple entries for the same (prefix, multi-topology-id, algorithm). All the conflicting entries become inactive except for the one with the smallest sid-index.";
        }
        leaf sid-conflict {
          type boolean;
          description
            "Reads true when the prefix SID entry is involved in a SID conflict within the scope of this IS-IS instance. This occurs when the same SID has been assigned to different prefixes after first eliminating entries that have lost the prefix-conflict comparison. All entries involved in a SID conflict that do not have the absolute lowest 'preference' value become inactive. In the SRL implementation SID entries associated with interfaces of this IS-IS instance are considered to have a lower numerical preference than remote prefix-sid entries. If there are still SID conflicts then all the remaining conflicting entries become inactive except for the one with the smallest sid-index.";
        }
        leaf sid-out-of-range {
          type boolean;
          description
            "Reads true when a received prefix SID from another router has a SID index or label value that is not within the locally defined SRGB range of the network instance; the prefix SID entry will be inactive.";
        }
        list source-router {
          key "system-id level-number";
          description
            "The ISIS routers that provided the prefix SID. (Multiple in the case of redistribution.)";
          leaf system-id {
            type srl_nokia-comm:isis-system-id;
            description
              "The system-id of an ISIS router that originated or redistributed the prefix SID";
          }
          leaf level-number {
            type srl_nokia-isis-types:isis-level-number;
            description
              "The level of the LSP that advertises the prefix SID";
          }
          leaf local-system {
            type boolean;
            description
              "True when the system ID belongs to the local system.";
          }
          container flags {
            description
              "Enter the flags context

               Flags that characterize the prefix SID";
            leaf re-advertised {
              description
                "If set the prefix to which this Prefix-SID is attached was propagated from another level or from another protocol.";
              type boolean;
            }
            leaf node-sid {
              description
                "If set the prefix SID refers to the router identified by the prefix.";
              type boolean;
            }
            leaf penultimate-hop-popping {
              description
                "If set the penultimate hop MUST NOT pop the Prefix-SID before delivering the packet to the node that advertised the Prefix-SID.";
              type boolean;
            }
            leaf explicit-null {
              description
                "If set any upstream neighbor of the Prefix-SID originator MUST replace the Prefix-SID with a Prefix-SID that has an Explicit NULL value (0 for IPv4 and 2 for IPv6) before forwarding the packet";
              type boolean;
            }
            leaf local {
              description
                "If set, then the value/index carried by the Prefix-SID has local significance.";
              type boolean;
            }
          }
        }
      }
    }
  }

  grouping micro-loop-avoidance {
    description
      "Grouping for micro-loop-avoidance functionality";
    container micro-loop-avoidance {
      description
        "Enter the micro-loop-avoidance context

         Enable the micro-loop-avoidance context";
      leaf admin-state {
        description
          "When set, micro-loop-avoidance is enabled for
           the ISIS instance.";
        type srl_nokia-comm:admin-state;
        default "disable";
        must "(. = 'disable') or (../../../../../../srl_nokia-netinst:type = 'srl_nokia-netinst:default')" {
          error-message "micro-loop-avoidance is supported only in the default network instance";
        }
      }
      leaf fib-delay {
        description
          "FIB delay before programming new primary next-hops";
        type uint32 {
          range "1..300";
        }
        units "deciseconds";
        default "15";
      }
      container remaining-fib-delay {
        config false;
        description
          "Enter the remaining-fib-delay context

           Remaining FIB delay before programming new primary next-hops.
           specified per topology (e.g., mt0 and mt2).";
        leaf mt0 {
          config false;
          description
            "Remaining FIB delay for topology mt0.";
          type uint32 {
            range "1..300";
          }
          units "deciseconds";
        }
        leaf mt2 {
          config false;
          description
            "Remaining FIB delay for topology mt2.";
          type uint32 {
            range "1..300";
          }
          units "deciseconds";
        }
      }
    }
  }

  grouping isis-topology-state {
    container topology {
      config false;
      description
        "Enter the topology context

         This context enters IS-IS topology state information.";
      list path {
        key "topology isis-level system-id";
        description
          "IS-IS IP path and optional LFA backup info, per topology.";
        leaf topology {
          description
            "Multi-Topology Identifier (MT-ID) associated with the path.";
          type srl_nokia-isis-types:isis-routing-topology;
        }
        leaf isis-level {
          description
            "Specifies the IS-IS protocol level to which this path attributes are applied.";
          type srl_nokia-isis-types:isis-level;
        }
        leaf system-id {
          description
            "System ID of the IS-IS node";
          type string;
        }
        leaf interface {
          description
            "Outgoing interface to reach the primary nexthop";
          type srl_nokia-comm:subinterface-all;
        }
        leaf nexthop {
          description
            "Primary nexthop system ID";
          type union {
            type srl_nokia-comm:isis-system-id;
            type string;
          }
        }
        leaf metric {
          description
            "The metric towards the remote system-id";
          type srl_nokia-isis-types:isis-wide-metric;
        }
        leaf lfa-interface {
          description
            "LFA backup outgoing interface (if available)";
          type srl_nokia-comm:subinterface-all;
        }
        leaf lfa-nexthop {
          description
            "LFA backup nexthop system ID (if available)";
          type union {
            type srl_nokia-comm:isis-system-id;
            type string;
          }
        }
        leaf lfa-metric {
          description
            "The metric using lfa towards the remote system-id";
          type srl_nokia-isis-types:isis-wide-metric;
        }
      }
    }
  }

  grouping lsp-stats-resource-allocation-status {
    leaf resource-allocation {
      type enumeration {
        enum success {
          description
            "Counter resource allocation succeeded";
        }
        enum failed {
          description
            "Counter resource allocation failed";
        }
      }
      description
        "Indication whether resource allocation succeeded or failed for the set of counters";
    }
  }

  augment "/srl_nokia-netinst:network-instance/srl_nokia-netinst:protocols" {
    uses isis-top;
  }
}
