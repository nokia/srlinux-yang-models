module srl_nokia-bridge-table-static-mac {
  yang-version 1.1;
  namespace "urn:nokia.com:srlinux:l2-static-mac:bridge-table-static-mac";
  prefix srl_nokia-bridge-table-static-mac;

  import srl_nokia-common {
    prefix srl_nokia-comm;
  }
  import srl_nokia-extensions {
    prefix srl_nokia-ext;
  }
  import srl_nokia-network-instance {
    prefix srl_nokia-netinst;
  }

  organization
    "Nokia";
  contact
    "Nokia SR Linux Support
     Web: <http://www.nokia.com>";
  description
    "This yang file gives a description of bridge table static-mac configuration.";

  revision 2026-07-31 {
    description
      "SRLinux 26.7.1";
  }
  revision 2024-10-31 {
    description
      "SRLinux 24.10.1";
  }
  revision 2024-03-31 {
    description
      "SRLinux 24.3.1";
  }
  revision 2023-03-31 {
    description
      "SRLinux 23.3.1";
  }
  revision 2020-06-30 {
    description
      "SRLinux 20.6.1";
  }

  grouping bridge-table-static-mac-top {
    container static-mac {
      list mac {
        key "address";
        description
          "static macs configured on the bridging instance";
        leaf address {
          type srl_nokia-comm:mac-address;
          srl_nokia-ext:show-importance "high";
        }
        leaf destination {
          type union {
            type enumeration {
              enum blackhole {
                value 0;
              }
            }
            type srl_nokia-comm:subinterface-all;
            type srl_nokia-comm:name;
          }
          mandatory true;
          must ". = 'blackhole' or (not(starts-with(.,'irb')))" {
            error-message "Must be blackhole or existing network-instance ethernet interface or lag name";
          }
          srl_nokia-ext:show-importance "high";
          description
            "The destination against which the mac is programmed

             This parameter is mandatory and may be configured as a subinterface, a blackhole or a connection-point.
             When a connection-point is configured as destination, the name of the connection-point is given
             as input, as follows: 'destination <name>'.";
        }
      }
      description
        "Enter the static-mac context";
    }
  }

  augment "/srl_nokia-netinst:network-instance/srl_nokia-netinst:bridge-table" {
    uses bridge-table-static-mac-top;
  }
}
