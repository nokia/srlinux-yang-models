module srl_nokia-bgp-evpn-bgp-instance-mpls-bridge-table-statistics {
  yang-version 1.1;
  namespace "urn:nokia.com:srlinux:l2-mac:bgp-evpn-bgp-instance-mpls-bridge-table-statistics";
  prefix srl_nokia-bgp-evpn-bgp-instance-mpls-bt-statistics;

  import srl_nokia-common {
    prefix srl_nokia-comm;
  }
  import srl_nokia-network-instance {
    prefix srl_nokia-netinst;
  }
  import srl_nokia-extensions {
    prefix srl_nokia-ext;
  }
  import srl_nokia-bgp-evpn {
    prefix srl_bgp-evpn;
  }

  organization
    "Nokia";
  contact
    "Nokia SR Linux Support
     Web: <http://www.nokia.com>";
  description
    "Model for bridge-table unicast destinations on the bgp-evpn mpls instance";

  revision 2026-07-31 {
    description
      "SRLinux 26.7.1";
  }
  revision 2022-03-31 {
    description
      "SRLinux 22.3.1";
  }

  grouping evpn-mpls-bridge-table-statistics-top {
    description
      "Statistics related to the bridge-table.";
    container statistics {
      config false;
      leaf active-entries {
        type srl_nokia-comm:zero-based-counter64;
        description
          "The total number of entries that are active on the evpn-mpls instance.";
        srl_nokia-ext:show-importance "high";
      }
      leaf total-entries {
        type srl_nokia-comm:zero-based-counter64;
        description
          "The total number of macs, active and inactive, on the evpn-mpls instance.";
        srl_nokia-ext:show-importance "high";
      }
      leaf failed-entries {
        type srl_nokia-comm:zero-based-counter64;
        description
          "The total number of macs, which have not been programmed on at least one slot.";
        srl_nokia-ext:show-importance "high";
      }
      list mac-type {
        key "type";
        description
          "The type of the mac on the evpn-mpls instance.";
        leaf type {
          type srl_nokia-comm:mac-type;
          srl_nokia-ext:show-importance "high";
        }
        leaf active-entries {
          type srl_nokia-comm:zero-based-counter64;
          description
            "The total number of entries of this type on the evpn-mpls instance.";
          srl_nokia-ext:show-importance "high";
        }
        leaf total-entries {
          type srl_nokia-comm:zero-based-counter64;
          description
            "The total number of macs of this type, active and inactive, on the evpn-mpls instance.";
          srl_nokia-ext:show-importance "high";
        }
        leaf failed-entries {
          type srl_nokia-comm:zero-based-counter64;
          description
            "The total number of macs of this type, which have not been programmed on at least one slot";
          srl_nokia-ext:show-importance "high";
        }
      }
      description
        "Enter the statistics context";
    }
  }

  augment "/srl_nokia-netinst:network-instance/srl_nokia-netinst:protocols/srl_nokia-netinst:bgp-evpn/srl_bgp-evpn:bgp-instance/srl_bgp-evpn:mpls/srl_bgp-evpn:bridge-table" {
    uses evpn-mpls-bridge-table-statistics-top;
  }
}
