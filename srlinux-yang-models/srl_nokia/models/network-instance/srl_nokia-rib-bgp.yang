module srl_nokia-rib-bgp {
  yang-version 1.1;
  namespace "urn:nokia.com:srlinux:bgp:rib-bgp";
  prefix srl_nokia-rib-bgp-routes;

  import ietf-yang-types {
    prefix yang;
  }
  import srl_nokia-common {
    prefix srl_nokia-comm;
  }
  import srl_nokia-extensions {
    prefix srl_nokia-ext;
  }
  import srl_nokia-network-instance {
    prefix srl_nokia-netinst;
  }
  import srl_nokia-features {
    prefix srl-feat;
  }
  import srl_nokia-ip-route-tables {
    prefix srl_nokia-rt;
  }
  import srl_nokia-srv6-types {
    prefix srl_nokia-srv6-types;
  }

  organization
    "Nokia";
  contact
    "Nokia SR Linux Support
     Web: <http://www.nokia.com>";
  description
    "This yang file models the state held by the BGP RIB databases.";

  revision 2026-07-31 {
    description
      "SRLinux 26.7.1";
  }
  revision 2026-03-31 {
    description
      "SRLinux 26.3.1";
  }
  revision 2025-10-31 {
    description
      "SRLinux 25.10.1";
  }
  revision 2025-07-31 {
    description
      "SRLinux 25.7.1";
  }
  revision 2025-03-31 {
    description
      "SRLinux 25.3.1";
  }
  revision 2024-10-31 {
    description
      "SRLinux 24.10.1";
  }
  revision 2024-07-31 {
    description
      "SRLinux 24.7.1";
  }
  revision 2024-03-31 {
    description
      "SRLinux 24.3.1";
  }
  revision 2023-10-31 {
    description
      "SRLinux 23.10.1";
  }
  revision 2023-07-31 {
    description
      "SRLinux 23.7.1";
  }
  revision 2023-03-31 {
    description
      "SRLinux 23.3.1";
  }
  revision 2022-11-30 {
    description
      "SRLinux 22.11.1";
  }
  revision 2022-03-31 {
    description
      "SRLinux 22.3.1";
  }
  revision 2021-06-30 {
    description
      "SRLinux 21.6.1";
  }
  revision 2021-03-31 {
    description
      "SRLinux 21.3.1";
  }
  revision 2020-06-30 {
    description
      "SRLinux 20.6.1";
  }
  revision 2019-11-30 {
    description
      "SRLinux 19.11.1";
  }

  identity prefix-sid-tlv-type {
    description
      "Base identity for a prefix SID TLV type.";
  }

  identity label-index {
    base prefix-sid-tlv-type;
    description
      "Label index TLV";
  }

  identity srgb-originator {
    base prefix-sid-tlv-type;
    description
      "SRGB originator TLV";
  }

  identity srv6-l3-service {
    base prefix-sid-tlv-type;
    description
      "SRv6 L3 service (TLV 5)";
    reference
      "RFC9252: BGP Overlay Services Based on Segment Routing over IPv6 (SRv6)";
  }

  identity srv6-l2-service {
    base prefix-sid-tlv-type;
    description
      "SRv6 L2 service (TLV 6)";
    reference
      "RFC9252: BGP Overlay Services Based on Segment Routing over IPv6 (SRv6)";
  }

  identity tunnel-encapsulation-attribute-tlv-type {
    description
      "Base identity for a tunnel-encapsulation attribute tunnel-type";
  }

  identity l2tpv3-over-ip {
    base tunnel-encapsulation-attribute-tlv-type;
    description
      "L2TPv3 tunnel (type 1)";
  }

  identity gre {
    base tunnel-encapsulation-attribute-tlv-type;
    description
      "GRE tunnel (type 2)";
  }

  identity ip-in-ip {
    base tunnel-encapsulation-attribute-tlv-type;
    description
      "IP-in-IP tunnel (type 7)";
  }

  identity vxlan {
    base tunnel-encapsulation-attribute-tlv-type;
    description
      "VXLAN tunnel (type 8)";
  }

  identity nvgre {
    base tunnel-encapsulation-attribute-tlv-type;
    description
      "NVGRE tunnel (type 9)";
  }

  identity mpls {
    base tunnel-encapsulation-attribute-tlv-type;
    description
      "MPLS tunnel (type 10)";
  }

  identity mpls-in-gre {
    base tunnel-encapsulation-attribute-tlv-type;
    description
      "MPLS in GRE tunnel (type 11)";
  }

  identity vxlan-gpe {
    base tunnel-encapsulation-attribute-tlv-type;
    description
      "VXLAN-GPE tunnel (type 12)";
  }

  identity mpls-in-udp {
    base tunnel-encapsulation-attribute-tlv-type;
    description
      "MPLS-in-UDP tunnel (type 13)";
  }

  identity ipv6 {
    base tunnel-encapsulation-attribute-tlv-type;
    description
      "IPv6 tunnel (type 14)";
  }

  identity srte-policy {
    base tunnel-encapsulation-attribute-tlv-type;
    description
      "SRTE policy tunnel (type 15)";
  }

  identity bare {
    base tunnel-encapsulation-attribute-tlv-type;
    description
      "Bare tunnel (type 16)";
  }

  identity cloud-security {
    base tunnel-encapsulation-attribute-tlv-type;
    description
      "Cloud security tunnel (type 18)";
  }

  identity geneve {
    base tunnel-encapsulation-attribute-tlv-type;
    description
      "Geneve tunnel (type 19)";
  }

  identity any-encap {
    base tunnel-encapsulation-attribute-tlv-type;
    description
      "Any-encapsulation tunnel (type 20)";
  }

  identity gtp {
    base tunnel-encapsulation-attribute-tlv-type;
    description
      "GTP tunnel (type 21)";
  }

  identity dynamic-path-selection-tunnel {
    base tunnel-encapsulation-attribute-tlv-type;
    description
      "DPS tunnel (type 22)";
  }

  identity originating-pe {
    base tunnel-encapsulation-attribute-tlv-type;
    description
      "OPE tunnel (type 23)";
  }

  identity dynamic-path-selection-policy {
    base tunnel-encapsulation-attribute-tlv-type;
    description
      "DPS policy (type 24)";
  }

  identity sdwan-hybrid {
    base tunnel-encapsulation-attribute-tlv-type;
    description
      "SDWAN-Hybrid tunnel (type 25)";
  }

  identity x-over-udp {
    base tunnel-encapsulation-attribute-tlv-type;
    description
      "X-over-UDP tunnel (type 26)";
  }

  identity distributed-etherlink-switch {
    base tunnel-encapsulation-attribute-tlv-type;
    description
      "DES tunnel (type 27)";
  }

  identity tunnel-encapsulation-attribute-subtlv-type {
    description
      "Base identity for a tunnel-encapsulation attribute subTLV";
  }

  identity encapsulation {
    base tunnel-encapsulation-attribute-subtlv-type;
    description
      "Encapsulation subTLV (type 1)";
  }

  identity protocol-type {
    base tunnel-encapsulation-attribute-subtlv-type;
    description
      "Protocol type subTLV (type 2)";
  }

  identity color {
    base tunnel-encapsulation-attribute-subtlv-type;
    description
      "Color subTLV (type 4)";
  }

  identity load-balancing-block {
    base tunnel-encapsulation-attribute-subtlv-type;
    description
      "Load balancing block subTLV (type 5)";
  }

  identity tunnel-egress-endpoint {
    base tunnel-encapsulation-attribute-subtlv-type;
    description
      "Tunnel egress endpoint subTLV (type 6)";
  }

  identity ds-field {
    base tunnel-encapsulation-attribute-subtlv-type;
    description
      "DS field subTLV (type 7)";
  }

  identity udp-dest-port {
    base tunnel-encapsulation-attribute-subtlv-type;
    description
      "UDP destination port subTLV (type 8)";
  }

  identity embedded-label-handling {
    base tunnel-encapsulation-attribute-subtlv-type;
    description
      "Embedded label handling subTLV (type 9)";
  }

  identity mpls-label-stack {
    base tunnel-encapsulation-attribute-subtlv-type;
    description
      "MPLS label stack subTLV (type 10)";
  }

  identity prefix-sid {
    base tunnel-encapsulation-attribute-subtlv-type;
    description
      "Prefix SID subTLV (type 11)";
  }

  identity preference {
    base tunnel-encapsulation-attribute-subtlv-type;
    description
      "Preference subTLV (type 12)";
  }

  identity binding-sid {
    base tunnel-encapsulation-attribute-subtlv-type;
    description
      "Binding SID subTLV (type 13)";
  }

  identity explicit-null-label-policy {
    base tunnel-encapsulation-attribute-subtlv-type;
    description
      "ENLP subTLV (type 14)";
  }

  identity priority {
    base tunnel-encapsulation-attribute-subtlv-type;
    description
      "Priority subTLV (type 15)";
  }

  identity spi {
    base tunnel-encapsulation-attribute-subtlv-type;
    description
      "SPI subTLV (type 16)";
  }

  identity srv6-binding-sid {
    base tunnel-encapsulation-attribute-subtlv-type;
    description
      "SRv6 binding SID subTLV (type 20)";
  }

  identity segment-list {
    base tunnel-encapsulation-attribute-subtlv-type;
    description
      "Segment list subTLV (type 128)";
  }

  identity srte-policy-candidate-path-name {
    base tunnel-encapsulation-attribute-subtlv-type;
    description
      "SRTE policy candidate path name subTLV (type 129)";
  }

  identity srte-policy-name {
    base tunnel-encapsulation-attribute-subtlv-type;
    description
      "SRTE policy name subTLV (type 130)";
  }

  typedef route-target-prefix {
    description
      "An RTC prefix in the format number1:number2/length, where number1 is an IPv4 address or a 2-byte ASN or a 4-byte ASN, number2 is a 2-byte or 4-byte administrative value and length is a number of bits between 0 and 96

       The default RTC prefix is represented by 0:0/0";
    srl_nokia-ext:generated-class-name "InterfaceName";
    type string;
  }

  typedef label-type {
    type enumeration {
      enum mpls-label {
        value 1;
      }
      enum vni {
        value 2;
      }
      enum transposed-srv6-function {
        value 3;
      }
    }
    description
      "The type of label encoded in the label field of an EVPN route or EVPN attribute

       The value depends on whether the route is received or advertised for an MPLS service
       (in which case the type will be mpls-label), for a VXLAN service (vni or VXLAN Network
       Identifier) or an SRv6 service where the function value is transposed into a label
       field (transposed-srv6-function).";
  }

  grouping full-mpls-label {
    container mpls {
      leaf label-value {
        description
          "MPLS label value";
        type srl_nokia-comm:mpls-label-non-reserved;
      }
      leaf traffic-class {
        description
          "MPLS traffic class";
        type uint8 {
          range "0..7";
        }
      }
      leaf bottom-of-stack {
        description
          "Bottom of stack flag";
        type boolean;
      }
      leaf time-to-live {
        description
          "MPLS TTL value";
        type uint8;
      }
      description
        "Enter the mpls context";
    }
  }

  grouping complete-srv6-sid {
    leaf complete-srv6-sid {
      if-feature "srl-feat:srv6";
      description
        "The entire 128 bit srv6 segment identifier included in srv6 routes

         It shows the complete srv6 sid value including locator, function and argument, even if transposition is
         used and the function or argument is encoded in the label field.";
      type srl_nokia-comm:ipv6-address;
    }
  }

  grouping state-common-key {
    leaf prefix {
      type srl_nokia-comm:ip-prefix;
    }
    leaf neighbor {
      description
        "If the route was learned from a BGP neighbor, this is the IPv4 or IPv6 address of that neighbor.";
      type srl_nokia-comm:ip-address-with-zone;
    }
    leaf path-id {
      description
        "Path identifier of the BGP route";
      type uint32;
    }
  }

  grouping state-common-local-rib-key {
    leaf prefix {
      type srl_nokia-comm:ip-prefix;
    }
    leaf neighbor {
      description
        "If the route was learned from a BGP neighbor, this is the IPv4 or IPv6 address of that neighbor.";
      type srl_nokia-comm:ip-address-with-zone;
    }
    leaf origin-protocol {
      description
        "If the route was imported from another protocol, this is the protocol name.";
      type identityref {
        base srl_nokia-comm:ip-route-type;
      }
    }
    leaf path-id {
      description
        "Path identifier of the BGP route";
      type uint32;
    }
  }

  grouping rtc-key {
    leaf origin-as {
      type srl_nokia-comm:as-number;
      description
        "The origin AS of the RTC route";
    }
    leaf route-target-prefix {
      type route-target-prefix;
      description
        "The RTC prefix in the format number1:number2/length, where number1 is an IPv4 address or a 2-byte ASN or a 4-byte ASN, number2 is a 2-byte or 4-byte administrative value and length is a number of bits between 0 and 96

         The default RTC prefix is represented by 0:0/0";
    }
    leaf neighbor {
      description
        "If the route was learned from a BGP neighbor, this is the IPv4 or IPv6 address of that neighbor.";
      type srl_nokia-comm:ip-address-with-zone;
    }
    leaf path-id {
      description
        "Path identifier of the BGP route";
      type uint32;
    }
  }

  grouping srte-policy-common-key {
    leaf distinguisher {
      description
        "Unique identifier of the policy candidate path in the context of <color, endpoint> tuple";
      type uint32;
    }
    leaf color {
      description
        "Color of the SRTE policy, used to steer traffic into the tunnel";
      type uint32;
    }
    leaf endpoint {
      description
        "The endpoint IPv4 or IPv6 address of the SR policy";
      type srl_nokia-comm:ip-address;
    }
    leaf neighbor {
      description
        "If the route was learned from a BGP neighbor, this is the IPv4 or IPv6 address of that neighbor";
      type srl_nokia-comm:ip-address-with-zone;
    }
    leaf path-id {
      description
        "Path identifier of the BGP route";
      type uint32;
    }
  }

  typedef link-state-nlri-type {
    type enumeration {
      enum node {
        value 1;
      }
      enum link {
        value 2;
      }
      enum ipv4-topology-prefix {
        value 3;
      }
      enum ipv6-topology-prefix {
        value 4;
      }
      enum sr-policy-candidate-path {
        value 5;
      }
      enum srv6-sid {
        value 6;
      }
    }
    description
      "The link-state NLRI type.";
  }

  grouping link-state-nlri-common-key {
    leaf nlri-type {
      description
        "Type of the link-state nlri.";
      type link-state-nlri-type;
    }
    leaf crc {
      description
        "CRC value calculated over the encoded nlri.";
      type uint32;
    }
    leaf nlri-length {
      description
        "Length of the encoded link-state nlri.";
      type uint32;
    }
    leaf nlri {
      description
        "Encoded link-state nlri.";
      type yang:hex-string;
    }
  }

  grouping link-state-common-key {
    uses link-state-nlri-common-key;
    leaf neighbor {
      description
        "If the route was learned from a BGP neighbor, this is the IPv4 or IPv6 address of that neighbor";
      type srl_nokia-comm:ip-address-with-zone;
    }
    leaf path-id {
      description
        "Path identifier of the BGP route";
      type uint32;
    }
  }

  grouping link-state-common-local-rib-key {
    uses link-state-nlri-common-key;
    leaf neighbor {
      description
        "If the route was learned from a BGP neighbor, this is the IPv4 or IPv6 address of that neighbor";
      type srl_nokia-comm:ip-address-with-zone;
    }
    leaf origin-protocol {
      description
        "If the route was imported from another protocol, this is the protocol name.";
      type identityref {
        base srl_nokia-comm:ip-route-type;
      }
    }
    leaf path-id {
      description
        "Path identifier of the BGP route";
      type uint32;
    }
  }

  grouping link-state-common {
    leaf-list nlri-string {
      description
        "Link-state nlri.";
      type string {
        length "80";
      }
      max-elements 30;
    }
  }

  grouping flowspec-v1-nlri-common-key {
    leaf crc {
      description
        "CRC value calculated over the encoded nlri.";
      type uint32;
    }
    leaf nlri-length {
      description
        "Length of the encoded flowspec nlri.";
      type uint32;
    }
    leaf nlri {
      description
        "Encoded flowspec nlri.";
      type yang:hex-string;
    }
  }

  grouping flowspec-v1-common-key {
    uses flowspec-v1-nlri-common-key;
    leaf neighbor {
      description
        "If the route was learned from a BGP neighbor, this is the IPv4 or IPv6 address of that neighbor";
      type srl_nokia-comm:ip-address-with-zone;
    }
    leaf path-id {
      description
        "Path identifier of the BGP route";
      type uint32;
    }
  }

  grouping flowspec-v1-common-local-rib-key {
    uses flowspec-v1-nlri-common-key;
    leaf neighbor {
      description
        "If the route was learned from a BGP neighbor, this is the IPv4 or IPv6 address of that neighbor";
      type srl_nokia-comm:ip-address-with-zone;
    }
    leaf origin-protocol {
      description
        "If the route was imported from another protocol, this is the protocol name.";
      type identityref {
        base srl_nokia-comm:ip-route-type;
      }
    }
    leaf path-id {
      description
        "Path identifier of the BGP route";
      type uint32;
    }
  }

  grouping flowspec-v1-nlri-components {
    container nlri-components {
      config false;
      description
        "Enter the nlri-components context

         Decoded FlowSpec NLRI operands: one leaf per RFC 8955 / 8956 component type (empty when absent). Raw NLRI hex is only at route level (flowspec-v1-common nlri-raw).";
      leaf destination-prefix {
        config false;
        description
          "Destination prefix component (decoded operands).";
        type string {
          length "0..256";
        }
      }
      leaf source-prefix {
        config false;
        description
          "Source prefix component (decoded operands).";
        type string {
          length "0..256";
        }
      }
      leaf ip-protocol {
        config false;
        description
          "IP protocol / next-header (decoded operands).";
        type string {
          length "0..256";
        }
      }
      leaf port {
        config false;
        description
          "Port component (decoded operands).";
        type string {
          length "0..256";
        }
      }
      leaf destination-port {
        config false;
        description
          "Destination port component (decoded operands).";
        type string {
          length "0..256";
        }
      }
      leaf source-port {
        config false;
        description
          "Source port component (decoded operands).";
        type string {
          length "0..256";
        }
      }
      leaf icmp-type {
        config false;
        description
          "ICMP type component (decoded operands).";
        type string {
          length "0..256";
        }
      }
      leaf icmp-code {
        config false;
        description
          "ICMP code component (decoded operands).";
        type string {
          length "0..256";
        }
      }
      leaf tcp-flags {
        config false;
        description
          "TCP flags component (decoded operands).";
        type string {
          length "0..256";
        }
      }
      leaf packet-length {
        config false;
        description
          "Packet length component (decoded operands).";
        type string {
          length "0..256";
        }
      }
      leaf dscp-mark {
        config false;
        description
          "DSCP / traffic-class component (decoded operands).";
        type string {
          length "0..256";
        }
      }
      leaf fragment {
        config false;
        description
          "Fragment component (decoded operands).";
        type string {
          length "0..256";
        }
      }
      leaf flow-label {
        config false;
        description
          "IPv6 flow label component (decoded operands).";
        type string {
          length "0..256";
        }
      }
    }
  }

  grouping flowspec-v1-common {
    description
      "Route-level NLRI, raw and components.";
    leaf-list nlri-raw {
      config false;
      description
        "FlowSpec NLRI raw data as hex string chunks.";
      type string {
        length "256";
      }
      max-elements 30;
    }
    uses flowspec-v1-nlri-components;
  }

  grouping state-routes-common {
    leaf last-modified {
      description
        "Time of the last modification of the route stored in the BGP RIB. For a route learned from a BGP neighbor the initial value is the same as last-update received. If an import policy later changed some attribute of the route last-modified would be updated to reflect the time of this change.";
      type srl_nokia-comm:date-and-time-delta;
    }
    leaf used-route {
      description
        "Indicates true if the route is being used for forwarding.";
      type boolean;
    }
    leaf unused-weight-only {
      if-feature "srl-feat:evpn-ifl-gw-ip";
      description
        "Indicates true if the route is unused, but being used for weight calculation";
      type boolean;
    }
    leaf valid-route {
      description
        "Indicates true if the route is valid.";
      type boolean;
    }
    leaf best-route {
      description
        "Set to true if the route is the BGP best path for the prefix.";
      type boolean;
    }
    leaf backup-route {
      description
        "Set to true if the route is being used as backup path for the prefix.";
      type boolean;
    }
    leaf stale-route {
      description
        "Set to true if the route is stale due to BGP graceful restart.";
      type boolean;
    }
    leaf fib-disabled {
      if-feature "srl-feat:routing-policy-bgp-disable-fib";
      description
        "Set to true if the route cannot be installed in the FIB via explicit configuration or other conditions";
      type boolean;
    }
    leaf pending-delete {
      description
        "Set to true if the route is marked for deletion.";
      type boolean;
    }
    leaf neighbor-as {
      type srl_nokia-comm:as-number;
      description
        "The last external AS to advertise the route into the local AS";
    }
    leaf group-best {
      type boolean;
      description
        "Set to true if the route is the best BGP route amongst all routes received from one particular neighbor AS";
    }
    leaf tie-break-reason {
      description
        "Indicates the reason why a BGP route is sorted behind the next best route. The BGP best path displays a value of 'none'.";
      type enumeration {
        enum unknown {
          value -1;
        }
        enum none {
          value 0;
        }
        enum origin {
          value 1;
        }
        enum as-path-length {
          value 2;
        }
        enum next-hop-cost {
          value 3;
        }
        enum med {
          value 4;
        }
        enum local-pref {
          value 5;
        }
        enum aggregate {
          value 6;
        }
        enum originator-id {
          value 7;
        }
        enum cluster-list {
          value 9;
        }
        enum extended-community {
          value 10;
        }
        enum aigp {
          value 11;
        }
        enum missing-attribute {
          value 12;
        }
        enum rtm-pref {
          value 13;
        }
        enum owner {
          value 14;
        }
        enum eigp-labeled {
          value 15;
        }
        enum vpn-route {
          value 16;
        }
        enum ebgp-route {
          value 17;
        }
        enum peer-ip {
          value 18;
        }
        enum local-peer {
          value 19;
        }
        enum multi-path {
          value 20;
        }
        enum vpn-rd {
          value 21;
        }
        enum next-hop-type {
          value 22;
        }
        enum invalid-route {
          value 23;
        }
        enum origin-validation {
          value 24;
        }
        enum long-live-gr-stale {
          value 25;
        }
        enum default-originate {
          value 26;
        }
        enum fib-install-disabled {
          value 27;
        }
        enum peer-router-id {
          value 28;
        }
        enum path-identifier {
          value 29;
        }
        enum domain-path-length {
          value 30;
        }
      }
    }
    container invalid-reason {
      leaf rejected-route {
        description
          "Indicates true if the route was rejected by an import policy.";
        type boolean;
      }
      leaf as-loop {
        description
          "Indicates true if the BGP route has an AS path loop that exceeds the configured threshold.";
        type boolean;
      }
      leaf next-hop-unresolved {
        description
          "Indicates true if the BGP route has a BGP next-hop that cannot be resolved to an outgoing interface.";
        type boolean;
      }
      leaf cluster-loop {
        description
          "Indicates true if the BGP route has a cluster-list loop.";
        type boolean;
      }
      leaf label-allocation-failed {
        description
          "Indicates true if dynamic-label-block has no more free labels";
        type boolean;
      }
      leaf fib-programming-failed {
        description
          "Indicates true if FIB programming failed";
        type boolean;
      }
      leaf domain-path-loop {
        if-feature "srl-feat:bgp-domain-path";
        description
          "Indicates true if the route has a D-PATH with a domain-id that matches one of the local domain-ids";
        type boolean;
      }
      leaf flowspec-validation-failed {
        if-feature "srl-feat:bgp-flowspec-v1";
        description
          "Indicates true if the destination prefix in the flowspec route is invalid";
        type boolean;
      }
      leaf flowspec-unsupported-match {
        if-feature "srl-feat:bgp-flowspec-v1";
        description
          "Indicates true if the nlri match in the flowspec route is unsupported";
        type boolean;
      }
      leaf flowspec-unsupported-action {
        if-feature "srl-feat:bgp-flowspec-v1";
        description
          "Indicates true if the action in the flowspec route's extended communities is unsupported";
        type boolean;
      }
      description
        "Enter the invalid-reason context";
    }
    container route-flap-damping {
      if-feature "srl-feat:bgp-route-flap-damping";
      description
        "Enter the route-flap-damping context

         Route flap damping state";
      leaf suppressed {
        description
          "Reads true when a non-withdrawn route is suppressed because FOM > suppress-threshold";
        type boolean;
      }
      leaf history {
        description
          "Reads true when the current FOM for a recently withdrawn route is greater than 0";
        type boolean;
      }
      leaf decayed {
        description
          "Reads true when the current FOM for a non-withdrawn route is greater than 0 but less than the suppress-threshold";
        type boolean;
      }
      leaf figure-of-merit {
        description
          "The current accumulated (and decayed) penalty value that determines whether the route is suppressed or not";
        type uint16;
      }
      leaf reuse-time {
        description
          "The amount of time remaining before a suppressed route can be used again

           This reads 0 if the route is not current suppressed.";
        type uint16;
        units "seconds";
      }
      leaf flap-count {
        description
          "The number of times that the route flapped";
        type uint32;
      }
    }
  }

  grouping ng-mvpn-route {
    leaf attr-id {
      description
        "Leaf reference to networkinstance/protocols/bgp/rib/attr-sets/attr-set/index";
      type leafref {
        path "/srl_nokia-netinst:network-instance/srl_nokia-rib-bgp-routes:bgp-rib/srl_nokia-rib-bgp-routes:attr-sets/srl_nokia-rib-bgp-routes:attr-set/srl_nokia-rib-bgp-routes:index";
      }
    }
  }

  grouping ng-mvpn-intra-as-ipmsi-ad {
    description
      "RFC6514 INTRA-AS IPMSI A-D Route Type NLRI

       To participate in the MVPN auto-discovery and binding, a PE router originates an Intra-AS I-PMSI A-D route.";
    leaf route-distinguisher {
      description
        "The route distinguisher encoded in the NLRI";
      type srl_nokia-comm:route-distinguisher;
    }
    leaf originating-router {
      description
        "The IPv4 or IPv6 address of the originating router";
      type srl_nokia-comm:ip-address;
    }
    leaf neighbor {
      description
        "If the route was learned from a BGP neighbor, this is the IPv4 or IPv6 address of that neighbor";
      type srl_nokia-comm:ip-address-with-zone;
    }
    leaf path-id {
      description
        "Path identifier of the BGP route";
      type uint32;
    }
  }

  grouping ng-mvpn-spmsi-ad {
    description
      "RFC6514 SPMSI A-D Route Type NLRI

       A PE can switches a C-tree from a shared tree to a selective tree via the S-PMSI route.
       This switch can happen based on threshold like bandwidth of a C-tree going beyond a certain threshold.";
    leaf route-distinguisher {
      description
        "The route distinguisher encoded in the NLRI";
      type srl_nokia-comm:route-distinguisher;
    }
    leaf multicast-source-address {
      description
        "The multicast source IP address";
      type srl_nokia-comm:ip-address;
    }
    leaf multicast-group-address {
      description
        "The multicast group IP address";
      type srl_nokia-comm:ip-address;
    }
    leaf originating-router {
      description
        "The IPv4 or IPv6 address of the originating router";
      type srl_nokia-comm:ip-address;
    }
    leaf neighbor {
      description
        "If the route was learned from a BGP neighbor, this is the IPv4 or IPv6 address of that neighbor";
      type srl_nokia-comm:ip-address-with-zone;
    }
    leaf path-id {
      description
        "Path identifier of the BGP route";
      type uint32;
    }
  }

  grouping ng-mvpn-leaf-ad {
    description
      "RFC6514 leaf A-D Route Type NLRI

       Leaf A-D routes may be originated as a result of processing a received Inter-AS I-PMSI A-D route or S-PMSI A-D route.
       If a Leaf A-D route is originated as a result of processing one of the received routes specified in the previous paragraph,
       the RouteKey of the Leaf A-D route is set to the NLRI of the received route. This list is specifically for AD routes originated for spmsi-ad routes.";
    leaf spmsi-ad-route-distinguisher {
      description
        "The route distinguisher encoded in the NLRI";
      type srl_nokia-comm:route-distinguisher;
    }
    leaf spmsi-ad-multicast-source-address {
      description
        "The multicast source IP address";
      type srl_nokia-comm:ip-address;
    }
    leaf spmsi-ad-multicast-group-address {
      description
        "The multicast group IP address";
      type srl_nokia-comm:ip-address;
    }
    leaf spmsi-ad-originating-router {
      description
        "The IPv4 or IPv6 address of the originating router";
      type srl_nokia-comm:ip-address;
    }
    leaf originating-router {
      description
        "The IPv4 or IPv6 address of the originating router";
      type srl_nokia-comm:ip-address;
    }
    leaf neighbor {
      description
        "If the route was learned from a BGP neighbor, this is the IPv4 or IPv6 address of that neighbor";
      type srl_nokia-comm:ip-address-with-zone;
    }
    leaf path-id {
      description
        "Path identifier of the BGP route";
      type uint32;
    }
  }

  grouping ng-mvpn-source-active-ad {
    description
      "RFC6514 Source Active A-D Route Type NLRI

       As result of receiving a Source Tree Join C-multicast route for (C-S,C-G) from some other PE the local PE adds either the S-PMSI
       or the I-PMSI to the outgoing interface list of the (C-S,C-G) state, the local PE MUST originate a Source Active A-D route if the PE has not originated such route already. ";
    leaf route-distinguisher {
      description
        "The route distinguisher encoded in the NLRI";
      type srl_nokia-comm:route-distinguisher;
    }
    leaf multicast-source-address {
      description
        "The multicast source IP address";
      type srl_nokia-comm:ip-address;
    }
    leaf multicast-group-address {
      description
        "The multicast group IP address";
      type srl_nokia-comm:ip-address;
    }
    leaf neighbor {
      description
        "If the route was learned from a BGP neighbor, this is the IPv4 or IPv6 address of that neighbor";
      type srl_nokia-comm:ip-address-with-zone;
    }
    leaf path-id {
      description
        "Path identifier of the BGP route";
      type uint32;
    }
  }

  grouping ng-mvpn-c-multicast {
    description
      "RFC6514 A Shared Tree Join route and a Source Tree Join Route Type NLRI

       Whenever a C-PIM instance on a particular PE creates a new (C-S,C-G) state, and the selected upstream PE for C-S is not the local PE,
       then the local PE MUST originate a C-multicast route of type Source Tree Join.";
    leaf route-distinguisher {
      description
        "The route distinguisher encoded in the NLRI";
      type srl_nokia-comm:route-distinguisher;
    }
    leaf source-as {
      type srl_nokia-comm:as-number;
      description
        "Autonomous System (ASN) Identifier of the source AS";
    }
    leaf multicast-source-address {
      description
        "The multicast source IP address";
      type srl_nokia-comm:ip-address;
    }
    leaf multicast-group-address {
      description
        "The multicast group IP address";
      type srl_nokia-comm:ip-address;
    }
    leaf neighbor {
      description
        "If the route was learned from a BGP neighbor, this is the IPv4 or IPv6 address of that neighbor";
      type srl_nokia-comm:ip-address-with-zone;
    }
    leaf path-id {
      description
        "Path identifier of the BGP route";
      type uint32;
    }
  }

  grouping evpn-ethernet-ad-common {
    leaf route-distinguisher {
      description
        "The route distinguisher encoded in the NLRI";
      type srl_nokia-comm:route-distinguisher;
    }
    leaf esi {
      description
        "The Ethernet Segment Identifier encoded in the NLRI";
      type srl_nokia-comm:esi;
    }
    leaf ethernet-tag-id {
      description
        "The 32-bit Ethernet Tag ID encoded in the NLRI. The Ethernet Tag ID identifies a broadcast domain";
      type uint32;
    }
    leaf neighbor {
      description
        "If the route was learned from a BGP neighbor, this is the IPv4 or IPv6 address of that neighbor";
      type srl_nokia-comm:ip-address-with-zone;
    }
    leaf path-id {
      description
        "Path identifier of the BGP route";
      type uint32;
    }
    container label {
      description
        "Enter the label context

         The encoded label value and type in the EVPN NLRI";
      leaf value {
        description
          "The value of the label field

           If the route is an EVPN MPLS route, the mpls-label is read out of the 20-bit high order value.
           If the route is an EVPN VXLAN route, the vni is read out of the 24-bit value. If the route is
           an EVPN SRv6 route, this field is set to zero if no transposition is used and set to a non-zero
           value if transposition is used. For all the cases, if this is an Auto-Discovery per ES route,
           this leaf is set to zero.";
        type uint32 {
          range "0..16777215";
        }
      }
      leaf value-type {
        description
          "Whether the encoded label value is an mpls-label, a vni or a transposed function or argument";
        type label-type;
      }
    }
    uses complete-srv6-sid;
    leaf attr-id {
      description
        "Leaf reference to networkinstance/protocols/bgp/rib/attr-sets/attr-set/index.";
      type leafref {
        path "/srl_nokia-netinst:network-instance/srl_nokia-rib-bgp-routes:bgp-rib/srl_nokia-rib-bgp-routes:attr-sets/srl_nokia-rib-bgp-routes:attr-set/srl_nokia-rib-bgp-routes:index";
      }
    }
  }

  grouping evpn-mac-ip-common {
    leaf route-distinguisher {
      description
        "The route distinguisher encoded in the NLRI";
      type srl_nokia-comm:route-distinguisher;
    }
    leaf ethernet-tag-id {
      description
        "The 32-bit Ethernet Tag ID encoded in the NLRI. The Ethernet Tag ID identifies a broadcast domain.";
      type uint32;
    }
    leaf mac-length {
      description
        "MAC address length";
      type uint8 {
        range "0..48";
      }
      units "bits";
    }
    leaf mac-address {
      description
        "The MAC address";
      type srl_nokia-comm:mac-address;
    }
    leaf ip-address {
      description
        "The IP host address";
      type srl_nokia-comm:ip-address;
    }
    leaf neighbor {
      description
        "If the route was learned from a BGP neighbor, this is the IPv4 or IPv6 address of that neighbor";
      type srl_nokia-comm:ip-address-with-zone;
    }
    leaf path-id {
      description
        "Path identifier of the BGP route";
      type uint32;
    }
    leaf esi {
      description
        "The Ethernet Segment Identifier";
      type srl_nokia-comm:esi;
    }
    container label1 {
      description
        "Enter the label1 context

         The encoded label1 value (used for layer 2 services) and type in the EVPN NLRI";
      leaf value {
        description
          "The value of the label field

           If the route is an EVPN MPLS route, the mpls-label is read out of the 20-bit high order value.
           If the route is an EVPN VXLAN route, the vni is read out of the 24-bit value. If the route is
           an EVPN SRv6 route, this field is set to zero if no transposition is used and set to a non-zero
           value if transposition is used.";
        type uint32 {
          range "0..16777215";
        }
      }
      leaf value-type {
        description
          "Whether the encoded label value is an mpls-label, a vni or a transposed function or argument";
        type label-type;
      }
    }
    container label2 {
      description
        "Enter the label2 context

         The encoded label2 value (used for layer 3 services) and type in the EVPN NLRI";
      leaf value {
        description
          "The value of the label field

           If the route is an EVPN MPLS route, the mpls-label is read out of the 20-bit high order value.
           If the route is an EVPN VXLAN route, the vni is read out of the 24-bit value. If the route is
           an EVPN SRv6 route, this field is set to zero if no transposition is used and set to a non-zero
           value if transposition is used.";
        type uint32 {
          range "0..16777215";
        }
      }
      leaf value-type {
        description
          "Whether the encoded label value is an mpls-label, a vni or a transposed function or argument";
        type label-type;
      }
    }
    leaf complete-srv6-sid-layer2 {
      if-feature "srl-feat:srv6";
      description
        "The entire 128 bit srv6 segment identifier included in srv6 routes

         It shows the complete srv6 sid value including locator, function and argument, even if transposition is
         used and the function or argument is encoded in the label field.";
      type srl_nokia-comm:ipv6-address;
    }
    leaf complete-srv6-sid-layer3 {
      if-feature "srl-feat:srv6";
      description
        "The entire 128 bit srv6 segment identifier included in srv6 routes

         It shows the complete srv6 sid value including locator, function and argument, even if transposition is
         used and the function or argument is encoded in the label field.";
      type srl_nokia-comm:ipv6-address;
    }
    leaf attr-id {
      description
        "Leaf reference to networkinstance/protocols/bgp/rib/attr-sets/attr-set/index";
      type leafref {
        path "/srl_nokia-netinst:network-instance/srl_nokia-rib-bgp-routes:bgp-rib/srl_nokia-rib-bgp-routes:attr-sets/srl_nokia-rib-bgp-routes:attr-set/srl_nokia-rib-bgp-routes:index";
      }
    }
  }

  grouping evpn-imet-common {
    leaf route-distinguisher {
      description
        "The route distinguisher encoded in the NLRI";
      type srl_nokia-comm:route-distinguisher;
    }
    leaf ethernet-tag-id {
      description
        "The 32-bit Ethernet Tag ID encoded in the NLRI. The Ethernet Tag ID identifies a broadcast domain";
      type uint32;
    }
    leaf originating-router {
      description
        "The IPv4 or IPv6 address of the originating router";
      type srl_nokia-comm:ip-address;
    }
    leaf neighbor {
      description
        "If the route was learned from a BGP neighbor, this is the IPv4 or IPv6 address of that neighbor";
      type srl_nokia-comm:ip-address-with-zone;
    }
    leaf path-id {
      description
        "Path identifier of the BGP route";
      type uint32;
    }
    leaf attr-id {
      description
        "Leaf reference to networkinstance/protocols/bgp/rib/attr-sets/attr-set/index";
      type leafref {
        path "/srl_nokia-netinst:network-instance/srl_nokia-rib-bgp-routes:bgp-rib/srl_nokia-rib-bgp-routes:attr-sets/srl_nokia-rib-bgp-routes:attr-set/srl_nokia-rib-bgp-routes:index";
      }
    }
  }

  grouping evpn-es-common {
    leaf route-distinguisher {
      description
        "The route distinguisher encoded in the NLRI";
      type srl_nokia-comm:route-distinguisher;
    }
    leaf esi {
      description
        "The Ethernet Segment Identifier";
      type srl_nokia-comm:esi;
    }
    leaf originating-router {
      description
        "The IPv4 or IPv6 address of the originating router";
      type srl_nokia-comm:ip-address;
    }
    leaf neighbor {
      description
        "If the route was learned from a BGP neighbor, this is the IPv4 or IPv6 address of that neighbor";
      type srl_nokia-comm:ip-address-with-zone;
    }
    leaf path-id {
      description
        "Path identifier of the BGP route";
      type uint32;
    }
    leaf attr-id {
      description
        "Leaf reference to networkinstance/protocols/bgp/rib/attr-sets/attr-set/index";
      type leafref {
        path "/srl_nokia-netinst:network-instance/srl_nokia-rib-bgp-routes:bgp-rib/srl_nokia-rib-bgp-routes:attr-sets/srl_nokia-rib-bgp-routes:attr-set/srl_nokia-rib-bgp-routes:index";
      }
    }
  }

  grouping evpn-ip-common {
    leaf route-distinguisher {
      description
        "The route distinguisher encoded in the NLRI";
      type srl_nokia-comm:route-distinguisher;
    }
    leaf ethernet-tag-id {
      description
        "The 32-bit Ethernet Tag ID encoded in the NLRI. The Ethernet Tag ID identifies a broadcast domain";
      type uint32;
    }
    leaf ip-prefix-length {
      description
        "IP prefix length";
      type uint8 {
        range "0..128";
      }
      units "bits";
    }
    leaf ip-prefix {
      description
        "The IPv4 or IPv6 prefix";
      type srl_nokia-comm:ip-prefix;
    }
    leaf neighbor {
      description
        "If the route was learned from a BGP neighbor, this is the IPv4 or IPv6 address of that neighbor";
      type srl_nokia-comm:ip-address-with-zone;
    }
    leaf path-id {
      description
        "Path identifier of the BGP route";
      type uint32;
    }
    leaf esi {
      description
        "The Ethernet Segment Identifier";
      type srl_nokia-comm:esi;
    }
    leaf gateway-ip {
      description
        "An IP address that encodes an overlay index";
      type srl_nokia-comm:ip-address;
    }
    container label {
      description
        "Enter the label context

         The encoded label value and type in the EVPN NLRI";
      leaf value {
        description
          "The value of the label field

           If the route is an EVPN MPLS route, the mpls-label is read out of the 20-bit high order value.
           If the route is an EVPN VXLAN route, the vni is read out of the 24-bit value. If the route is
           an EVPN SRv6 route, this field is set to zero if no transposition is used and set to a non-zero
           value if transposition is used.";
        type uint32 {
          range "0..16777215";
        }
      }
      leaf value-type {
        description
          "Whether the encoded label value is an mpls-label, a vni or a transposed function or argument";
        type label-type;
      }
    }
    uses complete-srv6-sid;
    leaf attr-id {
      description
        "Leaf reference to networkinstance/protocols/bgp/rib/attr-sets/attr-set/index";
      type leafref {
        path "/srl_nokia-netinst:network-instance/srl_nokia-rib-bgp-routes:bgp-rib/srl_nokia-rib-bgp-routes:attr-sets/srl_nokia-rib-bgp-routes:attr-set/srl_nokia-rib-bgp-routes:index";
      }
    }
  }

  grouping evpn-smet-common {
    leaf route-distinguisher {
      description
        "The route distinguisher encoded in the NLRI";
      type srl_nokia-comm:route-distinguisher;
    }
    leaf ethernet-tag-id {
      description
        "The 32-bit Ethernet Tag ID encoded in the NLRI

         The Ethernet Tag ID identifies a broadcast domain";
      type uint32;
    }
    leaf multicast-source-length {
      description
        "The multicast source address length";
      type uint8 {
        range "0..128";
      }
      units "bits";
    }
    leaf multicast-source-address {
      description
        "The multicast source IP address";
      type srl_nokia-comm:ip-address;
    }
    leaf multicast-group-length {
      description
        "The multicast group address length";
      type uint8 {
        range "0..128";
      }
      units "bits";
    }
    leaf multicast-group-address {
      description
        "The multicast group IP address";
      type srl_nokia-comm:ip-address;
    }
    leaf originating-router {
      description
        "The IPv4 or IPv6 address of the originating router";
      type srl_nokia-comm:ip-address;
    }
    container flags {
      description
        "Enter the flags context

         The SMET route Flags field in the NLRI";
      leaf igmp-mld-version-1 {
        description
          "When set to true, it indicates version 1

           When the route is used for IPv4, it refers to IGMP version 1. When used for IPv6, it refers
           to MLD version 1.";
        type boolean;
      }
      leaf igmp-mld-version-2 {
        description
          "When set to true, it indicates version 2

           When the route is used for IPv4, it refers to IGMP version 2. When used for IPv6, it refers
           to MLD version 2.";
        type boolean;
      }
      leaf igmp-version-3 {
        description
          "When set to true, it indicates version 3

           When the route is used for IPv4, it refers to IGMP version 3";
        type boolean;
      }
      leaf include-exclude-group-type {
        description
          "The Include/Exclude Group type bit

           Value 0 indicates Include Group type, and value 1 indicates Exclude Group type.";
        type enumeration {
          enum 0;
          enum 1;
        }
      }
    }
    leaf neighbor {
      description
        "If the route was learned from a BGP neighbor, this is the IPv4 or IPv6 address of that neighbor";
      type srl_nokia-comm:ip-address-with-zone;
    }
    leaf path-id {
      description
        "Path identifier of the BGP route";
      type uint32;
    }
    leaf attr-id {
      description
        "Leaf reference to networkinstance/protocols/bgp/rib/attr-sets/attr-set/index";
      type leafref {
        path "/srl_nokia-netinst:network-instance/srl_nokia-rib-bgp-routes:bgp-rib/srl_nokia-rib-bgp-routes:attr-sets/srl_nokia-rib-bgp-routes:attr-set/srl_nokia-rib-bgp-routes:index";
      }
    }
  }

  grouping evpn-multicast-membership-report-synch-common {
    leaf route-distinguisher {
      description
        "The route distinguisher encoded in the NLRI";
      type srl_nokia-comm:route-distinguisher;
    }
    leaf esi {
      description
        "The Ethernet Segment Identifier";
      type srl_nokia-comm:esi;
    }
    leaf ethernet-tag-id {
      description
        "The 32-bit Ethernet Tag ID encoded in the NLRI

         The Ethernet Tag ID identifies a broadcast domain.";
      type uint32;
    }
    leaf multicast-source-length {
      description
        "The multicast source address length";
      type uint8 {
        range "0..128";
      }
      units "bits";
    }
    leaf multicast-source-address {
      description
        "The multicast source IP address";
      type srl_nokia-comm:ip-address;
    }
    leaf multicast-group-length {
      description
        "The multicast group address length";
      type uint8 {
        range "0..128";
      }
      units "bits";
    }
    leaf multicast-group-address {
      description
        "The multicast group IP address";
      type srl_nokia-comm:ip-address;
    }
    leaf originating-router {
      description
        "The IPv4 or IPv6 address of the originating router";
      type srl_nokia-comm:ip-address;
    }
    container flags {
      description
        "Enter the flags context

         The Multicast Membership Report Synch route Flags field in the NLRI";
      leaf igmp-mld-version-1 {
        description
          "When set to true, it indicates version 1

           When the route is used for IPv4, it refers to IGMP version 1. When used for IPv6, it refers
           to MLD version 1.";
        type boolean;
      }
      leaf igmp-mld-version-2 {
        description
          "When set to true, it indicates version 2

           When the route is used for IPv4, it refers to IGMP version 2. When used for IPv6, it refers
           to MLD version 2.";
        type boolean;
      }
      leaf igmp-version-3 {
        description
          "When set to true, it indicates version 3

           When the route is used for IPv4, it refers to IGMP version 3.";
        type boolean;
      }
      leaf include-exclude-group-type {
        description
          "The Include/Exclude Group type bit

           Value 0 indicates Include Group type, and value 1 indicates Exclude Group type.";
        type enumeration {
          enum 0;
          enum 1;
        }
      }
    }
    leaf neighbor {
      description
        "If the route was learned from a BGP neighbor, this is the IPv4 or IPv6 address of that neighbor";
      type srl_nokia-comm:ip-address-with-zone;
    }
    leaf path-id {
      description
        "Path identifier of the BGP route";
      type uint32;
    }
    leaf attr-id {
      description
        "Leaf reference to networkinstance/protocols/bgp/rib/attr-sets/attr-set/index";
      type leafref {
        path "/srl_nokia-netinst:network-instance/srl_nokia-rib-bgp-routes:bgp-rib/srl_nokia-rib-bgp-routes:attr-sets/srl_nokia-rib-bgp-routes:attr-set/srl_nokia-rib-bgp-routes:index";
      }
    }
  }

  grouping evpn-multicast-leave-synch-common {
    leaf route-distinguisher {
      description
        "The route distinguisher encoded in the NLRI";
      type srl_nokia-comm:route-distinguisher;
    }
    leaf esi {
      description
        "The Ethernet Segment Identifier";
      type srl_nokia-comm:esi;
    }
    leaf ethernet-tag-id {
      description
        "The 32-bit Ethernet Tag ID encoded in the NLRI

         The Ethernet Tag ID identifies a broadcast domain.";
      type uint32;
    }
    leaf multicast-source-length {
      description
        "The multicast source address length";
      type uint8 {
        range "0..128";
      }
      units "bits";
    }
    leaf multicast-source-address {
      description
        "The multicast source IP address";
      type srl_nokia-comm:ip-address;
    }
    leaf multicast-group-length {
      description
        "The multicast group address length";
      type uint8 {
        range "0..128";
      }
      units "bits";
    }
    leaf multicast-group-address {
      description
        "The multicast group IP address";
      type srl_nokia-comm:ip-address;
    }
    leaf originating-router {
      description
        "The IPv4 or IPv6 address of the originating router";
      type srl_nokia-comm:ip-address;
    }
    leaf maximum-response-time {
      description
        "The value to be used while sending a query";
      type uint8;
      units "deciseconds";
    }
    container flags {
      description
        "Enter the flags context

         The Multicast Membership Report Synch route Flags field in the NLRI";
      leaf igmp-mld-version-1 {
        description
          "When set to true, it indicates version 1

           When the route is used for IPv4, it refers to IGMP version 1. When used for IPv6, it refers
           to MLD version 1.";
        type boolean;
      }
      leaf igmp-mld-version-2 {
        description
          "When set to true, it indicates version 2

           When the route is used for IPv4, it refers to IGMP version 2. When used for IPv6, it refers
           to MLD version 2.";
        type boolean;
      }
      leaf igmp-version-3 {
        description
          "When set to true, it indicates version 3

           When the route is used for IPv4, it refers to IGMP version 3.";
        type boolean;
      }
      leaf include-exclude-group-type {
        description
          "The Include/Exclude Group type bit

           Value 0 indicates Include Group type, and value 1 indicates Exclude Group type.";
        type enumeration {
          enum 0;
          enum 1;
        }
      }
    }
    leaf neighbor {
      description
        "If the route was learned from a BGP neighbor, this is the IPv4 or IPv6 address of that neighbor";
      type srl_nokia-comm:ip-address-with-zone;
    }
    leaf path-id {
      description
        "Path identifier of the BGP route";
      type uint32;
    }
    leaf attr-id {
      description
        "Leaf reference to networkinstance/protocols/bgp/rib/attr-sets/attr-set/index";
      type leafref {
        path "/srl_nokia-netinst:network-instance/srl_nokia-rib-bgp-routes:bgp-rib/srl_nokia-rib-bgp-routes:attr-sets/srl_nokia-rib-bgp-routes:attr-set/srl_nokia-rib-bgp-routes:index";
      }
    }
  }

  grouping srv6-sid-information-subtlv {
    container srv6-sid-information {
      when "../type = 'srl_nokia-srv6-types:srv6-sid-information'";
      description
        "Enter the srv6-sid-information context

         Service SID information";
      leaf sid-value {
        description
          "SRv6 SID";
        type srl_nokia-comm:ipv6-address;
      }
      leaf behavior {
        description
          "Endpoint behavior associated with the SRv6 SID";
        type identityref {
          base srl_nokia-srv6-types:srv6-service-endpoint-behavior;
        }
      }
      list sub-sub-tlv {
        key "type";
        description
          "List of sub-sub-TLV types of the SRv6 SID Information sub-TLV.";
        leaf type {
          type identityref {
            base srl_nokia-srv6-types:srv6-service-data-sub-sub-tlv-type;
          }
          description
            "The type of sub-sub-TLV being described. The type of sub-sub-TLV is expressed as a canonical name.";
        }
        container srv6-sid-structure {
          when "../type = 'srl_nokia-srv6-types:srv6-sid-structure-bgp'";
          description
            "Enter the srv6-sid-structure context

             SRv6 SID stricture information";
          leaf block-length {
            description
              "Length of the block part of the SRv6 SID";
            type uint8;
          }
          leaf node-length {
            description
              "Length of the node part of the SRv6 SID";
            type uint8;
          }
          leaf function-length {
            description
              "Length of the function part of the SRv6 SID";
            type uint8;
          }
          leaf argument-length {
            description
              "Length of the argument part of the SRv6 SID";
            type uint8;
          }
          leaf transposition-length {
            description
              "Number of bits taken out of the SRv6 SID value and encoded in the MPLS Label field";
            type uint8;
          }
          leaf transposition-offset {
            description
              "Position (from MSB) of the bits taken out of the SRv6 SID value and encoded in the MPLS Label field";
            type uint8;
          }
        }
      }
    }
  }

  grouping bgp-rib-top {
    container bgp-rib {
      config false;
      description
        "Enter the bgp-rib context

         Container for BGP RIB state";
      list afi-safi {
        key "afi-safi-name";
        description
          "List of address families with routes in the BGP RIB";
        leaf afi-safi-name {
          type identityref {
            base srl_nokia-comm:bgp-address-family;
          }
          description
            "The name of the address family";
        }
        container ipv4-unicast {
          description
            "Enter the ipv4-unicast context

             Container for RIB state of IPv4-unicast routes";
          container local-rib {
            description
              "Enter the local-rib context

               Container for local RIB, containing all imported routes from other protocols plus the post-import-policy version of all IPv4 routes learned from all BGP neighbors";
            list route {
              key "prefix neighbor origin-protocol path-id";
              description
                "List of IPv4 routes in the local RIB";
              uses state-common-local-rib-key;
              uses state-routes-common;
              leaf attr-id {
                description
                  "Leaf reference to networkinstance/bgp-rib/attr-sets/attr-set/index";
                type leafref {
                  path "../../../../../srl_nokia-rib-bgp-routes:attr-sets/srl_nokia-rib-bgp-routes:attr-set/srl_nokia-rib-bgp-routes:index";
                }
              }
            }
          }
          container rib-in-out {
            description
              "Enter the rib-in-out context

               Container for BGP routes learned and advertised to BGP neighbors";
            container rib-in-pre {
              description
                "Enter the rib-in-pre context

                 Container for the pre-import-policy version of BGP routes learned from BGP neighbors";
              list route {
                key "prefix neighbor path-id";
                description
                  "List of IPv4 routes";
                uses state-common-key;
                leaf attr-id {
                  description
                    "Leaf reference to networkinstance/protocols/bgp/rib/attr-sets/attr-set/index";
                  type leafref {
                    path "../../../../../../srl_nokia-rib-bgp-routes:attr-sets/srl_nokia-rib-bgp-routes:attr-set/srl_nokia-rib-bgp-routes:index";
                  }
                }
              }
            }
            container rib-in-post {
              description
                "Enter the rib-in-post context

                 Container for the post-import-policy version of BGP routes learned from BGP neighbors";
              list route {
                description
                  "List of IPv4 routes";
                key "prefix neighbor path-id";
                uses state-common-key;
                uses state-routes-common;
                leaf attr-id {
                  description
                    "Leaf reference to networkinstance/protocols/bgp/rib/attr-sets/attr-set/index";
                  type leafref {
                    path "../../../../../../srl_nokia-rib-bgp-routes:attr-sets/srl_nokia-rib-bgp-routes:attr-set/srl_nokia-rib-bgp-routes:index";
                  }
                }
                uses srl_nokia-rt:internal-tags;
              }
            }
            container rib-out-post {
              description
                "Enter the rib-out-post context

                 Container for the post-export-policy version of BGP routes advertised to BGP neighbors";
              list route {
                key "prefix neighbor path-id";
                description
                  "List of IPv4 routes";
                uses state-common-key;
                leaf attr-id {
                  description
                    "Leaf reference to networkinstance/protocols/bgp/rib/
                     attr-sets/attr-set/index";
                  type leafref {
                    path "../../../../../../srl_nokia-rib-bgp-routes:attr-sets/srl_nokia-rib-bgp-routes:attr-set/srl_nokia-rib-bgp-routes:index";
                  }
                }
              }
            }
          }
        }
        container ipv4-labeled-unicast {
          if-feature "srl-feat:bgp-labeled-unicast";
          description
            "Enter the ipv4-labeled-unicast context

             Container for RIB state of labeled IPv4-unicast routes";
          container local-rib {
            description
              "Enter the local-rib context

               Container for local RIB, containing all imported routes from other protocols plus the post-import-policy version of all label-IPv4 routes learned from all BGP neighbors";
            list route {
              key "prefix neighbor origin-protocol path-id";
              description
                "List of label-IPv4 routes in the local RIB";
              uses state-common-local-rib-key;
              uses state-routes-common;
              leaf-list received-mpls-label {
                max-elements 1;
                description
                  "Received MPLS label value";
                type srl_nokia-comm:mpls-label-with-implicit-and-explicit-null;
              }
              leaf attr-id {
                description
                  "Leaf reference to networkinstance/bgp-rib/attr-sets/attr-set/index";
                type leafref {
                  path "../../../../../srl_nokia-rib-bgp-routes:attr-sets/srl_nokia-rib-bgp-routes:attr-set/srl_nokia-rib-bgp-routes:index";
                }
              }
            }
          }
          container rib-in-out {
            description
              "Enter the rib-in-out context

               Container for BGP routes learned and advertised to BGP neighbors";
            container rib-in-pre {
              description
                "Enter the rib-in-pre context

                 Container for the pre-import-policy version of BGP routes learned from BGP neighbors";
              list route {
                key "prefix neighbor path-id";
                description
                  "List of IPv4 routes";
                uses state-common-key;
                leaf-list received-mpls-label {
                  max-elements 1;
                  description
                    "Received MPLS label value";
                  type srl_nokia-comm:mpls-label-with-implicit-and-explicit-null;
                }
                leaf attr-id {
                  description
                    "Leaf reference to networkinstance/protocols/bgp/rib/attr-sets/attr-set/index";
                  type leafref {
                    path "../../../../../../srl_nokia-rib-bgp-routes:attr-sets/srl_nokia-rib-bgp-routes:attr-set/srl_nokia-rib-bgp-routes:index";
                  }
                }
              }
            }
            container rib-in-post {
              description
                "Enter the rib-in-post context

                 Container for the post-import-policy version of BGP routes learned from BGP neighbors";
              list route {
                description
                  "List of IPv4 routes";
                key "prefix neighbor path-id";
                uses state-common-key;
                uses state-routes-common;
                leaf-list received-mpls-label {
                  max-elements 1;
                  description
                    "Received MPLS label value";
                  type srl_nokia-comm:mpls-label-with-implicit-and-explicit-null;
                }
                leaf attr-id {
                  description
                    "Leaf reference to networkinstance/protocols/bgp/rib/
                     attr-sets/attr-set/index";
                  type leafref {
                    path "../../../../../../srl_nokia-rib-bgp-routes:attr-sets/srl_nokia-rib-bgp-routes:attr-set/srl_nokia-rib-bgp-routes:index";
                  }
                }
                uses srl_nokia-rt:internal-tags;
              }
            }
            container rib-out-post {
              description
                "Enter the rib-out-post context

                 Container for the post-export-policy version of BGP routes advertised to BGP neighbors.";
              list route {
                key "prefix neighbor path-id";
                description
                  "List of IPv4 routes.";
                uses state-common-key;
                leaf-list advertised-mpls-label {
                  max-elements 1;
                  description
                    "Advertised MPLS label value";
                  type srl_nokia-comm:mpls-label-with-implicit-and-explicit-null;
                }
                leaf attr-id {
                  description
                    "Leaf reference to networkinstance/protocols/bgp/rib/attr-sets/attr-set/index.";
                  type leafref {
                    path "../../../../../../srl_nokia-rib-bgp-routes:attr-sets/srl_nokia-rib-bgp-routes:attr-set/srl_nokia-rib-bgp-routes:index";
                  }
                }
              }
            }
          }
        }
        container l3vpn-ipv4-unicast {
          if-feature "srl-feat:ipvpn";
          description
            "Enter the l3vpn-ipv4-unicast context

             Container for RIB state of VPN-IPv4 unicast routes.";
          container local-rib {
            description
              "Enter the local-rib context

               Container for local RIB

               Includes the post import-policy RIB-INs corresponding to VPN-IPv4 routes received from default net-instance BGP peers (post import-policy means after processing by the BGP import policy attached to the default net-instance peer and after processing by the vrf-import policy of importing IP VRF network instances) plus the post vrf-export policy “imported” routes from local IP-VRF network instances.";
            list route {
              key "route-distinguisher prefix neighbor path-id";
              description
                "List of VPN-IPv4 unicast routes in the local RIB.";
              leaf route-distinguisher {
                description
                  "The route distinguisher encoded in the NLRI.";
                type srl_nokia-comm:route-distinguisher;
              }
              uses state-common-key;
              uses state-routes-common;
              uses complete-srv6-sid;
              leaf-list imported-ip-vrf-network-instances {
                description
                  "List of IP-VRF network instances that imported the route";
                type leafref {
                  path "/srl_nokia-netinst:network-instance/srl_nokia-netinst:name";
                }
              }
              leaf-list dpath-looped-ip-vrf-network-instances {
                if-feature "srl-feat:bgp-domain-path";
                description
                  "List of IP-VRF network instances in which a loop due to the D-PATH attribute is detected";
                type leafref {
                  path "/srl_nokia-netinst:network-instance/srl_nokia-netinst:name";
                }
              }
              leaf-list received-mpls-label {
                max-elements 1;
                description
                  "Received MPLS label value";
                type srl_nokia-comm:mpls-label-with-implicit-and-explicit-null;
              }
              leaf attr-id {
                description
                  "Leaf reference to networkinstance/bgp-rib/attr-sets/attr-set/index";
                type leafref {
                  path "../../../../../srl_nokia-rib-bgp-routes:attr-sets/srl_nokia-rib-bgp-routes:attr-set/srl_nokia-rib-bgp-routes:index";
                }
              }
            }
          }
          container rib-in-out {
            description
              "Enter the rib-in-out context

               Container for BGP routes learned and advertised to BGP neighbors.";
            container rib-in-pre {
              description
                "Enter the rib-in-pre context

                 Container for the pre-import-policy version of BGP routes learned from BGP neighbors.";
              list route {
                key "route-distinguisher prefix neighbor path-id";
                description
                  "List of VPN-IPv4 unicast routes learned from BGP neighbors.";
                leaf route-distinguisher {
                  description
                    "The route distinguisher encoded in the NLRI.";
                  type srl_nokia-comm:route-distinguisher;
                }
                uses state-common-key;
                uses complete-srv6-sid;
                leaf-list imported-ip-vrf-network-instances {
                  description
                    "List of IP-VRF network instances that imported the route";
                  type leafref {
                    path "/srl_nokia-netinst:network-instance/srl_nokia-netinst:name";
                  }
                }
                leaf-list dpath-looped-ip-vrf-network-instances {
                  if-feature "srl-feat:bgp-domain-path";
                  description
                    "List of IP-VRF network instances in which a loop due to the D-PATH attribute is detected";
                  type leafref {
                    path "/srl_nokia-netinst:network-instance/srl_nokia-netinst:name";
                  }
                }
                leaf-list received-mpls-label {
                  max-elements 1;
                  description
                    "Received MPLS label value";
                  type srl_nokia-comm:mpls-label-with-implicit-and-explicit-null;
                }
                leaf attr-id {
                  description
                    "Leaf reference to networkinstance/protocols/bgp/rib/attr-sets/attr-set/index.";
                  type leafref {
                    path "../../../../../../srl_nokia-rib-bgp-routes:attr-sets/srl_nokia-rib-bgp-routes:attr-set/srl_nokia-rib-bgp-routes:index";
                  }
                }
              }
            }
            container rib-in-post {
              description
                "Enter the rib-in-post context

                 Container for the post-import-policy version of BGP routes learned from BGP neighbors.";
              list route {
                key "route-distinguisher prefix neighbor path-id";
                description
                  "List of VPN-IPv4 unicast routes";
                leaf route-distinguisher {
                  description
                    "The route distinguisher encoded in the NLRI.";
                  type srl_nokia-comm:route-distinguisher;
                }
                uses state-common-key;
                uses state-routes-common;
                uses complete-srv6-sid;
                leaf-list imported-ip-vrf-network-instances {
                  description
                    "List of IP-VRF network instances that imported the route";
                  type leafref {
                    path "/srl_nokia-netinst:network-instance/srl_nokia-netinst:name";
                  }
                }
                leaf-list dpath-looped-ip-vrf-network-instances {
                  if-feature "srl-feat:bgp-domain-path";
                  description
                    "List of IP-VRF network instances in which a loop due to the D-PATH attribute is detected";
                  type leafref {
                    path "/srl_nokia-netinst:network-instance/srl_nokia-netinst:name";
                  }
                }
                leaf-list received-mpls-label {
                  max-elements 1;
                  description
                    "Received MPLS label value";
                  type srl_nokia-comm:mpls-label-with-implicit-and-explicit-null;
                }
                leaf attr-id {
                  description
                    "Leaf reference to networkinstance/protocols/bgp/rib/
                     attr-sets/attr-set/index.";
                  type leafref {
                    path "../../../../../../srl_nokia-rib-bgp-routes:attr-sets/srl_nokia-rib-bgp-routes:attr-set/srl_nokia-rib-bgp-routes:index";
                  }
                }
                uses srl_nokia-rt:internal-tags;
              }
            }
            container rib-out-post {
              description
                "Enter the rib-out-post context

                 Container for the post-export-policy version of BGP routes advertised to BGP neighbors.";
              list route {
                key "route-distinguisher prefix neighbor path-id";
                description
                  "List of VPN-IPv4 unicast routes.";
                leaf route-distinguisher {
                  description
                    "The route distinguisher encoded in the NLRI.";
                  type srl_nokia-comm:route-distinguisher;
                }
                uses state-common-key;
                uses complete-srv6-sid;
                leaf-list advertised-mpls-label {
                  max-elements 1;
                  description
                    "Advertised MPLS label value";
                  type srl_nokia-comm:mpls-label-with-implicit-and-explicit-null;
                }
                leaf attr-id {
                  description
                    "Leaf reference to networkinstance/protocols/bgp/rib/attr-sets/attr-set/index.";
                  type leafref {
                    path "../../../../../../srl_nokia-rib-bgp-routes:attr-sets/srl_nokia-rib-bgp-routes:attr-set/srl_nokia-rib-bgp-routes:index";
                  }
                }
              }
            }
          }
        }
        container l3vpn-ipv6-unicast {
          if-feature "srl-feat:ipvpn";
          description
            "Enter the l3vpn-ipv6-unicast context

             Container for RIB state of VPN-IPv6 unicast routes.";
          container local-rib {
            description
              "Enter the local-rib context

               Container for local RIB

               Includes the post import-policy RIB-INs corresponding to VPN-IPv6 routes received from default net-instance BGP peers (post import-policy means after processing by the BGP import policy attached to the default net-instance peer and after processing by the vrf-import policy of importing IP VRF network instances) plus the post vrf-export policy “imported” routes from local IP-VRF network instances.";
            list route {
              key "route-distinguisher prefix neighbor path-id";
              description
                "List of VPN-IPv6 unicast routes in the local RIB.";
              leaf route-distinguisher {
                description
                  "The route distinguisher encoded in the NLRI.";
                type srl_nokia-comm:route-distinguisher;
              }
              uses state-common-key;
              uses state-routes-common;
              uses complete-srv6-sid;
              leaf-list imported-ip-vrf-network-instances {
                description
                  "List of IP-VRF network instances that imported the route";
                type leafref {
                  path "/srl_nokia-netinst:network-instance/srl_nokia-netinst:name";
                }
              }
              leaf-list dpath-looped-ip-vrf-network-instances {
                if-feature "srl-feat:bgp-domain-path";
                description
                  "List of IP-VRF network instances in which a loop due to the D-PATH attribute is detected";
                type leafref {
                  path "/srl_nokia-netinst:network-instance/srl_nokia-netinst:name";
                }
              }
              leaf-list received-mpls-label {
                max-elements 1;
                description
                  "Received MPLS label value";
                type srl_nokia-comm:mpls-label-with-implicit-and-explicit-null;
              }
              leaf attr-id {
                description
                  "Leaf reference to networkinstance/bgp-rib/attr-sets/attr-set/index";
                type leafref {
                  path "../../../../../srl_nokia-rib-bgp-routes:attr-sets/srl_nokia-rib-bgp-routes:attr-set/srl_nokia-rib-bgp-routes:index";
                }
              }
            }
          }
          container rib-in-out {
            description
              "Enter the rib-in-out context

               Container for BGP routes learned and advertised to BGP neighbors.";
            container rib-in-pre {
              description
                "Enter the rib-in-pre context

                 Container for the pre-import-policy version of BGP routes learned from BGP neighbors.";
              list route {
                key "route-distinguisher prefix neighbor path-id";
                description
                  "List of VPN-IPv6 unicast routes learned from BGP neighbors.";
                leaf route-distinguisher {
                  description
                    "The route distinguisher encoded in the NLRI.";
                  type srl_nokia-comm:route-distinguisher;
                }
                uses state-common-key;
                uses complete-srv6-sid;
                leaf-list imported-ip-vrf-network-instances {
                  description
                    "List of IP-VRF network instances that imported the route";
                  type leafref {
                    path "/srl_nokia-netinst:network-instance/srl_nokia-netinst:name";
                  }
                }
                leaf-list dpath-looped-ip-vrf-network-instances {
                  if-feature "srl-feat:bgp-domain-path";
                  description
                    "List of IP-VRF network instances in which a loop due to the D-PATH attribute is detected";
                  type leafref {
                    path "/srl_nokia-netinst:network-instance/srl_nokia-netinst:name";
                  }
                }
                leaf-list received-mpls-label {
                  max-elements 1;
                  description
                    "Received MPLS label value";
                  type srl_nokia-comm:mpls-label-with-implicit-and-explicit-null;
                }
                leaf attr-id {
                  description
                    "Leaf reference to networkinstance/protocols/bgp/rib/attr-sets/attr-set/index.";
                  type leafref {
                    path "../../../../../../srl_nokia-rib-bgp-routes:attr-sets/srl_nokia-rib-bgp-routes:attr-set/srl_nokia-rib-bgp-routes:index";
                  }
                }
              }
            }
            container rib-in-post {
              description
                "Enter the rib-in-post context

                 Container for the post-import-policy version of BGP routes learned from BGP neighbors.";
              list route {
                key "route-distinguisher prefix neighbor path-id";
                description
                  "List of VPN-IPv6 unicast routes";
                leaf route-distinguisher {
                  description
                    "The route distinguisher encoded in the NLRI.";
                  type srl_nokia-comm:route-distinguisher;
                }
                uses state-common-key;
                uses state-routes-common;
                uses complete-srv6-sid;
                leaf-list imported-ip-vrf-network-instances {
                  description
                    "List of IP-VRF network instances that imported the route";
                  type leafref {
                    path "/srl_nokia-netinst:network-instance/srl_nokia-netinst:name";
                  }
                }
                leaf-list dpath-looped-ip-vrf-network-instances {
                  if-feature "srl-feat:bgp-domain-path";
                  description
                    "List of IP-VRF network instances in which a loop due to the D-PATH attribute is detected";
                  type leafref {
                    path "/srl_nokia-netinst:network-instance/srl_nokia-netinst:name";
                  }
                }
                leaf-list received-mpls-label {
                  max-elements 1;
                  description
                    "Received MPLS label value";
                  type srl_nokia-comm:mpls-label-with-implicit-and-explicit-null;
                }
                leaf attr-id {
                  description
                    "Leaf reference to networkinstance/protocols/bgp/rib/
                     attr-sets/attr-set/index.";
                  type leafref {
                    path "../../../../../../srl_nokia-rib-bgp-routes:attr-sets/srl_nokia-rib-bgp-routes:attr-set/srl_nokia-rib-bgp-routes:index";
                  }
                }
                uses srl_nokia-rt:internal-tags;
              }
            }
            container rib-out-post {
              description
                "Enter the rib-out-post context

                 Container for the post-export-policy version of BGP routes advertised to BGP neighbors.";
              list route {
                key "route-distinguisher prefix neighbor path-id";
                description
                  "List of VPN-IPv6 unicast routes.";
                leaf route-distinguisher {
                  description
                    "The route distinguisher encoded in the NLRI.";
                  type srl_nokia-comm:route-distinguisher;
                }
                uses state-common-key;
                uses complete-srv6-sid;
                leaf-list advertised-mpls-label {
                  max-elements 1;
                  description
                    "Advertised MPLS label value";
                  type srl_nokia-comm:mpls-label-with-implicit-and-explicit-null;
                }
                leaf attr-id {
                  description
                    "Leaf reference to networkinstance/protocols/bgp/rib/attr-sets/attr-set/index.";
                  type leafref {
                    path "../../../../../../srl_nokia-rib-bgp-routes:attr-sets/srl_nokia-rib-bgp-routes:attr-set/srl_nokia-rib-bgp-routes:index";
                  }
                }
              }
            }
          }
        }
        container ipv6-unicast {
          description
            "Enter the ipv6-unicast context

             Container for RIB state of IPv6-unicast routes.";
          container local-rib {
            description
              "Enter the local-rib context

               Container for local RIB, containing all imported routes from other protocols plus the post-import-policy version of all IPv4 routes learned from all BGP neighbors.";
            list route {
              key "prefix neighbor origin-protocol path-id";
              description
                "List of IPv6 routes in the local RIB.";
              uses state-common-local-rib-key;
              uses state-routes-common;
              leaf attr-id {
                description
                  "Leaf reference to networkinstance/protocols/bgp/rib/attr-sets/attr-set/index";
                type leafref {
                  path "../../../../../srl_nokia-rib-bgp-routes:attr-sets/srl_nokia-rib-bgp-routes:attr-set/srl_nokia-rib-bgp-routes:index";
                }
              }
            }
          }
          container rib-in-out {
            description
              "Enter the rib-in-out context

               Container for BGP routes learned and advertised to BGP neighbors.";
            container rib-in-pre {
              description
                "Enter the rib-in-pre context

                 Container for the pre-import-policy version of BGP routes learned from BGP neighbors.";
              list route {
                key "prefix neighbor path-id";
                description
                  "List of IPv6 routes.";
                uses state-common-key;
                leaf attr-id {
                  description
                    "Leaf reference to networkinstance/protocols/bgp/rib/attr-sets/attr-set/index.";
                  type leafref {
                    path "../../../../../../srl_nokia-rib-bgp-routes:attr-sets/srl_nokia-rib-bgp-routes:attr-set/srl_nokia-rib-bgp-routes:index";
                  }
                }
              }
            }
            container rib-in-post {
              description
                "Enter the rib-in-post context

                 Container for the post-import-policy version of BGP routes learned from BGP neighbors.";
              list route {
                description
                  "List of IPv6 routes";
                key "prefix neighbor path-id";
                uses state-common-key;
                uses state-routes-common;
                leaf attr-id {
                  description
                    "Leaf reference to networkinstance/protocols/bgp/rib/attr-sets/attr-set/index.";
                  type leafref {
                    path "../../../../../../srl_nokia-rib-bgp-routes:attr-sets/srl_nokia-rib-bgp-routes:attr-set/srl_nokia-rib-bgp-routes:index";
                  }
                }
                uses srl_nokia-rt:internal-tags;
              }
            }
            container rib-out-post {
              description
                "Enter the rib-out-post context

                 Container for the post-export-policy version of BGP routes advertised to BGP neighbors.";
              list route {
                key "prefix neighbor path-id";
                description
                  "List of IPv6 routes.";
                uses state-common-key;
                leaf attr-id {
                  description
                    "Leaf reference to networkinstance/protocols/bgp/rib/attr-sets/attr-set/index.";
                  type leafref {
                    path "../../../../../../srl_nokia-rib-bgp-routes:attr-sets/srl_nokia-rib-bgp-routes:attr-set/srl_nokia-rib-bgp-routes:index";
                  }
                }
              }
            }
          }
        }
        container ipv6-labeled-unicast {
          if-feature "srl-feat:bgp-labeled-unicast";
          description
            "Enter the ipv6-labeled-unicast context

             Container for RIB state of labeled IPv6-unicast routes.";
          container local-rib {
            description
              "Enter the local-rib context

               Container for local RIB, containing all imported routes from other protocols plus the post-import-policy version of all label-IPv4 routes learned from all BGP neighbors.";
            list route {
              key "prefix neighbor origin-protocol path-id";
              description
                "List of label-IPv6 routes in the local RIB.";
              uses state-common-local-rib-key;
              uses state-routes-common;
              leaf-list received-mpls-label {
                max-elements 1;
                description
                  "Received MPLS label value";
                type srl_nokia-comm:mpls-label-with-implicit-and-explicit-null;
              }
              leaf attr-id {
                description
                  "Leaf reference to networkinstance/bgp-rib/attr-sets/attr-set/index";
                type leafref {
                  path "../../../../../srl_nokia-rib-bgp-routes:attr-sets/srl_nokia-rib-bgp-routes:attr-set/srl_nokia-rib-bgp-routes:index";
                }
              }
            }
          }
          container rib-in-out {
            description
              "Enter the rib-in-out context

               Container for BGP routes learned and advertised to BGP neighbors.";
            container rib-in-pre {
              description
                "Enter the rib-in-pre context

                 Container for the pre-import-policy version of BGP routes learned from BGP neighbors.";
              list route {
                key "prefix neighbor path-id";
                description
                  "List of label-IPv6 routes.";
                uses state-common-key;
                leaf-list received-mpls-label {
                  max-elements 1;
                  description
                    "Received MPLS label value";
                  type srl_nokia-comm:mpls-label-with-implicit-and-explicit-null;
                }
                leaf attr-id {
                  description
                    "Leaf reference to networkinstance/protocols/bgp/rib/attr-sets/attr-set/index.";
                  type leafref {
                    path "../../../../../../srl_nokia-rib-bgp-routes:attr-sets/srl_nokia-rib-bgp-routes:attr-set/srl_nokia-rib-bgp-routes:index";
                  }
                }
              }
            }
            container rib-in-post {
              description
                "Enter the rib-in-post context

                 Container for the post-import-policy version of BGP routes learned from BGP neighbors.";
              list route {
                description
                  "List of label-IPv6 routes";
                key "prefix neighbor path-id";
                uses state-common-key;
                uses state-routes-common;
                leaf-list received-mpls-label {
                  max-elements 1;
                  description
                    "Received MPLS label value";
                  type srl_nokia-comm:mpls-label-with-implicit-and-explicit-null;
                }
                leaf attr-id {
                  description
                    "Leaf reference to networkinstance/protocols/bgp/rib/attr-sets/attr-set/index.";
                  type leafref {
                    path "../../../../../../srl_nokia-rib-bgp-routes:attr-sets/srl_nokia-rib-bgp-routes:attr-set/srl_nokia-rib-bgp-routes:index";
                  }
                }
                uses srl_nokia-rt:internal-tags;
              }
            }
            container rib-out-post {
              description
                "Enter the rib-out-post context

                 Container for the post-export-policy version of BGP routes advertised to BGP neighbors.";
              list route {
                key "prefix neighbor path-id";
                description
                  "List of label-IPv6 routes.";
                uses state-common-key;
                leaf-list advertised-mpls-label {
                  max-elements 1;
                  description
                    "Advertised MPLS label value";
                  type srl_nokia-comm:mpls-label-with-implicit-and-explicit-null;
                }
                leaf attr-id {
                  description
                    "Leaf reference to networkinstance/protocols/bgp/rib/attr-sets/attr-set/index.";
                  type leafref {
                    path "../../../../../../srl_nokia-rib-bgp-routes:attr-sets/srl_nokia-rib-bgp-routes:attr-set/srl_nokia-rib-bgp-routes:index";
                  }
                }
              }
            }
          }
        }
        container ipv4-mvpn {
          if-feature "srl-feat:bgp-ipvx-mvpn";
          description
            "Enter the ipv4-mvpn context

             Container for RIB state of ipv4-mvpn routes.";
          container local-rib {
            description
              "Enter the local-rib context

               Ipv4-mvpn routes that are selected as the best route.
                This includes routes imported from other protocols.";
            list intra-as-ipmsi-ad-route {
              description
                "List of ng-mvpn intra-as inclusive pmsi auto-discovery routes";
              key "route-distinguisher originating-router neighbor path-id";
              uses ng-mvpn-intra-as-ipmsi-ad;
              uses state-routes-common;
              uses ng-mvpn-route;
            }
            list spmsi-ad-route {
              description
                "List of ng-mvpn intra-as selective pmsi auto-discovery routes";
              key "route-distinguisher multicast-source-address multicast-group-address originating-router neighbor path-id";
              uses ng-mvpn-spmsi-ad;
              uses state-routes-common;
              uses ng-mvpn-route;
            }
            list leaf-ad-route {
              description
                "List of ng-mvpn leaf ad routes";
              key "spmsi-ad-route-distinguisher spmsi-ad-multicast-source-address spmsi-ad-multicast-group-address spmsi-ad-originating-router originating-router neighbor path-id";
              uses ng-mvpn-leaf-ad;
              uses state-routes-common;
              uses ng-mvpn-route;
            }
            list source-active-ad-route {
              description
                "List of ng-mvpn source active ad routes";
              key "route-distinguisher multicast-source-address multicast-group-address neighbor path-id";
              uses ng-mvpn-source-active-ad;
              uses state-routes-common;
              uses ng-mvpn-route;
            }
            list shared-tree-join-route {
              description
                "List of ng-mvpn Shared Tree Join routes";
              key "route-distinguisher source-as multicast-source-address multicast-group-address neighbor path-id";
              uses ng-mvpn-c-multicast;
              uses state-routes-common;
              uses ng-mvpn-route;
            }
            list source-tree-join-route {
              description
                "List of ng-mvpn Source Tree Join routes";
              key "route-distinguisher source-as multicast-source-address multicast-group-address neighbor path-id";
              uses ng-mvpn-c-multicast;
              uses state-routes-common;
              uses ng-mvpn-route;
            }
          }
          container rib-in-out {
            description
              "Enter the rib-in-out context

               Container for BGP routes learned and advertised to BGP neighbors.";
            container rib-in-pre {
              list intra-as-ipmsi-ad-route {
                description
                  "List of ng-mvpn intra-as inclusive pmsi auto-discovery routes";
                key "route-distinguisher originating-router neighbor path-id";
                uses ng-mvpn-intra-as-ipmsi-ad;
                uses ng-mvpn-route;
              }
              list spmsi-ad-route {
                description
                  "List of ng-mvpn intra-as selective pmsi auto-discovery routes";
                key "route-distinguisher multicast-source-address multicast-group-address originating-router neighbor path-id";
                uses ng-mvpn-spmsi-ad;
                uses ng-mvpn-route;
              }
              list leaf-ad-route {
                description
                  "List of ng-mvpn leaf ad routes";
                key "spmsi-ad-route-distinguisher spmsi-ad-multicast-source-address spmsi-ad-multicast-group-address spmsi-ad-originating-router originating-router neighbor path-id";
                uses ng-mvpn-leaf-ad;
                uses ng-mvpn-route;
              }
              list source-active-ad-route {
                description
                  "List of ng-mvpn source active ad routes";
                key "route-distinguisher multicast-source-address multicast-group-address neighbor path-id";
                uses ng-mvpn-source-active-ad;
                uses ng-mvpn-route;
              }
              list shared-tree-join-route {
                description
                  "List of ng-mvpn Shared Tree Join routes";
                key "route-distinguisher source-as multicast-source-address multicast-group-address neighbor path-id";
                uses ng-mvpn-c-multicast;
                uses ng-mvpn-route;
              }
              list source-tree-join-route {
                description
                  "List of ng-mvpn Source Tree Join routes";
                key "route-distinguisher source-as multicast-source-address multicast-group-address neighbor path-id";
                uses ng-mvpn-c-multicast;
                uses ng-mvpn-route;
              }
              description
                "Enter the rib-in-pre context";
            }
            container rib-in-post {
              list intra-as-ipmsi-ad-route {
                description
                  "List of ng-mvpn intra-as inclusive pmsi auto-discovery routes";
                key "route-distinguisher originating-router neighbor path-id";
                uses ng-mvpn-intra-as-ipmsi-ad;
                uses state-routes-common;
                uses ng-mvpn-route;
              }
              list spmsi-ad-route {
                description
                  "List of ng-mvpn intra-as selective pmsi auto-discovery routes";
                key "route-distinguisher multicast-source-address multicast-group-address originating-router neighbor path-id";
                uses ng-mvpn-spmsi-ad;
                uses state-routes-common;
                uses ng-mvpn-route;
              }
              list leaf-ad-route {
                description
                  "List of ng-mvpn leaf ad routes";
                key "spmsi-ad-route-distinguisher spmsi-ad-multicast-source-address spmsi-ad-multicast-group-address spmsi-ad-originating-router originating-router neighbor path-id";
                uses ng-mvpn-leaf-ad;
                uses state-routes-common;
                uses ng-mvpn-route;
              }
              list source-active-ad-route {
                description
                  "List of ng-mvpn source active ad routes";
                key "route-distinguisher multicast-source-address multicast-group-address neighbor path-id";
                uses ng-mvpn-source-active-ad;
                uses state-routes-common;
                uses ng-mvpn-route;
              }
              list shared-tree-join-route {
                description
                  "List of ng-mvpn Shared Tree Join routes";
                key "route-distinguisher source-as multicast-source-address multicast-group-address neighbor path-id";
                uses ng-mvpn-c-multicast;
                uses state-routes-common;
                uses ng-mvpn-route;
              }
              list source-tree-join-route {
                description
                  "List of ng-mvpn Source Tree Join routes";
                key "route-distinguisher source-as multicast-source-address multicast-group-address neighbor path-id";
                uses ng-mvpn-c-multicast;
                uses state-routes-common;
                uses ng-mvpn-route;
              }
              description
                "Enter the rib-in-post context";
            }
            container rib-out-post {
              list intra-as-ipmsi-ad-route {
                description
                  "List of ng-mvpn intra-as inclusive pmsi auto-discovery routes";
                key "route-distinguisher originating-router neighbor path-id";
                uses ng-mvpn-intra-as-ipmsi-ad;
                uses ng-mvpn-route;
              }
              list spmsi-ad-route {
                description
                  "List of ng-mvpn intra-as selective pmsi auto-discovery routes";
                key "route-distinguisher multicast-source-address multicast-group-address originating-router neighbor path-id";
                uses ng-mvpn-spmsi-ad;
                uses ng-mvpn-route;
              }
              list leaf-ad-route {
                description
                  "List of ng-mvpn leaf ad routes";
                key "spmsi-ad-route-distinguisher spmsi-ad-multicast-source-address spmsi-ad-multicast-group-address spmsi-ad-originating-router originating-router neighbor path-id";
                uses ng-mvpn-leaf-ad;
                uses ng-mvpn-route;
              }
              list source-active-ad-route {
                description
                  "List of ng-mvpn source active ad routes";
                key "route-distinguisher multicast-source-address multicast-group-address neighbor path-id";
                uses ng-mvpn-source-active-ad;
                uses ng-mvpn-route;
              }
              list shared-tree-join-route {
                description
                  "List of ng-mvpn Shared Tree Join routes";
                key "route-distinguisher source-as multicast-source-address multicast-group-address neighbor path-id";
                uses ng-mvpn-c-multicast;
                uses ng-mvpn-route;
              }
              list source-tree-join-route {
                description
                  "List of ng-mvpn Source Tree Join routes";
                key "route-distinguisher source-as multicast-source-address multicast-group-address neighbor path-id";
                uses ng-mvpn-c-multicast;
                uses ng-mvpn-route;
              }
              description
                "Enter the rib-out-post context";
            }
          }
        }
        container ipv6-mvpn {
          if-feature "srl-feat:bgp-ipvx-mvpn";
          description
            "Enter the ipv6-mvpn context

             Container for RIB state of ipv6-mvpn routes.";
          container local-rib {
            description
              "Enter the local-rib context

               Ipv6-mvpn routes that are selected as the best route.
                This includes routes imported from other protocols.";
            list intra-as-ipmsi-ad-route {
              description
                "List of ng-mvpn intra-as inclusive pmsi auto-discovery routes";
              key "route-distinguisher originating-router neighbor path-id";
              uses ng-mvpn-intra-as-ipmsi-ad;
              uses state-routes-common;
              uses ng-mvpn-route;
            }
            list spmsi-ad-route {
              description
                "List of ng-mvpn intra-as selective pmsi auto-discovery routes";
              key "route-distinguisher multicast-source-address multicast-group-address originating-router neighbor path-id";
              uses ng-mvpn-spmsi-ad;
              uses state-routes-common;
              uses ng-mvpn-route;
            }
            list leaf-ad-route {
              description
                "List of ng-mvpn leaf ad routes";
              key "spmsi-ad-route-distinguisher spmsi-ad-multicast-source-address spmsi-ad-multicast-group-address spmsi-ad-originating-router originating-router neighbor path-id";
              uses ng-mvpn-leaf-ad;
              uses state-routes-common;
              uses ng-mvpn-route;
            }
            list source-active-ad-route {
              description
                "List of ng-mvpn source active ad routes";
              key "route-distinguisher multicast-source-address multicast-group-address neighbor path-id";
              uses ng-mvpn-source-active-ad;
              uses state-routes-common;
              uses ng-mvpn-route;
            }
            list shared-tree-join-route {
              description
                "List of ng-mvpn Shared Tree Join routes";
              key "route-distinguisher source-as multicast-source-address multicast-group-address neighbor path-id";
              uses ng-mvpn-c-multicast;
              uses state-routes-common;
              uses ng-mvpn-route;
            }
            list source-tree-join-route {
              description
                "List of ng-mvpn Source Tree Join routes";
              key "route-distinguisher source-as multicast-source-address multicast-group-address neighbor path-id";
              uses ng-mvpn-c-multicast;
              uses state-routes-common;
              uses ng-mvpn-route;
            }
          }
          container rib-in-out {
            description
              "Enter the rib-in-out context

               Container for BGP routes learned and advertised to BGP neighbors.";
            container rib-in-pre {
              list intra-as-ipmsi-ad-route {
                description
                  "List of ng-mvpn intra-as inclusive pmsi auto-discovery routes";
                key "route-distinguisher originating-router neighbor path-id";
                uses ng-mvpn-intra-as-ipmsi-ad;
                uses ng-mvpn-route;
              }
              list spmsi-ad-route {
                description
                  "List of ng-mvpn intra-as selective pmsi auto-discovery routes";
                key "route-distinguisher multicast-source-address multicast-group-address originating-router neighbor path-id";
                uses ng-mvpn-spmsi-ad;
                uses ng-mvpn-route;
              }
              list leaf-ad-route {
                description
                  "List of ng-mvpn leaf ad routes";
                key "spmsi-ad-route-distinguisher spmsi-ad-multicast-source-address spmsi-ad-multicast-group-address spmsi-ad-originating-router originating-router neighbor path-id";
                uses ng-mvpn-leaf-ad;
                uses ng-mvpn-route;
              }
              list source-active-ad-route {
                description
                  "List of ng-mvpn source active ad routes";
                key "route-distinguisher multicast-source-address multicast-group-address neighbor path-id";
                uses ng-mvpn-source-active-ad;
                uses ng-mvpn-route;
              }
              list shared-tree-join-route {
                description
                  "List of ng-mvpn Shared Tree Join routes";
                key "route-distinguisher source-as multicast-source-address multicast-group-address neighbor path-id";
                uses ng-mvpn-c-multicast;
                uses ng-mvpn-route;
              }
              list source-tree-join-route {
                description
                  "List of ng-mvpn Source Tree Join routes";
                key "route-distinguisher source-as multicast-source-address multicast-group-address neighbor path-id";
                uses ng-mvpn-c-multicast;
                uses ng-mvpn-route;
              }
              description
                "Enter the rib-in-pre context";
            }
            container rib-in-post {
              list intra-as-ipmsi-ad-route {
                description
                  "List of ng-mvpn intra-as inclusive pmsi auto-discovery routes";
                key "route-distinguisher originating-router neighbor path-id";
                uses ng-mvpn-intra-as-ipmsi-ad;
                uses state-routes-common;
                uses ng-mvpn-route;
              }
              list spmsi-ad-route {
                description
                  "List of ng-mvpn intra-as selective pmsi auto-discovery routes";
                key "route-distinguisher multicast-source-address multicast-group-address originating-router neighbor path-id";
                uses ng-mvpn-spmsi-ad;
                uses state-routes-common;
                uses ng-mvpn-route;
              }
              list leaf-ad-route {
                description
                  "List of ng-mvpn leaf ad routes";
                key "spmsi-ad-route-distinguisher spmsi-ad-multicast-source-address spmsi-ad-multicast-group-address spmsi-ad-originating-router originating-router neighbor path-id";
                uses ng-mvpn-leaf-ad;
                uses state-routes-common;
                uses ng-mvpn-route;
              }
              list source-active-ad-route {
                description
                  "List of ng-mvpn source active ad routes";
                key "route-distinguisher multicast-source-address multicast-group-address neighbor path-id";
                uses ng-mvpn-source-active-ad;
                uses state-routes-common;
                uses ng-mvpn-route;
              }
              list shared-tree-join-route {
                description
                  "List of ng-mvpn Shared Tree Join routes";
                key "route-distinguisher source-as multicast-source-address multicast-group-address neighbor path-id";
                uses ng-mvpn-c-multicast;
                uses state-routes-common;
                uses ng-mvpn-route;
              }
              list source-tree-join-route {
                description
                  "List of ng-mvpn Source Tree Join routes";
                key "route-distinguisher source-as multicast-source-address multicast-group-address neighbor path-id";
                uses ng-mvpn-c-multicast;
                uses state-routes-common;
                uses ng-mvpn-route;
              }
              description
                "Enter the rib-in-post context";
            }
            container rib-out-post {
              list intra-as-ipmsi-ad-route {
                description
                  "List of ng-mvpn intra-as inclusive pmsi auto-discovery routes";
                key "route-distinguisher originating-router neighbor path-id";
                uses ng-mvpn-intra-as-ipmsi-ad;
                uses ng-mvpn-route;
              }
              list spmsi-ad-route {
                description
                  "List of ng-mvpn intra-as selective pmsi auto-discovery routes";
                key "route-distinguisher multicast-source-address multicast-group-address originating-router neighbor path-id";
                uses ng-mvpn-spmsi-ad;
                uses ng-mvpn-route;
              }
              list leaf-ad-route {
                description
                  "List of ng-mvpn leaf ad routes";
                key "spmsi-ad-route-distinguisher spmsi-ad-multicast-source-address spmsi-ad-multicast-group-address spmsi-ad-originating-router originating-router neighbor path-id";
                uses ng-mvpn-leaf-ad;
                uses ng-mvpn-route;
              }
              list source-active-ad-route {
                description
                  "List of ng-mvpn source active ad routes";
                key "route-distinguisher multicast-source-address multicast-group-address neighbor path-id";
                uses ng-mvpn-source-active-ad;
                uses ng-mvpn-route;
              }
              list shared-tree-join-route {
                description
                  "List of ng-mvpn Shared Tree Join routes";
                key "route-distinguisher source-as multicast-source-address multicast-group-address neighbor path-id";
                uses ng-mvpn-c-multicast;
                uses ng-mvpn-route;
              }
              list source-tree-join-route {
                description
                  "List of ng-mvpn Source Tree Join routes";
                key "route-distinguisher source-as multicast-source-address multicast-group-address neighbor path-id";
                uses ng-mvpn-c-multicast;
                uses ng-mvpn-route;
              }
              description
                "Enter the rib-out-post context";
            }
          }
        }
        container evpn {
          description
            "Enter the evpn context

             Container for RIB state of EVPN routes";
          container local-rib {
            description
              "Enter the local-rib context

               Container for local RIB state of EVPN routes

               Includes the post import-policy RIB-INs corresponding to EVPN routes received from default net-instance BGP peers
               (post import-policy means after processing by the BGP import policy attached to the default net-instance peer and
               after processing by the vrf-import policy of importing network instances) plus the post vrf-export policy “imported”
               routes from local network instances.";
            list ethernet-ad-route {
              description
                "List of Ethernet AD (Auto-Discovery) routes";
              key "route-distinguisher esi ethernet-tag-id neighbor path-id";
              uses evpn-ethernet-ad-common;
              uses state-routes-common;
              leaf-list imported-network-instances {
                description
                  "List of network instances that imported the route";
                type leafref {
                  path "/srl_nokia-netinst:network-instance/srl_nokia-netinst:name";
                }
              }
              uses srl_nokia-rt:internal-tags;
            }
            list mac-ip-route {
              description
                "List of Mac/IP Advertisement routes";
              key "route-distinguisher ethernet-tag-id mac-length mac-address ip-address neighbor path-id";
              uses evpn-mac-ip-common;
              uses state-routes-common;
              leaf-list imported-network-instances {
                description
                  "List of network instances that imported the route";
                type leafref {
                  path "/srl_nokia-netinst:network-instance/srl_nokia-netinst:name";
                }
              }
              leaf-list dpath-looped-network-instances {
                if-feature "srl-feat:bgp-domain-path";
                description
                  "List of network instances in which a loop due to the D-PATH attribute is detected";
                type leafref {
                  path "/srl_nokia-netinst:network-instance/srl_nokia-netinst:name";
                }
              }
              uses srl_nokia-rt:internal-tags;
            }
            list imet-route {
              description
                "List of Inclusive Multicast Ethernet Tag routes";
              key "route-distinguisher ethernet-tag-id originating-router neighbor path-id";
              uses evpn-imet-common;
              uses state-routes-common;
              leaf-list imported-network-instances {
                description
                  "List of network instances that imported the route";
                type leafref {
                  path "/srl_nokia-netinst:network-instance/srl_nokia-netinst:name";
                }
              }
              uses srl_nokia-rt:internal-tags;
            }
            list ethernet-segment-route {
              description
                "List of Ethernet Segment routes";
              key "route-distinguisher esi originating-router neighbor path-id";
              uses evpn-es-common;
              uses state-routes-common;
              uses srl_nokia-rt:internal-tags;
            }
            list ip-prefix-route {
              description
                "List of IP prefix routes";
              key "route-distinguisher ethernet-tag-id ip-prefix-length ip-prefix neighbor path-id";
              uses evpn-ip-common;
              uses state-routes-common;
              leaf-list imported-network-instances {
                description
                  "List of network instances that imported the route";
                type leafref {
                  path "/srl_nokia-netinst:network-instance/srl_nokia-netinst:name";
                }
              }
              leaf-list dpath-looped-network-instances {
                if-feature "srl-feat:bgp-domain-path";
                description
                  "List of IP-VRF network instances in which a loop due to the D-PATH attribute is detected";
                type leafref {
                  path "/srl_nokia-netinst:network-instance/srl_nokia-netinst:name";
                }
              }
              uses srl_nokia-rt:internal-tags;
            }
            list smet-route {
              description
                "List of Selective Multicast Ethernet Tag routes";
              key "route-distinguisher ethernet-tag-id multicast-source-length multicast-source-address multicast-group-length multicast-group-address originating-router neighbor path-id";
              uses evpn-smet-common;
              uses state-routes-common;
              leaf-list imported-network-instances {
                description
                  "List of network instances that imported the route";
                type leafref {
                  path "/srl_nokia-netinst:network-instance/srl_nokia-netinst:name";
                }
              }
              uses srl_nokia-rt:internal-tags;
            }
            list multicast-membership-report-synch-route {
              description
                "List of Multicast Membership Report Synch routes";
              key "route-distinguisher esi ethernet-tag-id multicast-source-length multicast-source-address multicast-group-length multicast-group-address originating-router neighbor path-id";
              uses evpn-multicast-membership-report-synch-common;
              uses state-routes-common;
              leaf-list imported-network-instances {
                description
                  "List of network instances that imported the route";
                type leafref {
                  path "/srl_nokia-netinst:network-instance/srl_nokia-netinst:name";
                }
              }
              uses srl_nokia-rt:internal-tags;
            }
            list multicast-leave-synch-route {
              description
                "List of Multicast Leave Synch routes";
              key "route-distinguisher esi ethernet-tag-id multicast-source-length multicast-source-address multicast-group-length multicast-group-address originating-router neighbor path-id";
              uses evpn-multicast-leave-synch-common;
              uses state-routes-common;
              leaf-list imported-network-instances {
                description
                  "List of network instances that imported the route";
                type leafref {
                  path "/srl_nokia-netinst:network-instance/srl_nokia-netinst:name";
                }
              }
              uses srl_nokia-rt:internal-tags;
            }
          }
          container rib-in-out {
            description
              "Enter the rib-in-out context

               Container for BGP routes learned and advertised to BGP neighbors";
            container rib-in-pre {
              description
                "Enter the rib-in-pre context

                 Container for the pre-import-policy version of BGP routes learned from BGP neighbors.";
              list ethernet-ad-route {
                description
                  "List of Ethernet AD (Auto-Discovery) routes";
                key "route-distinguisher esi ethernet-tag-id neighbor path-id";
                uses evpn-ethernet-ad-common;
              }
              list mac-ip-route {
                description
                  "List of Mac/IP Advertisement routes";
                key "route-distinguisher ethernet-tag-id mac-length mac-address ip-address neighbor path-id";
                uses evpn-mac-ip-common;
              }
              list imet-route {
                description
                  "List of Inclusive Multicast Ethernet Tag routes";
                key "route-distinguisher ethernet-tag-id originating-router neighbor path-id";
                uses evpn-imet-common;
              }
              list ethernet-segment-route {
                description
                  "List of Ethernet Segment routes";
                key "route-distinguisher esi originating-router neighbor path-id";
                uses evpn-es-common;
              }
              list ip-prefix-route {
                description
                  "List of IP prefix routes";
                key "route-distinguisher ethernet-tag-id ip-prefix-length ip-prefix neighbor path-id";
                uses evpn-ip-common;
              }
              list smet-route {
                description
                  "List of Selective Multicast Ethernet Tag routes";
                key "route-distinguisher ethernet-tag-id multicast-source-length multicast-source-address multicast-group-length multicast-group-address originating-router neighbor path-id";
                uses evpn-smet-common;
              }
              list multicast-membership-report-synch-route {
                description
                  "List of Multicast Membership Report Synch routes";
                key "route-distinguisher esi ethernet-tag-id multicast-source-length multicast-source-address multicast-group-length multicast-group-address originating-router neighbor path-id";
                uses evpn-multicast-membership-report-synch-common;
              }
              list multicast-leave-synch-route {
                description
                  "List of Multicast Leave Synch routes";
                key "route-distinguisher esi ethernet-tag-id multicast-source-length multicast-source-address multicast-group-length multicast-group-address originating-router neighbor path-id";
                uses evpn-multicast-leave-synch-common;
              }
            }
            container rib-in-post {
              description
                "Enter the rib-in-post context

                 Container for the post-import-policy version of BGP routes learned from BGP neighbors.";
              list ethernet-ad-route {
                description
                  "List of Ethernet AD (Auto-Discovery) routes";
                key "route-distinguisher esi ethernet-tag-id neighbor path-id";
                uses evpn-ethernet-ad-common;
                uses state-routes-common;
                uses srl_nokia-rt:internal-tags;
              }
              list mac-ip-route {
                description
                  "List of Mac/IP Advertisement routes";
                key "route-distinguisher ethernet-tag-id mac-length mac-address ip-address neighbor path-id";
                uses evpn-mac-ip-common;
                uses state-routes-common;
                uses srl_nokia-rt:internal-tags;
              }
              list imet-route {
                description
                  "List of Inclusive Multicast Ethernet Tag routes";
                key "route-distinguisher ethernet-tag-id originating-router neighbor path-id";
                uses evpn-imet-common;
                uses state-routes-common;
                uses srl_nokia-rt:internal-tags;
              }
              list ethernet-segment-route {
                description
                  "List of Ethernet Segment routes";
                key "route-distinguisher esi originating-router neighbor path-id";
                uses evpn-es-common;
                uses state-routes-common;
                uses srl_nokia-rt:internal-tags;
              }
              list ip-prefix-route {
                description
                  "List of IP prefix routes";
                key "route-distinguisher ethernet-tag-id ip-prefix-length ip-prefix neighbor path-id";
                uses evpn-ip-common;
                uses state-routes-common;
                uses srl_nokia-rt:internal-tags;
              }
              list smet-route {
                description
                  "List of Selective Multicast Ethernet Tag routes";
                key "route-distinguisher ethernet-tag-id multicast-source-length multicast-source-address multicast-group-length multicast-group-address originating-router neighbor path-id";
                uses evpn-smet-common;
                uses state-routes-common;
                uses srl_nokia-rt:internal-tags;
              }
              list multicast-membership-report-synch-route {
                description
                  "List of Multicast Membership Report Synch routes";
                key "route-distinguisher esi ethernet-tag-id multicast-source-length multicast-source-address multicast-group-length multicast-group-address originating-router neighbor path-id";
                uses evpn-multicast-membership-report-synch-common;
                uses state-routes-common;
                uses srl_nokia-rt:internal-tags;
              }
              list multicast-leave-synch-route {
                description
                  "List of Multicast Leave Synch routes";
                key "route-distinguisher esi ethernet-tag-id multicast-source-length multicast-source-address multicast-group-length multicast-group-address originating-router neighbor path-id";
                uses evpn-multicast-leave-synch-common;
                uses state-routes-common;
                uses srl_nokia-rt:internal-tags;
              }
            }
            container rib-out-post {
              description
                "Enter the rib-out-post context

                 Container for the post-export-policy version of BGP routes advertised to BGP neighbors.";
              list ethernet-ad-route {
                description
                  "List of Ethernet AD (Auto-Discovery) routes";
                key "route-distinguisher esi ethernet-tag-id neighbor path-id";
                uses evpn-ethernet-ad-common;
                leaf next-hop {
                  description
                    "The advertised BGP next-hop address.";
                  type srl_nokia-comm:ip-address;
                }
              }
              list mac-ip-route {
                description
                  "List of Mac/IP Advertisement routes";
                key "route-distinguisher ethernet-tag-id mac-length mac-address ip-address neighbor path-id";
                uses evpn-mac-ip-common;
                leaf next-hop {
                  description
                    "The advertised BGP next-hop address.";
                  type srl_nokia-comm:ip-address;
                }
              }
              list imet-route {
                description
                  "List of Inclusive Multicast Ethernet Tag routes";
                key "route-distinguisher ethernet-tag-id originating-router neighbor path-id";
                uses evpn-imet-common;
                leaf next-hop {
                  description
                    "The advertised BGP next-hop address.";
                  type srl_nokia-comm:ip-address;
                }
              }
              list ethernet-segment-route {
                description
                  "List of Ethernet Segment routes";
                key "route-distinguisher esi originating-router neighbor path-id";
                uses evpn-es-common;
                leaf next-hop {
                  description
                    "The advertised BGP next-hop address.";
                  type srl_nokia-comm:ip-address;
                }
              }
              list ip-prefix-route {
                description
                  "List of IP prefix routes";
                key "route-distinguisher ethernet-tag-id ip-prefix-length ip-prefix neighbor path-id";
                uses evpn-ip-common;
                leaf next-hop {
                  description
                    "The advertised BGP next-hop address.";
                  type srl_nokia-comm:ip-address;
                }
              }
              list smet-route {
                description
                  "List of Selective Multicast Ethernet Tag routes";
                key "route-distinguisher ethernet-tag-id multicast-source-length multicast-source-address multicast-group-length multicast-group-address originating-router neighbor path-id";
                uses evpn-smet-common;
                leaf next-hop {
                  description
                    "The advertised BGP next-hop address.";
                  type srl_nokia-comm:ip-address;
                }
              }
              list multicast-membership-report-synch-route {
                description
                  "List of Multicast Membership Report Synch routes";
                key "route-distinguisher esi ethernet-tag-id multicast-source-length multicast-source-address multicast-group-length multicast-group-address originating-router neighbor path-id";
                uses evpn-multicast-membership-report-synch-common;
                leaf next-hop {
                  description
                    "The advertised BGP next-hop address.";
                  type srl_nokia-comm:ip-address;
                }
              }
              list multicast-leave-synch-route {
                description
                  "List of Multicast Leave Synch routes";
                key "route-distinguisher esi ethernet-tag-id multicast-source-length multicast-source-address multicast-group-length multicast-group-address originating-router neighbor path-id";
                uses evpn-multicast-leave-synch-common;
                leaf next-hop {
                  description
                    "The advertised BGP next-hop address.";
                  type srl_nokia-comm:ip-address;
                }
              }
            }
          }
        }
        container ipv4-flowspec-v1 {
          if-feature "srl-feat:bgp-flowspec-v1";
          description
            "Enter the ipv4-flowspec-v1 context

             Container for RIB state of ipv4-flowspec-v1 routes";
          container local-rib {
            description
              "Enter the local-rib context

               Container for local RIB, containing all imported routes from other protocols plus the post-import-policy version of all IPv4 routes learned from all BGP neighbors";
            list route {
              key "crc nlri-length nlri neighbor origin-protocol path-id";
              description
                "List of ipv4-flowspec-v1 routes. Keys to route include
                 prefix, neighbor, origin and path-id. If route is
                 imported route from other local protocols, neighbor
                 IP address will be zero. If route is selected to
                 be advertised to peer by local BGP speaker's
                 decision making process, then the origin will be
                 set to 'bgp'.";
              uses flowspec-v1-common-local-rib-key;
              uses flowspec-v1-common;
              uses state-routes-common;
              leaf attr-id {
                description
                  "Leaf reference to networkinstance/protocols/bgp/rib/attr-sets/attr-set/index.";
                type leafref {
                  path "../../../../../srl_nokia-rib-bgp-routes:attr-sets/srl_nokia-rib-bgp-routes:attr-set/srl_nokia-rib-bgp-routes:index";
                }
              }
            }
          }
          container rib-in-out {
            description
              "Enter the rib-in-out context

               Container for BGP routes learned and advertised to BGP neighbors";
            container rib-in-pre {
              description
                "Enter the rib-in-pre context

                 Container for the pre-import-policy version of BGP routes learned from BGP neighbors";
              list route {
                key "crc nlri-length nlri neighbor path-id";
                description
                  "List of ipv4-flowspec-v1 routes in the RIB-IN, before import-policy modification.";
                uses flowspec-v1-common-key;
                uses flowspec-v1-common;
                leaf attr-id {
                  description
                    "Leaf reference to networkinstance/protocols/bgp/rib/attr-sets/attr-set/index.";
                  type leafref {
                    path "../../../../../../srl_nokia-rib-bgp-routes:attr-sets/srl_nokia-rib-bgp-routes:attr-set/srl_nokia-rib-bgp-routes:index";
                  }
                }
              }
            }
            container rib-in-post {
              description
                "Enter the rib-in-post context

                 Container for the post-import-policy version of BGP routes learned from BGP neighbors";
              list route {
                key "crc nlri-length nlri neighbor path-id";
                description
                  "List of ipv4-flowspec-v1 routes in the RIB-IN, after import-policy modification.";
                uses flowspec-v1-common-key;
                uses flowspec-v1-common;
                uses state-routes-common;
                leaf attr-id {
                  description
                    "Leaf reference to networkinstance/protocols/bgp/rib/attr-sets/attr-set/index.";
                  type leafref {
                    path "../../../../../../srl_nokia-rib-bgp-routes:attr-sets/srl_nokia-rib-bgp-routes:attr-set/srl_nokia-rib-bgp-routes:index";
                  }
                }
                uses srl_nokia-rt:internal-tags;
              }
            }
            container rib-out-post {
              description
                "Enter the rib-out-post context

                 Container for the post-export-policy version of BGP routes advertised to BGP neighbors";
              list route {
                key "crc nlri-length nlri neighbor path-id";
                description
                  "List of ipv4-flowspec-v1 routes in the RIB-OUT, after export-policy modification.";
                uses flowspec-v1-common-key;
                uses flowspec-v1-common;
                leaf attr-id {
                  description
                    "Leaf reference to networkinstance/protocols/bgp/rib/attr-sets/attr-set/index.";
                  type leafref {
                    path "../../../../../../srl_nokia-rib-bgp-routes:attr-sets/srl_nokia-rib-bgp-routes:attr-set/srl_nokia-rib-bgp-routes:index";
                  }
                }
              }
            }
          }
        }
        container ipv6-flowspec-v1 {
          if-feature "srl-feat:bgp-flowspec-v1";
          description
            "Enter the ipv6-flowspec-v1 context

             Container for RIB state of ipv6-flowspec-v1 routes";
          container local-rib {
            description
              "Enter the local-rib context

               Container for local RIB, containing all imported routes from other protocols plus the post-import-policy version of all IPv4 routes learned from all BGP neighbors";
            list route {
              key "crc nlri-length nlri neighbor origin-protocol path-id";
              description
                "List of ipv6-flowspec-v1 routes. Keys to route include
                 prefix, neighbor, origin and path-id. If route is
                 imported route from other local protocols, neighbor
                 IP address will be zero. If route is selected to
                 be advertised to peer by local BGP speaker's
                 decision making process, then the origin will be
                 set to 'bgp'.";
              uses flowspec-v1-common-local-rib-key;
              uses flowspec-v1-common;
              uses state-routes-common;
              leaf attr-id {
                description
                  "Leaf reference to networkinstance/protocols/bgp/rib/attr-sets/attr-set/index.";
                type leafref {
                  path "../../../../../srl_nokia-rib-bgp-routes:attr-sets/srl_nokia-rib-bgp-routes:attr-set/srl_nokia-rib-bgp-routes:index";
                }
              }
            }
          }
          container rib-in-out {
            description
              "Enter the rib-in-out context

               Container for BGP routes learned and advertised to BGP neighbors";
            container rib-in-pre {
              description
                "Enter the rib-in-pre context

                 Container for the pre-import-policy version of BGP routes learned from BGP neighbors";
              list route {
                key "crc nlri-length nlri neighbor path-id";
                description
                  "List of ipv6-flowspec-v1 routes in the RIB-IN, before import-policy modification.";
                uses flowspec-v1-common-key;
                uses flowspec-v1-common;
                leaf attr-id {
                  description
                    "Leaf reference to networkinstance/protocols/bgp/rib/attr-sets/attr-set/index.";
                  type leafref {
                    path "../../../../../../srl_nokia-rib-bgp-routes:attr-sets/srl_nokia-rib-bgp-routes:attr-set/srl_nokia-rib-bgp-routes:index";
                  }
                }
              }
            }
            container rib-in-post {
              description
                "Enter the rib-in-post context

                 Container for the post-import-policy version of BGP routes learned from BGP neighbors";
              list route {
                key "crc nlri-length nlri neighbor path-id";
                description
                  "List of ipv6-flowspec-v1 routes in the RIB-IN, after import-policy modification.";
                uses flowspec-v1-common-key;
                uses flowspec-v1-common;
                uses state-routes-common;
                leaf attr-id {
                  description
                    "Leaf reference to networkinstance/protocols/bgp/rib/attr-sets/attr-set/index.";
                  type leafref {
                    path "../../../../../../srl_nokia-rib-bgp-routes:attr-sets/srl_nokia-rib-bgp-routes:attr-set/srl_nokia-rib-bgp-routes:index";
                  }
                }
                uses srl_nokia-rt:internal-tags;
              }
            }
            container rib-out-post {
              description
                "Enter the rib-out-post context

                 Container for the post-export-policy version of BGP routes advertised to BGP neighbors";
              list route {
                key "crc nlri-length nlri neighbor path-id";
                description
                  "List of ipv6-flowspec-v1 routes in the RIB-OUT, after export-policy modification.";
                uses flowspec-v1-common-key;
                uses flowspec-v1-common;
                leaf attr-id {
                  description
                    "Leaf reference to networkinstance/protocols/bgp/rib/attr-sets/attr-set/index.";
                  type leafref {
                    path "../../../../../../srl_nokia-rib-bgp-routes:attr-sets/srl_nokia-rib-bgp-routes:attr-set/srl_nokia-rib-bgp-routes:index";
                  }
                }
              }
            }
          }
        }
        container route-target {
          if-feature "srl-feat:bgp-rtc or srl-feat:bgp-rr-for-rtc";
          description
            "Enter the route-target context

             Container for RIB state of RTC routes.";
          container rib-in-out {
            description
              "Enter the rib-in-out context

               Container for BGP routes learned and advertised to BGP neighbors.";
            container rib-in-pre {
              description
                "Enter the rib-in-pre context

                 Container for the pre-import-policy version of BGP routes learned from BGP neighbors.";
              list route {
                key "origin-as route-target-prefix neighbor path-id";
                description
                  "List of RTC routes in the RIB-IN, before import-policy modification.";
                uses rtc-key;
                leaf attr-id {
                  description
                    "Leaf reference to networkinstance/protocols/bgp/rib/attr-sets/attr-set/index.";
                  type leafref {
                    path "../../../../../../srl_nokia-rib-bgp-routes:attr-sets/srl_nokia-rib-bgp-routes:attr-set/srl_nokia-rib-bgp-routes:index";
                  }
                }
              }
            }
            container rib-in-post {
              description
                "Enter the rib-in-post context

                 Container for the post-import-policy version of BGP routes learned from BGP neighbors.";
              list route {
                description
                  "List of RTC routes in the RIB-IN, after import-policy modification.";
                key "origin-as route-target-prefix neighbor path-id";
                uses rtc-key;
                uses state-routes-common;
                leaf attr-id {
                  description
                    "Leaf reference to networkinstance/protocols/bgp/rib/
                     attr-sets/attr-set/index.";
                  type leafref {
                    path "../../../../../../srl_nokia-rib-bgp-routes:attr-sets/srl_nokia-rib-bgp-routes:attr-set/srl_nokia-rib-bgp-routes:index";
                  }
                }
                uses srl_nokia-rt:internal-tags;
              }
            }
            container rib-out-post {
              description
                "Enter the rib-out-post context

                 Container for the post-export-policy version of BGP routes advertised to BGP neighbors.";
              list route {
                key "origin-as route-target-prefix neighbor path-id";
                description
                  "List of RTC routes in the RIB-OUT, after export-policy modification.";
                uses rtc-key;
                leaf attr-id {
                  description
                    "Leaf reference to networkinstance/protocols/bgp/rib/attr-sets/attr-set/index.";
                  type leafref {
                    path "../../../../../../srl_nokia-rib-bgp-routes:attr-sets/srl_nokia-rib-bgp-routes:attr-set/srl_nokia-rib-bgp-routes:index";
                  }
                }
              }
            }
          }
        }
        container srte-policy-ipv4 {
          if-feature "srl-feat:bgp-srte-policy";
          description
            "Enter the srte-policy-ipv4 context

             Container for RIB state of SR policy candidate paths with IPv4 endpoint addresses";
          container rib-in-out {
            description
              "Enter the rib-in-out context

               Container for BGP routes learned and advertised to BGP neighbors";
            container rib-in-pre {
              description
                "Enter the rib-in-pre context

                 Container for the pre-import-policy version of BGP routes learned from BGP neighbors";
              list route {
                key "distinguisher color endpoint neighbor path-id";
                description
                  "List of received BGP routes encoding SR policy candidate paths towards IPv4 endpoints";
                uses srte-policy-common-key;
                leaf attr-id {
                  description
                    "Leaf reference to networkinstance/protocols/bgp/rib/attr-sets/attr-set/index";
                  type leafref {
                    path "../../../../../../srl_nokia-rib-bgp-routes:attr-sets/srl_nokia-rib-bgp-routes:attr-set/srl_nokia-rib-bgp-routes:index";
                  }
                }
              }
            }
            container rib-in-post {
              description
                "Enter the rib-in-post context

                 Container for the post-import-policy version of BGP routes learned from BGP neighbors";
              list route {
                key "distinguisher color endpoint neighbor path-id";
                description
                  "List of received BGP routes encoding SR policy candidate paths towards IPv4 endpoints";
                uses srte-policy-common-key;
                uses state-routes-common;
                leaf attr-id {
                  description
                    "Leaf reference to networkinstance/protocols/bgp/rib/attr-sets/attr-set/index";
                  type leafref {
                    path "../../../../../../srl_nokia-rib-bgp-routes:attr-sets/srl_nokia-rib-bgp-routes:attr-set/srl_nokia-rib-bgp-routes:index";
                  }
                }
                uses srl_nokia-rt:internal-tags;
              }
            }
            container rib-out-post {
              description
                "Enter the rib-out-post context

                 Container for the post-export-policy version of BGP routes advertised to BGP neighbors";
              list route {
                key "distinguisher color endpoint neighbor path-id";
                description
                  "List of SR policy routes in the RIB-OUT, after export-policy modification";
                uses srte-policy-common-key;
                leaf attr-id {
                  description
                    "Leaf reference to networkinstance/protocols/bgp/rib/
                     attr-sets/attr-set/index";
                  type leafref {
                    path "../../../../../../srl_nokia-rib-bgp-routes:attr-sets/srl_nokia-rib-bgp-routes:attr-set/srl_nokia-rib-bgp-routes:index";
                  }
                }
              }
            }
          }
        }
        container srte-policy-ipv6 {
          if-feature "srl-feat:bgp-srte-policy";
          description
            "Enter the srte-policy-ipv6 context

             Container for RIB state of SR policy candidate paths with IPv6 endpoint addresses";
          container rib-in-out {
            description
              "Enter the rib-in-out context

               Container for BGP routes learned and advertised to BGP neighbors";
            container rib-in-pre {
              description
                "Enter the rib-in-pre context

                 Container for the pre-import-policy version of BGP routes learned from BGP neighbors";
              list route {
                key "distinguisher color endpoint neighbor path-id";
                description
                  "List of received BGP routes encoding SR policy candidate paths towards IPv6 endpoints";
                uses srte-policy-common-key;
                leaf attr-id {
                  description
                    "Leaf reference to networkinstance/protocols/bgp/rib/attr-sets/attr-set/index";
                  type leafref {
                    path "../../../../../../srl_nokia-rib-bgp-routes:attr-sets/srl_nokia-rib-bgp-routes:attr-set/srl_nokia-rib-bgp-routes:index";
                  }
                }
              }
            }
            container rib-in-post {
              description
                "Enter the rib-in-post context

                 Container for the post-import-policy version of BGP routes learned from BGP neighbors";
              list route {
                key "distinguisher color endpoint neighbor path-id";
                description
                  "List of received BGP routes encoding SR policy candidate paths towards IPv6 endpoints";
                uses srte-policy-common-key;
                uses state-routes-common;
                leaf attr-id {
                  description
                    "Leaf reference to networkinstance/protocols/bgp/rib/attr-sets/attr-set/index";
                  type leafref {
                    path "../../../../../../srl_nokia-rib-bgp-routes:attr-sets/srl_nokia-rib-bgp-routes:attr-set/srl_nokia-rib-bgp-routes:index";
                  }
                }
                uses srl_nokia-rt:internal-tags;
              }
            }
            container rib-out-post {
              description
                "Enter the rib-out-post context

                 Container for the post-export-policy version of BGP routes advertised to BGP neighbors";
              list route {
                key "distinguisher color endpoint neighbor path-id";
                description
                  "List of SR policy routes in the RIB-OUT, after export-policy modification";
                uses srte-policy-common-key;
                leaf attr-id {
                  description
                    "Leaf reference to networkinstance/protocols/bgp/rib/
                     attr-sets/attr-set/index";
                  type leafref {
                    path "../../../../../../srl_nokia-rib-bgp-routes:attr-sets/srl_nokia-rib-bgp-routes:attr-set/srl_nokia-rib-bgp-routes:index";
                  }
                }
              }
            }
          }
        }
        container link-state {
          if-feature "srl-feat:traffic-engineering-bgpls";
          description
            "Enter the link-state context

             Container for RIB state of link-state routes";
          container local-rib {
            description
              "Enter the local-rib context

               Link-State routes that are selected as the best route.
               This includes routes imported from other protocols.";
            list route {
              key "nlri-type crc nlri-length nlri neighbor origin-protocol path-id";
              description
                "List of Link-State routes. Keys to route include
                 prefix, neighbor, origin and path-id. If route is
                 imported route from other local protocols, neighbor
                 IP address will be zero. If route is selected to
                 be advertised to peer by local BGP speaker's
                 decision making process, then the origin will be
                 set to 'bgp'.";
              uses link-state-common-local-rib-key;
              uses link-state-common;
              uses state-routes-common;
              leaf attr-id {
                description
                  "Leaf reference to networkinstance/protocols/bgp/rib/attr-sets/attr-set/index.";
                type leafref {
                  path "../../../../../srl_nokia-rib-bgp-routes:attr-sets/srl_nokia-rib-bgp-routes:attr-set/srl_nokia-rib-bgp-routes:index";
                }
              }
            }
          }
          container rib-in-out {
            description
              "Enter the rib-in-out context

               Container for BGP routes learned and advertised to BGP neighbors";
            container rib-in-pre {
              description
                "Enter the rib-in-pre context

                 Container for the pre-import-policy version of BGP routes learned from BGP neighbors";
              list route {
                key "nlri-type crc nlri-length nlri neighbor path-id";
                description
                  "List of received BGP routes encoding node link-state info";
                uses link-state-common-key;
                uses link-state-common;
                leaf attr-id {
                  description
                    "Leaf reference to networkinstance/protocols/bgp/rib/attr-sets/attr-set/index.";
                  type leafref {
                    path "../../../../../../srl_nokia-rib-bgp-routes:attr-sets/srl_nokia-rib-bgp-routes:attr-set/srl_nokia-rib-bgp-routes:index";
                  }
                }
              }
            }
            container rib-in-post {
              description
                "Enter the rib-in-post context

                 Container for the post-import-policy version of BGP routes learned from BGP neighbors";
              list route {
                key "nlri-type crc nlri-length nlri neighbor path-id";
                description
                  "List of received BGP routes encoding node link-state info";
                uses link-state-common-key;
                uses link-state-common;
                uses state-routes-common;
                leaf attr-id {
                  description
                    "Leaf reference to networkinstance/protocols/bgp/rib/attr-sets/attr-set/index.";
                  type leafref {
                    path "../../../../../../srl_nokia-rib-bgp-routes:attr-sets/srl_nokia-rib-bgp-routes:attr-set/srl_nokia-rib-bgp-routes:index";
                  }
                }
              }
            }
            container rib-out-post {
              description
                "Enter the rib-out-post context

                 Container for the post-export-policy version of BGP routes advertised to BGP neighbors";
              list route {
                key "nlri-type crc nlri-length nlri neighbor path-id";
                description
                  "List of link-state routes in the RIB-OUT, after export-policy modification";
                uses link-state-common-key;
                uses link-state-common;
                leaf attr-id {
                  description
                    "Leaf reference to networkinstance/protocols/bgp/rib/attr-sets/attr-set/index.";
                  type leafref {
                    path "../../../../../../srl_nokia-rib-bgp-routes:attr-sets/srl_nokia-rib-bgp-routes:attr-set/srl_nokia-rib-bgp-routes:index";
                  }
                }
              }
            }
          }
        }
      }
      container attr-sets {
        description
          "Enter the attr-sets context

           Container for BGP RIB path attribute sets that can be shared by one or more
           BGP routes.";
        list attr-set {
          description
            "List of attribute sets.";
          key "index";
          leaf index {
            description
              "A unique internal identifier of the attribute set.";
            type uint64;
          }
          container as-path {
            description
              "Enter the as-path context

               A container for the AS path attribute of the attribute set.";
            list segment {
              description
                "A list of segments. Each segment has a type and a list of one or more AS
                 numbers.";
              key "as-path-index";
              leaf as-path-index {
                description
                  "RIB attribute AS Path index";
                type uint32;
              }
              leaf type {
                description
                  "The type of the AS path segment.";
                type enumeration {
                  enum as-set;
                  enum as-sequence;
                  enum as-confed-sequence;
                  enum as-confed-set;
                }
              }
              leaf-list member {
                description
                  "A list of AS numbers (each of which is a 2byte-ASN or a 4byte-ASN) that belong
                   to the AS path segment.";
                type uint32;
                ordered-by user;
              }
            }
          }
          leaf origin {
            description
              "The value of the ORIGIN path attribute";
            type enumeration {
              enum igp;
              enum egp;
              enum incomplete;
            }
          }
          leaf atomic-aggregate {
            description
              "Set to true to indicate the presence of the ATOMIC_AGGREGATE path attribute.";
            type boolean;
          }
          leaf next-hop {
            description
              "The IPv4 or IPv6 address of the BGP next-hop (extracted from the
               NEXT_HOP field of the UPDATE or the MP_REACH_NLRI next-hop).";
            type srl_nokia-comm:ip-address-with-zone;
          }
          leaf med {
            description
              "The value of the MULTI_EXIT_DISC path attribute.";
            type uint32;
          }
          leaf local-pref {
            description
              "The value of the LOCAL_PREF path attribute.";
            type uint32;
          }
          leaf originator-id {
            description
              "The address in the ORIGINATOR_ID attribute added by a route reflector.";
            type srl_nokia-comm:ip-address;
          }
          leaf-list cluster-list {
            description
              "The list of IPv4 addresses in the CLUSTER_LIST path attribute.";
            type srl_nokia-comm:ip-address;
            ordered-by user;
          }
          leaf aigp {
            description
              "The value in the AIGP path attribute.";
            type uint64;
          }
          container aggregator {
            description
              "Enter the aggregator context";
            leaf as-number {
              description
                "The 2byte or 4byte AS number of the router that formed the aggregate
                 route.";
              type uint32 {
                range "1..4294967295";
              }
            }
            leaf address {
              description
                "The router ID of the BGP router that formed the aggregate route.";
              type srl_nokia-comm:ip-address;
            }
          }
          container pmsi-tunnel {
            description
              "Enter the pmsi-tunnel context

               A container for the Provider Multicast Service Interface Tunnel Attribute (PTA) of the attribute set.";
            leaf tunnel-type {
              description
                "The value of the tunnel-type in the PMSI Tunnel Attribute";
              type enumeration {
                enum no-tunnel;
                enum rsvp-te-p2mp;
                enum mldp-p2mp;
                enum pim-ssm;
                enum pim-sm;
                enum bidir-pim;
                enum ingress-replication;
                enum mldp-mp2mp;
                enum assisted-replication;
                enum bier;
              }
            }
            container flags {
              description
                "Enter the flags context

                 A container for the PTA Flags";
              leaf assisted-replication-type {
                description
                  "The value of the assisted-replication role type.";
                type enumeration {
                  enum none;
                  enum ar-replicator;
                  enum ar-leaf;
                  enum reserved;
                }
              }
              container pruned-flood-list {
                description
                  "Enter the pruned-flood-list context

                   A container for the optimized ingress replication pruned flood list flags.";
                leaf broadcast-multicast {
                  description
                    "The value of the broadcast-multicast flag.";
                  type enumeration {
                    enum 0;
                    enum 1;
                  }
                }
                leaf unknown-unicast {
                  description
                    "The value of the unknown-unicast flag.";
                  type enumeration {
                    enum 0;
                    enum 1;
                  }
                }
              }
              leaf leaf-information-required {
                description
                  "The value of the Leaf Information Required (LIR) flag.";
                type boolean;
              }
            }
            container label {
              description
                "Enter the label context

                 The encoded label value and type in the PMSI Tunnel Attribute";
              leaf value {
                description
                  "The value of the label field

                   If the route is an EVPN MPLS route, the mpls-label is read out of the 20-bit high order value.
                   If the route is an EVPN VXLAN route, the vni is read out of the 24-bit value. If the route is
                   an EVPN SRv6 route, this field is set to zero if no transposition is used and set to a non-zero
                   value if transposition is used.";
                type uint32 {
                  range "0..16777215";
                }
              }
              leaf value-type {
                description
                  "Whether the encoded label value is an mpls-label, a vni or a transposed function or argument";
                type label-type;
              }
            }
            leaf tunnel-endpoint {
              description
                "The value of the tunnel-endpoint in the PMSI Tunnel Attribute.";
              type srl_nokia-comm:ip-address;
            }
            uses complete-srv6-sid;
          }
          container pmsi-tunnel-mldp {
            description
              "Enter the pmsi-tunnel-mldp context

               A container for the Provider Multicast Service Interface Tunnel Attribute (PTA) for mLDP.";
            container flags {
              description
                "Enter the flags context

                 A container for the PTA Flags";
              leaf leaf-information-required {
                description
                  "The value of the Leaf Information Required (LIR) flag.";
                type boolean;
              }
            }
            container label {
              description
                "Enter the label context

                 The encoded label value and type in the PMSI Tunnel Attribute";
              leaf value {
                description
                  "The value of the label field

                   If the route is an EVPN MPLS route, the mpls-label is read out of the 20-bit high order value.
                   If the route is an EVPN VXLAN route, the vni is read out of the 24-bit value. If the route is
                   an EVPN SRv6 route, this field is set to zero if no transposition is used and set to a non-zero
                   value if transposition is used.";
                type uint32 {
                  range "0..16777215";
                }
              }
            }
            container pmsi-tunnel-attribute {
              description
                "Enter the pmsi-tunnel-attribute context

                 This container the pmsi tunnel attribute information for mLDP.";
              leaf root-node-address {
                description
                  "IP address of the root router, where the PMSI originates from.";
                type srl_nokia-comm:ip-address;
              }
              leaf opaque-lenght {
                description
                  "The length of the opaque value, in octets";
                type uint32;
              }
              leaf opaque-value {
                description
                  "The LDP MP opaque value, currently only opeque type 1 is supported which is the treeID of the p2mp lsp on the root";
                type uint32;
              }
            }
          }
          container communities {
            description
              "Enter the communities context

               Container for different types of BGP communities";
            leaf-list community {
              description
                "List of standard 4-byte community values in the COMMUNITY path
                 attribute. Each should be displayed in the format <0..65355>:<0..65535>";
              type string;
              ordered-by user;
            }
            leaf-list ext-community {
              description
                "List of extended 8-byte community values in the COMMUNITY path
                 attribute.";
              type string;
              ordered-by user;
            }
            leaf-list large-community {
              description
                "List of large 12-byte community values in the LARGE_COMMUNITY path
                 attribute. Each should be displayed in the format: <0..4294967295>:<0..4294967295>:<
                 0..4294967295>";
              type string {
                length "1..72";
              }
              ordered-by user;
            }
            leaf-list ipv6-ext-community {
              description
                "List of ipv6-extended 20-byte community values in the COMMUNITY path
                 attribute.";
              type string;
              ordered-by user;
            }
            leaf-list ext-community-raw-format {
              description
                "List of extended 8-byte community values in the COMMUNITY path
                 attribute.";
              type string;
              ordered-by user;
            }
          }
          container domain-path {
            if-feature "srl-feat:bgp-domain-path";
            description
              "Enter the domain-path context

               Sequence of domain segments in the propagation path of the route";
            list domain-segment {
              description
                "List of domain segments in the propagation path of the route";
              key "sequence-id";
              leaf sequence-id {
                description
                  "The sequence number of the domain segment, starting with 0 as the first domain segment in the propagation path";
                type uint32;
              }
              leaf domain-segment-length {
                type uint8;
                description
                  "Number of domains in a segment";
              }
              list domain {
                key "sequence-id";
                leaf sequence-id {
                  description
                    "The sequence number of the domain, starting with 0 as the first domain in the segment";
                  type uint32;
                }
                leaf domain-id {
                  description
                    "The domain identifier

                     Composed of a 4-octet global administrator field followed by a 2-octet local administrator
                     field, in the format: global-admin:local:admin";
                  type srl_nokia-comm:domain-id;
                }
                leaf inter-subnet-forwarding-safi-type {
                  description
                    "Inter-Subnet Forwarding SAFI type in which a route was received, before the route is re-exported into a different domain";
                  type uint8;
                }
              }
            }
          }
          container prefix-sid {
            if-feature "srl-feat:bgp-labeled-unicast-prefix-sid";
            description
              "Enter the prefix-sid context

               This container defines Prefix SID TLVs";
            list tlv {
              key "type";
              description
                "List of TLV types in the LSDB for the specified LSP.";
              leaf type {
                type identityref {
                  base prefix-sid-tlv-type;
                }
                description
                  "The type of TLV being described. The type of TLV is expressed as a canonical name.";
              }
              container label-index {
                when "../type = 'label-index'";
                description
                  "Enter the label-index context

                   This container defines TLV 1.";
                leaf label-index {
                  type uint32;
                  description
                    "32-bit value representing the index value in the SRGB space";
                }
              }
              container srgb-originator {
                when "../type = 'srgb-originator'";
                description
                  "Enter the srgb-originator context

                   This container defines TLV 3.";
                leaf-list srgb {
                  description
                    "List of SRGB ranges, each in the format <first-label>:<number-of-labels>";
                  type string {
                    pattern '[0-9]+:[0-9]+';
                  }
                }
              }
              container srv6-l3-service {
                when "../srl_nokia-rib-bgp-routes:type = 'srl_nokia-srv6-types:srv6-l3-service'";
                description
                  "Enter the srv6-l3-service context

                   This container defines TLV 5.";
                list sub-tlv {
                  key "type";
                  description
                    "List of sub-TLV types of the SRv6 L3 Service TLV.";
                  leaf type {
                    type identityref {
                      base srl_nokia-srv6-types:srv6-service-sub-tlv-type;
                    }
                    description
                      "The type of sub-TLV being described. The type of sub-TLV is expressed as a canonical name.";
                  }
                  uses srv6-sid-information-subtlv;
                }
              }
              container srv6-l2-service {
                when "../srl_nokia-rib-bgp-routes:type = 'srl_nokia-srv6-types:srv6-l2-service'";
                description
                  "Enter the srv6-l2-service context

                   This container defines TLV 6.";
                list sub-tlv {
                  key "type";
                  description
                    "List of sub-TLV types of the SRv6 L2 Service TLV.";
                  leaf type {
                    type identityref {
                      base srl_nokia-srv6-types:srv6-service-sub-tlv-type;
                    }
                    description
                      "The type of sub-TLV being described. The type of sub-TLV is expressed as a canonical name.";
                  }
                  uses srv6-sid-information-subtlv;
                }
              }
            }
          }
          container tunnel-encapsulation {
            if-feature "srl-feat:segment-routing-colored-te-policies or srl-feat:evpn-mh-anycast or srl-feat:evpn-anycast-l3-subnet";
            description
              "Enter the tunnel-encapsulation context

               This container models the Tunnel Encapsulation Attribute defined by RFC 9012";
            leaf tunnel-type {
              description
                "Identifies a type of tunnel";
              type identityref {
                base tunnel-encapsulation-attribute-tlv-type;
              }
            }
            container srte-policy {
              when "../tunnel-type = 'srte-policy'";
              description
                "Enter the srte-policy context

                 SRTE policy tunnel type";
              container sub-tlvs {
                list subtlv {
                  key "type";
                  description
                    "List of subTLV types in the tunnel-encapsulation attribute";
                  leaf type {
                    type identityref {
                      base tunnel-encapsulation-attribute-subtlv-type;
                    }
                    description
                      "The type of subTLV being described. The type of subTLV is expressed as a canonical name.";
                  }
                  container preference {
                    when "../type = 'preference'";
                    leaf value {
                      description
                        "4-octet value indicating the Preference of the SR Policy Candidate Path";
                      type uint32;
                    }
                    description
                      "Enter the preference context";
                  }
                  container binding-sid {
                    when "../type = 'binding-sid'";
                    leaf length {
                      description
                        "Length of the value field, expected to be 6 bytes";
                      type uint8;
                    }
                    leaf specified-bsid-only {
                      type boolean;
                    }
                    leaf drop-upon-invalid {
                      type boolean;
                      description
                        "Drop matching traffic if there is no valid candidate path";
                    }
                    uses full-mpls-label;
                    description
                      "Enter the binding-sid context";
                  }
                  list segment-list {
                    when "../type = 'segment-list'";
                    key "index";
                    leaf index {
                      description
                        "Index indicating the encoding order of the segment-list";
                      type uint8;
                    }
                    leaf length {
                      description
                        "The total length of the sub-TLVs encoded within the Segment List sub-TLV in bytes";
                      type uint16;
                    }
                    container sub-tlvs {
                      container weight {
                        leaf value {
                          description
                            "4 octets an unsigned integer value indicating the weight associated with a segment list";
                          type uint32;
                        }
                        description
                          "Enter the weight context";
                      }
                      list segment {
                        description
                          "List of segment subTLVs in the segment-list subTLV";
                        key "index";
                        leaf index {
                          description
                            "Index indicating the encoding order of the segments in the segment-list";
                          type uint8;
                        }
                        leaf type {
                          type enumeration {
                            enum a;
                            enum b;
                            enum c;
                            enum d;
                            enum e;
                            enum f;
                            enum g;
                            enum h;
                            enum i;
                            enum j;
                            enum k;
                          }
                          description
                            "The type of subTLV being described. The type of subTLV is expressed as a canonical name.";
                        }
                        container segment-type-a {
                          when "../type = 'A'";
                          uses full-mpls-label;
                          leaf sid-verification {
                            description
                              "Set true when SID verification is requested";
                            type boolean;
                          }
                          description
                            "Enter the segment-type-a context";
                        }
                      }
                      description
                        "Enter the sub-tlvs context";
                    }
                  }
                  container explicit-null-label-policy {
                    when "../type = 'explicit-null-label-policy'";
                    description
                      "Enter the explicit-null-label-policy context

                       Used to specify whether an Explicit NULL Label must be pushed on an unlabeled IP packet before any other labels";
                    leaf value {
                      description
                        "Explicit null label policy";
                      type uint8 {
                        range "1..4";
                      }
                    }
                  }
                  container priority {
                    when "../type = 'priority'";
                    description
                      "Enter the priority context

                       Used to specify indicate the order in which the SR policies are re-computed upon topological change";
                    leaf value {
                      type uint8;
                    }
                  }
                  container srte-policy-candidate-path-name {
                    when "../type = 'srte-policy-candidate-path-name'";
                    description
                      "Enter the srte-policy-candidate-path-name context

                       Symbolic name of the candidate path";
                    leaf name {
                      type string;
                    }
                  }
                  container srte-policy-name {
                    when "../type = 'srte-policy-name'";
                    description
                      "Enter the srte-policy-name context

                       Symbolic name of the policy";
                    leaf name {
                      type string;
                    }
                  }
                }
                description
                  "Enter the sub-tlvs context";
              }
            }
            container vxlan {
              when "../tunnel-type = 'vxlan'";
              description
                "Enter the vxlan context

                 VXLAN tunnel type";
              container sub-tlvs {
                list subtlv {
                  key "type";
                  description
                    "List of subTLV types in the tunnel-encapsulation attribute";
                  leaf type {
                    type identityref {
                      base tunnel-encapsulation-attribute-subtlv-type;
                    }
                    description
                      "The type of subTLV being described

                       The type of subTLV is expressed as a canonical name.";
                  }
                  container address-family {
                    when "../type = 'tunnel-egress-endpoint'";
                    description
                      "Enter the address-family context

                       Address family of the tunnel egress endpoint";
                    leaf address-family {
                      description
                        "Address family of the tunnel egress endpoint address";
                      type identityref {
                        base srl_nokia-comm:address-family;
                      }
                    }
                  }
                  container address {
                    when "../type = 'tunnel-egress-endpoint'";
                    description
                      "Enter the address context

                       Address of the tunnel egress endpoint";
                    leaf address {
                      description
                        "Address of the tunnel egress endpoint";
                      type srl_nokia-comm:ip-address;
                    }
                  }
                }
                description
                  "Enter the sub-tlvs context";
              }
            }
          }
          container link-state {
            if-feature "srl-feat:traffic-engineering-bgpls";
            description
              "Enter the link-state context

               Container for link-state attributes.";
            leaf-list attr {
              description
                "List of link-state attribute strings.";
              type string {
                length "80";
              }
              max-elements 200;
            }
          }
          container unknown-attributes {
            description
              "Enter the unknown-attributes context

               Container for unknown path attributes";
            list unknown-attribute {
              description
                "List of unknown BGP path attributes";
              key "unknown-attr-index";
              leaf unknown-attr-index {
                description
                  "RIB attribute unknown attribute index";
                type uint32;
              }
              leaf attr-type {
                description
                  "The type code of the unknown path
                   attribute";
                type uint8;
              }
              leaf attr-len {
                description
                  "The length of the unknown path
                   attribute";
                type uint16;
              }
              leaf optional {
                description
                  "Set to true if the unknown path
                   attribute has the optional flag is set to
                   1.";
                type boolean;
              }
              leaf transitive {
                description
                  "Set to true if the unknown path
                   attribute has the transitive flag is set to
                   1.";
                type boolean;
              }
              leaf partial {
                description
                  "Set to true if the unknown path
                   attribute has the partial flag is set to 1.";
                type boolean;
              }
              leaf extended {
                description
                  "Set to true if the unknown path attribute has the extended length flag
                   is set to 1.";
                type boolean;
              }
            }
          }
        }
      }
    }
  }

  augment "/srl_nokia-netinst:network-instance" {
    uses bgp-rib-top;
  }
}
