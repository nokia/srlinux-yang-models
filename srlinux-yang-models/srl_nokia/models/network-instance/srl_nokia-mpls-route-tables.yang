module srl_nokia-mpls-route-tables {
  yang-version 1.1;
  namespace "urn:nokia.com:srlinux:fib:mpls-route-tables";
  prefix srl_nokia-mpls-route-tables;

  import srl_nokia-common {
    prefix srl_nokia-comm;
  }
  import srl_nokia-extensions {
    prefix srl_nokia-ext;
  }
  import srl_nokia-network-instance {
    prefix srl_nokia-netinst;
  }
  import srl_nokia-ip-route-tables {
    prefix srl_nokia-ip-tables;
  }
  import srl_nokia-features {
    prefix srl_nokia-feat;
  }
  import srl_nokia-bgp-vpn {
    prefix srl_nokia-bgp-vpn;
  }
  import srl_nokia-system {
    prefix srl_nokia-system;
  }
  import srl_nokia-system-network-instance {
    prefix srl_nokia-system-netinst;
  }
  import srl_nokia-system-network-instance-bgp-evpn-ethernet-segments {
    prefix srl_nokia-eth-seg;
  }

  organization
    "Nokia";
  contact
    "Nokia SR Linux Support
     Web: <http://www.nokia.com>";
  description
    "A model describing the MPLS routing tables of a network instance.";

  revision 2026-07-31 {
    description
      "SRLinux 26.7.1";
  }
  revision 2026-03-31 {
    description
      "SRLinux 26.3.1";
  }
  revision 2025-10-31 {
    description
      "SRLinux 25.10.1";
  }
  revision 2025-03-31 {
    description
      "SRLinux 25.3.1";
  }
  revision 2024-07-31 {
    description
      "SRLinux 24.7.1";
  }
  revision 2023-07-31 {
    description
      "SRLinux 23.7.1";
  }
  revision 2021-06-30 {
    description
      "SRLinux 21.6.1";
  }
  revision 2019-11-30 {
    description
      "SRLinux 19.11.1";
  }

  grouping mpls-entry-common-fields {
    leaf operation {
      type enumeration {
        enum pop;
        enum swap;
        enum swap-pop;
        enum pop-xconnect-unicast;
        enum pop-xconnect-multicast;
      }
      srl_nokia-ext:show-importance "high";
      description
        "The forwarding operation associated with the MPLS label entry.";
    }
    leaf entry-type {
      type identityref {
        base srl_nokia-comm:mpls-label-entry-type;
      }
      srl_nokia-ext:show-importance "high";
      description
        "The entry type of the MPLS FIB entry.";
    }
    leaf last-app-update {
      type srl_nokia-comm:date-and-time-delta;
      description
        "The date and time of the last update of this MPLS label entry by the owning application or protocol.";
    }
    leaf next-hop-group {
      type leafref {
        path "/srl_nokia-netinst:network-instance/srl_nokia-netinst:route-table/srl_nokia-ip-tables:next-hop-group/srl_nokia-ip-tables:index";
      }
      description
        "The next-hop-group indirection object used by this route. Applicable only if the operation is SWAP.";
    }
    leaf next-network-instance {
      type leafref {
        path "/srl_nokia-netinst:network-instance/srl_nokia-netinst:name";
      }
      description
        "If this ILM entry is for a pop label, and this label is at the bottom of the stack, the next forwarding lookup will be done in the referenced network-instance";
    }
    leaf next-bgp-instance {
      if-feature "srl_nokia-feat:evpn or srl_nokia-feat:ipvpn";
      type leafref {
        path "/srl_nokia-netinst:network-instance/srl_nokia-netinst:protocols/srl_nokia-bgp-vpn:bgp-vpn/srl_nokia-bgp-vpn:bgp-instance/srl_nokia-bgp-vpn:id";
      }
    }
    leaf next-ethernet-segment {
      if-feature "srl_nokia-feat:evpn-mh";
      type leafref {
        path "/srl_nokia-system:system/srl_nokia-system-netinst:network-instance/srl_nokia-system-netinst:protocols/srl_nokia-system-netinst:evpn/srl_nokia-eth-seg:ethernet-segments/srl_nokia-eth-seg:bgp-instance/srl_nokia-eth-seg:ethernet-segment/srl_nokia-eth-seg:name";
      }
      description
        "If this ILM entry is for a pop label, and this label is below an EVPN label at the bottom of the stack,
         the label will identify an Ethernet Segment and forwarding in the network-instance may exclude the
         bridged subinterfaces associated with the Ethernet Segment";
    }
    uses srl_nokia-ip-tables:fib-programming-status {
      if-feature "srl_nokia-feat:fib-ilm-programming";
    }
  }

  grouping mpls-table-statistics {
    container statistics {
      leaf active-entries {
        type srl_nokia-comm:zero-based-counter64;
        description
          "The total number of MPLS entries that are active in the FIB.";
      }
      description
        "Enter the statistics context";
    }
  }

  grouping mpls-tables-top {
    container mpls {
      description
        "Enter the mpls context

         The container for the MPLS routing table of the network instance.";
      list label-entry {
        key "label-value";
        leaf label-value {
          type srl_nokia-comm:mpls-label-non-reserved;
          description
            "The MPLS label value";
        }
        uses mpls-entry-common-fields;
      }
      uses mpls-table-statistics;
    }
  }

  augment "/srl_nokia-netinst:network-instance/srl_nokia-netinst:route-table" {
    uses mpls-tables-top;
  }
}
