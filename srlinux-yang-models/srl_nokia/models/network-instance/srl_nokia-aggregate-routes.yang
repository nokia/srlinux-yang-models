module srl_nokia-aggregate-routes {
  yang-version 1.1;
  namespace "urn:nokia.com:srlinux:static-route:aggregate-routes";
  prefix srl_nokia-aggregate-routes;

  import srl_nokia-common {
    prefix srl_nokia-comm;
  }
  import srl_nokia-features {
    prefix srl_nokia-feat;
  }
  import srl_nokia-network-instance {
    prefix srl_nokia-netinst;
  }
  import srl_nokia-policy-types {
    prefix srl_nokia-pol-types;
  }

  organization
    "Nokia";
  contact
    "Nokia SR Linux Support
     Web: <http://www.nokia.com>";
  description
    "This yang file gives a description of aggregate route configuration.";

  revision 2026-07-31 {
    description
      "SRLinux 26.7.1";
  }
  revision 2024-07-31 {
    description
      "SRLinux 24.7.1";
  }
  revision 2024-03-31 {
    description
      "SRLinux 24.3.1";
  }
  revision 2021-03-31 {
    description
      "SRLinux 21.3.1";
  }
  revision 2019-11-30 {
    description
      "SRLinux 19.11.1";
  }

  grouping aggregate-route-top {
    container aggregate-routes {
      presence "Configure Aggregate Routes";
      leaf instance-name {
        if-feature "srl_nokia-feat:network-instance-protocol-instance-names";
        type srl_nokia-comm:name;
        description
          "The name of the aggregate routing instance (optional)";
      }
      list route {
        max-elements 16384;
        key "prefix";
        leaf prefix {
          type srl_nokia-comm:ip-prefix;
          must "../../../srl_nokia-netinst:type != 'srl_nokia-netinst:host'" {
            error-message "Aggregate routes not supported with network instance of type host";
          }
        }
        leaf admin-state {
          type srl_nokia-comm:admin-state;
          default "enable";
          description
            "Administratively enable or disable this aggregate route.";
        }
        leaf installed {
          config false;
          type boolean;
          description
            "If set to true, this indicates that the aggregate route was installed into the datapath. If this is false then there are 2 possible reasons:
             (a) the admin-state is disable
             (b) there is another IP route for the same prefix that has a superior preference";
        }
        leaf generate-icmp {
          type boolean;
          description
            "When set to true the router generares ICMP unreachable messages for packets matching the aggregate route (and not a more specific route).";
        }
        leaf summary-only {
          type boolean;
          default "false";
          description
            "When set to true the router blocks the advertisement of all contributing
             routes of this aggregate route in dynamic protocols such as BGP.";
        }
        container aggregator {
          leaf address {
            type srl_nokia-comm:ipv4-address;
            description
              "Specifies the aggregator's IP address.";
          }
          leaf as-number {
            description
              "Specifies the aggregator's ASN";
            type srl_nokia-comm:as-number {
              range "1..4294967295";
            }
          }
          description
            "Enter the aggregator context";
        }
        container communities {
          leaf-list add {
            type union {
              type srl_nokia-pol-types:bgp-std-community-type;
              type srl_nokia-pol-types:bgp-std-community-well-known-type;
              type srl_nokia-pol-types:bgp-large-community-type;
            }
            ordered-by user;
            max-elements 12;
          }
          description
            "Enter the communities context";
        }
      }
    }
  }

  augment "/srl_nokia-netinst:network-instance" {
    uses aggregate-route-top;
  }
}
