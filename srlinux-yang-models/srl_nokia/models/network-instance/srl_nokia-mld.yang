module srl_nokia-mld {
  yang-version 1.1;
  namespace "urn:nokia.com:srlinux:igmp:mld";
  prefix srl_nokia-mld;

  import srl_nokia-common {
    prefix srl_nokia-comm;
  }
  import srl_nokia-network-instance {
    prefix srl_nokia-netinst;
  }
  import srl_nokia-routing-policy {
    prefix srl-rpol;
  }
  import srl_nokia-igmp-types {
    prefix srl_nokia-igmp-types;
  }
  import srl_nokia-features {
    prefix srl_nokia-feat;
  }
  import srl_nokia-extensions {
    prefix srl_nokia-ext;
  }
  import srl_nokia-mcast-cac {
    prefix srl_nokia-mcac;
  }

  organization
    "Nokia";
  contact
    "Nokia SR Linux Support
     Web: <http://www.nokia.com>";
  description
    "This yang file models configuration and state of the mld protocol";

  revision 2026-07-31 {
    description
      "SRLinux 26.7.1";
  }
  revision 2026-03-31 {
    description
      "SRLinux 26.3.1";
  }
  revision 2023-07-31 {
    description
      "SRLinux 23.7.1";
  }
  revision 2023-03-31 {
    description
      "SRLinux 23.3.1";
  }
  revision 2022-11-30 {
    description
      "SRLinux 22.11.1";
  }
  revision 2022-06-30 {
    description
      "SRLinux 22.6.1";
  }
  revision 2022-03-31 {
    description
      "SRLinux 22.3.1";
  }
  revision 2021-11-30 {
    description
      "SRLinux 21.11.1";
  }

  typedef mld-version {
    type uint8 {
      range "1..2";
    }
    description
      "MLD Version.";
    reference
      "v1 = RFC2710, v2 = RFC4604";
  }

  typedef mld-interval-type {
    type uint32;
    units "seconds";
    description
      "Interval at which the router sends the MLD query message toward
       the upstream neighbor.";
    reference
      "RFC3376 8.2 Page 40";
  }

  grouping mld-policy {
    leaf import-policy {
      if-feature "srl_nokia-feat:mcast-route-policy";
      description
        "Apply an import policy.  The lenght of the policy name should not exceed 32 charachters";
      type leafref {
        path "/srl-rpol:routing-policy/srl-rpol:policy/srl-rpol:name";
      }
    }
  }

  grouping mld-interface-key {
    leaf interface-name {
      description
        "Reference to a specific subinterface of the form <interface-name>.<subinterface-index>";
      type srl_nokia-comm:subinterface-all;
    }
  }

  grouping mld-grp-range-keys {
    leaf start {
      type srl_nokia-comm:ipv6-address;
      description
        "start of the group range";
      must "starts-with(.,'ff')" {
        error-message "Not a valid IPv6 multicast address";
      }
      must "not (re-match(.,'[f]{2}[0-9a-f][0-3].*') or re-match(.,'[f]{2}[0-9a-f][f].*'))" {
        error-message "Not a valid IPv6 multicast address scope";
      }
    }
    leaf end {
      type srl_nokia-comm:ipv6-address;
      description
        "end of the group range";
      must "starts-with(.,'ff')" {
        error-message "Not a valid IPv6 multicast address";
      }
      must "not (re-match(.,'[f]{2}[0-9a-f][0-3].*') or re-match(.,'[f]{2}[0-9a-f][f].*'))" {
        error-message "Not a valid IPv6 multicast address scope";
      }
    }
  }

  grouping mld-ssm-config {
    description
      "Source specific multicast (SSM) configuration";
    container ssm {
      description
        "Enter the ssm context

         Container to configure Source specific multicast (SSM) options";
      container mappings {
        description
          "Enter the mappings context

           A list of source specific multicast (SSM) mappings";
        list group-range {
          key "start end";
          description
            "A Source Specific Multicast (SSM) mapping

             This allows MLD v2 hosts to be able to join in SSM environments
             by translating MLD v1 reports into MLD v2 reports.
             The request in an MLD v1 join is sent toward the source
             address found by matching the multicast address.";
          uses mld-grp-range-keys;
          list source {
            description
              "Multicast source address list";
            min-elements 1;
            key "source";
            leaf source {
              type srl_nokia-comm:ipv6-address;
              description
                "Multicast source address";
              must "not(.='::/128' or .='::1/128' or starts-with(.,'ff') or starts-with(.,'fe80'))" {
                error-message "Not a global unicast IPv6 address";
              }
            }
          }
        }
      }
    }
  }

  grouping mld-interfaces-tracing-config {
    leaf interfaces {
      type empty;
      description
        "Enable tracing all interface events";
    }
  }

  grouping mld-packet-tracing-config {
    container packet {
      presence "Enable the tracing of MLD packets";
      description
        "Trace MLD Packet types
         Only one type can be enabled at a time";
      container interface {
        presence "Enable the tracing of IGMP packets";
        description
          "Enable interface filter for packets";
        choice interface {
          mandatory true;
          leaf name {
            description
              "Trace for interface with this name";
            type leafref {
              path "../../../../../interface/interface-name";
            }
          }
          leaf all {
            description
              "Trace for all interfaces";
            type empty;
          }
        }
      }
      leaf type {
        type enumeration {
          enum all {
            value 0;
            description
              "Enable tracing of all MLD packets";
          }
          enum query {
            value 1;
            description
              "Enable tracing of MLD Query packets";
          }
          enum v1-report {
            value 2;
            description
              "Enable tracing of MLD version 1 Report packets";
          }
          enum v1-done {
            value 3;
            description
              "Enable tracing of MLD version 1 Done packets";
          }
          enum v2-report {
            value 4;
            description
              "Enable tracing of MLD version 2 Report packets";
          }
        }
      }
      leaf modifier {
        type enumeration {
          enum dropped {
            value 0;
            description
              "Enable tracing for the packets which are dropped";
          }
          enum ingress-and-dropped {
            value 1;
            description
              "Enable tracing for the packets which are sent or received";
          }
          enum egress-ingress-and-dropped {
            value 2;
            description
              "Enable tracing for the packets which are sent, received or dropped";
          }
        }
        default "egress-ingress-and-dropped";
      }
    }
  }

  grouping mld-global-trace-options {
    container trace-options {
      description
        "Enter the trace-options context";
      container trace {
        description
          "Enter the trace context

           Tracing parameter flags";
        container interface {
          presence "Enable the tracing of MLD packets";
          description
            "Enable tracing interface events.";
          choice interface {
            mandatory true;
            leaf name {
              description
                "Trace for interface with this name";
              type leafref {
                path "../../../../interface/interface-name";
              }
            }
            leaf all {
              description
                "Trace for all interfaces";
              type empty;
            }
          }
        }
        uses mld-packet-tracing-config;
      }
    }
  }

  grouping mld-global-config {
    description
      "MLD specific configuration";
    leaf admin-state {
      description
        "Administratively enable or disable the MLD instance";
      type srl_nokia-comm:admin-state;
      default "disable";
    }
    leaf query-interval {
      description
        "Interval at which the router sends the mld membership queries";
      type mld-interval-type {
        range "2..1024";
      }
      default "125";
      must '. > ../query-response-interval' {
        error-message "query-response-interval must be less than query-interval";
      }
      must '. > ../query-last-member-interval' {
        error-message "query-last-member-interval must be less than query-interval";
      }
    }
    leaf query-last-member-interval {
      description
        "Interval at which Group-Specific-Query packets are transmitted";
      type mld-interval-type {
        range "1..1023";
      }
      default "1";
    }
    leaf query-response-interval {
      description
        "Time to wait to receive a response to the MLD membership query from the host";
      type mld-interval-type {
        range "1..1023";
      }
      default "10";
    }
    leaf robust-count {
      description
        "Tune MLD robustness to allow for expected packet loss

         The robust-count variable allows tuning for the expected packet
         loss on a subnet. If a subnet anticipates losses, the robust-count
         variable can be increased.";
      type uint32 {
        range "2..10";
      }
      default "2";
    }
    uses mld-global-trace-options;
    uses mld-ssm-config;
  }

  grouping mld-interface-config {
    leaf admin-state {
      description
        "Administratively enable or disable the MLD protocol for this interface

         Used to administratively enable or disable the MLD protocol on a
         routed subinterface";
      type srl_nokia-comm:admin-state;
      default "enable";
    }
    leaf version {
      description
        "MLD Version";
      type mld-version;
      default "2";
    }
    leaf router-alert-check {
      description
        "Enable or disable router alert checking for MLD messages received on this interface";
      type boolean;
      default "true";
    }
    leaf maximum-number-groups {
      description
        "MAX number of MLD Groups for this interface, 0 means no limit";
      type uint32 {
        range "1..4096";
      }
    }
    leaf maximum-number-sources {
      description
        "MAX number of MLD sources per group for this interface, 0 means no limit";
      type uint32 {
        range "1..512";
      }
    }
    leaf maximum-number-group-sources {
      description
        "MAX number of MLD group/source combinations for this interface, 0 means no limit";
      type uint32 {
        range "1..4096";
      }
    }
    leaf query-interval {
      description
        "Interval at which the router sends the mld membership queries";
      type mld-interval-type {
        range "2..1024";
      }
      must '. > ../query-response-interval' {
        error-message "query-response-interval must be less than query-interval";
      }
      must '. > ../query-last-member-interval' {
        error-message "query-last-member-interval must be less than query-interval";
      }
    }
    leaf query-last-member-interval {
      description
        "Interval at which Group-Specific-Query packets are transmitted";
      type mld-interval-type {
        range "1..1023";
      }
    }
    leaf query-response-interval {
      description
        "Time to wait to receive a response to the MLD membership query from the host";
      type mld-interval-type {
        range "1..1023";
      }
    }
    uses mld-policy;
    uses mld-ssm-config;
    container static-membership-groups {
      description
        "Enter the static-membership-groups context

         Container to configure static <S,G>s for this interface";
      list group-range {
        key "start end";
        uses mld-grp-range-keys;
        choice source-or-starg {
          mandatory true;
          case source {
            list source {
              description
                "Multicast source address list";
              key "source";
              leaf source {
                type srl_nokia-comm:ipv6-address;
                description
                  "Multicast source address";
                must "not(.='::/128' or .='::1/128' or starts-with(.,'ff') or starts-with(.,'fe80'))" {
                  error-message "Not a global unicast IPv6 address";
                }
              }
            }
          }
          case starg {
            leaf starg {
              description
                "any source address (*,G)";
              type empty;
            }
          }
        }
      }
    }
  }

  grouping mld-msg-stats {
    leaf general-queries {
      config false;
      description
        "General Queries";
      type srl_nokia-comm:zero-based-counter32;
    }
    leaf group-queries {
      config false;
      description
        "Group Specific Queries";
      type srl_nokia-comm:zero-based-counter32;
    }
    leaf group-source-queries {
      config false;
      description
        "Group and Source Specific Queries";
      type srl_nokia-comm:zero-based-counter32;
    }
    leaf v1-reports {
      config false;
      description
        "V1 Reports";
      type srl_nokia-comm:zero-based-counter32;
    }
    leaf v2-reports {
      config false;
      description
        "V2 Reports";
      type srl_nokia-comm:zero-based-counter32;
    }
    leaf leaves {
      config false;
      description
        "Leaves";
      type srl_nokia-comm:zero-based-counter32;
    }
    leaf drops {
      config false;
      description
        "Total number of dropped packets";
      type srl_nokia-comm:zero-based-counter32;
    }
  }

  grouping mld-msg-tx-stats {
    leaf general-queries {
      config false;
      description
        "General Queries";
      type srl_nokia-comm:zero-based-counter32;
    }
    leaf group-queries {
      config false;
      description
        "Group Specific Queries";
      type srl_nokia-comm:zero-based-counter32;
    }
    leaf group-source-queries {
      config false;
      description
        "Group and Source Specific Queries";
      type srl_nokia-comm:zero-based-counter32;
    }
    leaf errors {
      config false;
      description
        "Transmission Errors";
      type srl_nokia-comm:zero-based-counter32;
    }
  }

  grouping mld-msg-error-stats {
    leaf bad-length {
      config false;
      description
        "Bad length";
      type srl_nokia-comm:zero-based-counter32;
    }
    leaf unknown-type {
      config false;
      description
        "Unknown type";
      type srl_nokia-comm:zero-based-counter32;
    }
    leaf wrong-version {
      config false;
      description
        "Wrong version";
      type srl_nokia-comm:zero-based-counter32;
    }
    leaf import-policy-drops {
      if-feature "srl_nokia-feat:mcast-route-policy";
      config false;
      description
        "Number of times we matched the host IP address or group or
         source addresses specified in the import policy.";
      type srl_nokia-comm:zero-based-counter32;
    }
    leaf missing-router-alert {
      config false;
      description
        "Router alert flag is not set";
      type srl_nokia-comm:zero-based-counter32;
    }
    leaf bad-encoding {
      config false;
      description
        "Badly encoded";
      type srl_nokia-comm:zero-based-counter32;
    }
    leaf local-scope {
      config false;
      description
        "Link-local scope multicast group address";
      type srl_nokia-comm:zero-based-counter32;
    }
    leaf reserved-scope {
      config false;
      description
        "Reserved scope multicast group address";
      type srl_nokia-comm:zero-based-counter32;
    }
    leaf reached-maximum-number-groups {
      config false;
      description
        "Number of times a join is dropped because we reached the maximum
         number of groups.";
      type srl_nokia-comm:zero-based-counter32;
    }
    leaf reached-maximum-number-group-sources {
      config false;
      description
        "Number of times a join is dropped because we reached the maximum
         number group-source combinations.";
      type srl_nokia-comm:zero-based-counter32;
    }
    leaf reached-maximum-number-sources {
      config false;
      description
        "Number of times a join is dropped because we reached the maximum
         number of sources per group.";
      type srl_nokia-comm:zero-based-counter32;
    }
    leaf out-of-memory-drops {
      config false;
      description
        "Number of times a join is dropped because we ran out of memory";
      type srl_nokia-comm:zero-based-counter32;
    }
  }

  grouping mld-msg-layer-3-error-stats {
    uses mld-msg-error-stats;
    leaf non-local {
      config false;
      description
        "Non-local sender source IP address";
      type srl_nokia-comm:zero-based-counter32;
    }
  }

  grouping mld-multicast-state {
    leaf star-group-entries {
      config false;
      description
        "The number of (*,G)s";
      type srl_nokia-comm:zero-based-counter32;
    }
    leaf source-group-entries {
      config false;
      description
        "The number of (S,G)s";
      type srl_nokia-comm:zero-based-counter32;
    }
  }

  grouping mld-statistics-state {
    container received {
      config false;
      description
        "Enter the received context

         Received message statistics";
      uses mld-msg-stats;
    }
    container transmitted {
      config false;
      description
        "Enter the transmitted context

         Transmit message statistics";
      uses mld-msg-tx-stats;
    }
    container error {
      config false;
      description
        "Enter the error context

         Error message statistics";
      uses mld-msg-layer-3-error-stats;
    }
    container multicast-states {
      config false;
      description
        "Enter the multicast-states context

         Multicast state count for this network instance";
      uses mld-multicast-state;
    }
  }

  grouping mld-interface-group-source-state {
    leaf source-type {
      config false;
      type srl_nokia-igmp-types:learn-type;
    }
    leaf forwarding-state {
      config false;
      description
        "Traffic forwardeding state on this port";
      type srl_nokia-igmp-types:forwarding-state;
    }
    leaf up-time {
      config false;
      type srl_nokia-comm:date-and-time-delta;
      description
        "The time elapsed since this entry was created";
    }
    leaf expiry-time {
      config false;
      description
        "The time left before multicast group timeout";
      type uint32;
      units "seconds";
    }
  }

  grouping mld-interface-group-state {
    description
      "MLD membership state";
    leaf last-reporter {
      config false;
      description
        "The last host address which has sent the report to join
         the multicast group.";
      type srl_nokia-comm:ip-address;
    }
    leaf group-type {
      config false;
      type srl_nokia-igmp-types:learn-type;
    }
    leaf filter-mode {
      config false;
      type srl_nokia-igmp-types:filter-mode;
    }
    leaf expiry-time {
      config false;
      description
        "The time left before multicast group timeout";
      type uint32;
      units "seconds";
    }
    leaf up-time {
      config false;
      type srl_nokia-comm:date-and-time-delta;
      description
        "The time elapsed since this entry was created";
    }
    leaf v1-host-timer {
      config false;
      description
        "The time remaining until the local router will assume that
         there are no longer any version 1 members.";
      type uint32;
      units "seconds";
    }
    leaf mld-compatibility-mode {
      config false;
      description
        "Compatibility with older version routers";
      type srl_nokia-igmp-types:mld-version;
    }
  }

  grouping mld-interface-membership {
    description
      "MLD membership information";
    leaf group-count {
      config false;
      description
        "The number of multicast groups which have been learned on this interface";
      type uint32;
    }
    container membership-groups {
      config false;
      description
        "Enter the membership-groups context

         List of MLD Membership information";
      list group {
        key "group";
        config false;
        description
          "Multicast group membership";
        leaf group {
          type srl_nokia-comm:ipv6-address;
          description
            "Multicast address";
        }
        uses mld-interface-group-state;
        list source {
          config false;
          key "source";
          description
            "Source addresses of multicast";
          leaf source {
            type srl_nokia-comm:ipv6-address;
            description
              "Source address of multicast";
          }
          uses mld-interface-group-source-state;
        }
      }
    }
  }

  grouping mld-global-state {
    leaf oper-state {
      config false;
      description
        "Used to report operational state of the MLD instance";
      type srl_nokia-comm:oper-state;
    }
  }

  grouping mld-global-membership {
    description
      "MLD membership information.";
    leaf group-count {
      config false;
      description
        "The number of multicast groups which have been learned on this instance";
      type uint32;
    }
    container membership-groups {
      config false;
      description
        "Enter the membership-groups context

         List of MLD Membership information";
      list group {
        key "group";
        config false;
        description
          "Multicast group membership";
        leaf group {
          type srl_nokia-comm:ipv6-address;
          description
            "Multicast address";
        }
        list source {
          config false;
          key "source";
          description
            "Source addresses of multicast";
          leaf source {
            type srl_nokia-comm:ipv6-address;
            description
              "Source address of multicast";
          }
          list forwarding-interface {
            config false;
            key "interface-name";
            uses mld-interface-key;
          }
          list blocked-interface {
            config false;
            key "interface-name";
            uses mld-interface-key;
          }
        }
      }
    }
  }

  grouping mld-interface-state {
    leaf oper-state {
      config false;
      description
        "The operational state of the MLD interface. This simply tracks the operational state of the subinterface";
      type srl_nokia-comm:oper-state;
    }
    leaf oper-version {
      config false;
      description
        "The operational MLD version on this interface";
      type mld-version;
    }
    container querier {
      config false;
      leaf address {
        config false;
        description
          "The address of the MLD Querier on the IP subnet to which this interface is attached";
        type srl_nokia-comm:ipv6-address;
      }
      leaf up-time {
        config false;
        type srl_nokia-comm:date-and-time-delta;
        description
          "The time since this querier was last elected";
      }
      leaf expiry-time {
        config false;
        description
          "The time remaining before this querier is aged out";
        type uint32;
        units "seconds";
      }
      description
        "Enter the querier context";
    }
    uses mld-interface-membership;
    container statistics {
      config false;
      description
        "Enter the statistics context

         Global MLD statistics";
      uses mld-statistics-state;
    }
  }

  grouping mld-top {
    container mld {
      if-feature "srl_nokia-feat:mld";
      presence "Configure MLD";
      must "not(../../srl_nokia-netinst:type = 'srl_nokia-netinst:ip-vrf')" {
        srl_nokia-ext:if-feature "not srl_nokia-features:mld-ipvrf";
        error-message "MLD routing configuration is not possible on network-instance of type ip-vrf";
      }
      must "not(../../srl_nokia-netinst:type = 'srl_nokia-netinst:mac-vrf')" {
        error-message "MLD routing configuration is not possible on network-instance of type mac-vrf";
      }
      must "../../srl_nokia-netinst:type != 'srl_nokia-netinst:host'" {
        error-message "MLD routing configuration is not possible on network-instance of type host";
      }
      uses mld-global-config;
      uses mld-global-state;
      uses mld-global-membership;
      list interface {
        description
          "List of MLD interfaces";
        key "interface-name";
        uses mld-interface-key;
        uses mld-interface-config;
        uses mld-interface-state;
        uses srl_nokia-mcac:mcac-interface-config;
      }
    }
  }

  augment "/srl_nokia-netinst:network-instance/srl_nokia-netinst:protocols" {
    uses mld-top;
  }
}
