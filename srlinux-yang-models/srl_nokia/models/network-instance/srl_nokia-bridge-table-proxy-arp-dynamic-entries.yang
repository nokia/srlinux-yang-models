module srl_nokia-bridge-table-proxy-arp-dynamic-entries {
  yang-version 1.1;
  namespace "urn:srl_nokia/network-instance/bridge-table/proxy-arp/dynamic-entries";
  prefix srl_nokia-bridge-proxy-arp-dynamic-entries;

  import srl_nokia-common {
    prefix srl_nokia-comm;
  }
  import srl_nokia-bridge-table-proxy-arp-nd {
    prefix srl_nokia-bridge-table-proxy-arp-nd;
  }
  import srl_nokia-network-instance {
    prefix srl_nokia-netinst;
  }
  import srl_nokia-extensions {
    prefix srl_nokia-ext;
  }

  description
    "This yang file gives a description of bridge table proxy arp dynamic entries.";

  revision 2021-11-30 {
    description
      "SRLinux 21.11.1";
  }

  grouping bridge-table-proxy-arp-dynamic-entries-top {
    container dynamic-entries {
      config false;
      list neighbor {
        key "ipv4-address";
        description
          "List of dynamic proxy ARP entries.";
        leaf ipv4-address {
          type srl_nokia-comm:ipv4-address;
          srl_nokia-ext:show-importance "high";
          description
            "IPv4 address of the proxy ARP entry.";
        }
        leaf link-layer-address {
          type srl_nokia-comm:mac-address;
          srl_nokia-ext:show-importance "high";
          description
            "The resolving MAC address of the proxy ARP entry.";
        }
        leaf last-update {
          type srl_nokia-comm:date-and-time-delta;
          srl_nokia-ext:show-importance "high";
          description
            "The date and time of the last update of this proxy ARP entry";
        }
        leaf aging {
          type union {
            type uint64;
            type enumeration {
              enum disabled {
                value -1;
              }
            }
          }
          units "seconds";
          srl_nokia-ext:show-importance "high";
          description
            "remaining age time for learnt macs";
        }
        leaf state {
          type srl_nokia-bridge-table-proxy-arp-nd:neighbor-state;
          srl_nokia-ext:show-importance "high";
          description
            "The state of the proxy ARP entry";
        }
      }
    }
  }

  augment "/srl_nokia-netinst:network-instance/srl_nokia-netinst:bridge-table/srl_nokia-bridge-table-proxy-arp-nd:proxy-arp" {
    uses bridge-table-proxy-arp-dynamic-entries-top;
  }
}
