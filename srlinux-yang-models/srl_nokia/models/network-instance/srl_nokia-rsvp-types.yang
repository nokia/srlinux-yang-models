module srl_nokia-rsvp-types {
  yang-version 1.1;
  namespace "urn:nokia.com:srlinux:mpls:rsvp-types";
  prefix srl_nokia-rsvp-types;

  organization
    "Nokia";
  contact
    "Nokia SR Linux Support
     Web: <http://www.nokia.com>";
  description
    "This YANG module defines the common data types used by the Resource reSerVation Protocol (RSVP).";

  revision 2026-07-31 {
    description
      "SRLinux 26.7.1";
  }

  typedef rsvp-te-threshold-level {
    type int32 {
      range "0..100";
    }
    description
      "Is an integer in the range of (0..100) that defines the traffic engineering (TE) threshold level.";
  }
}
