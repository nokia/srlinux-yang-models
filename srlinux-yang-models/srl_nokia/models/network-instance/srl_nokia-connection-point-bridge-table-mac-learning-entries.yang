module srl_nokia-connection-point-bridge-table-mac-learning-entries {
  yang-version 1.1;

  // namespace

  namespace "urn:nokia.com:srlinux:l2-mac-learn:connection-point-bridge-table-mac-learning-entries";
  prefix srl_nokia-connection-point-bridge-table-mac-learning-entries;

  import srl_nokia-network-instance {
    prefix srl_nokia-netinst;
  }
  import srl_nokia-interfaces-bridge-table-mac-learning-entries {
    prefix srl_nokia-interfaces-bridge-table-mac-learning-entries;
  }

  organization
    "Nokia";
  contact
    "Nokia SR Linux Support
     Web: <http://www.nokia.com>";
  description
    "This yang file gives a description of mac entries learned on this connection-points bridge table.";

  revision 2024-03-31 {
    description
      "SRLinux 24.3.3";
  }

  augment "/srl_nokia-netinst:network-instance/srl_nokia-netinst:connection-point/srl_nokia-netinst:bridge-table/srl_nokia-netinst:mac-learning" {
    uses srl_nokia-interfaces-bridge-table-mac-learning-entries:bridge-table-mac-learning-entries-top;
  }
}
