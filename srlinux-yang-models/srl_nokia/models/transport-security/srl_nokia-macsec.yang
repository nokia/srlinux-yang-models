module srl_nokia-macsec {
  yang-version 1.1;
  namespace "urn:nokia.com:srlinux:macsec:macsec";
  prefix srl_nokia-macsec;

  import srl_nokia-transport-security {
    prefix srl_nokia-transport-security;
  }
  import srl_nokia-common {
    prefix srl_nokia-comm;
  }
  import srl_nokia-features {
    prefix srl_nokia-feat;
  }
  import srl_nokia-extensions {
    prefix srl_nokia-ext;
  }
  import srl_nokia-interfaces {
    prefix srl_nokia-if;
  }
  import srl_nokia-keychains {
    prefix srl-keychain;
  }
  import srl_nokia-system {
    prefix srl_nokia-system;
  }

  organization
    "Nokia";
  contact
    "Nokia SR Linux Support
     Web: <http://www.nokia.com>";
  description
    "This module models MKA and macsec configuration under a subinterface";

  revision 2026-07-31 {
    description
      "SRLinux 26.7.1";
  }
  revision 2025-10-31 {
    description
      "SRLinux 25.10.1";
  }
  revision 2025-07-31 {
    description
      "SRLinux 25.7.1";
  }
  revision 2025-03-31 {
    description
      "SRLinux 25.3.1";
  }
  revision 2024-10-31 {
    description
      "SRLinux 24.10.1";
  }
  revision 2024-07-31 {
    description
      "SRLinux 24.7.1";
  }
  revision 2024-03-31 {
    description
      "SRLinux 24.3.1";
  }
  revision 2023-03-31 {
    description
      "SRLinux 23.3.1";
  }

  typedef macsec-cipher-suite {
    type enumeration {
      enum gcm-aes-128 {
        description
          "gcm-aes-128 Cipher Suite";
      }
      enum gcm-aes-256 {
        description
          "gcm-aes-256 Cipher Suite";
      }
      enum gcm-aes-xpn-128 {
        description
          "gcm-aes-xpn-128 Cipher Suite";
      }
      enum gcm-aes-xpn-256 {
        description
          "gcm-aes-xpn-256 Cipher Suite";
      }
    }
    description
      "Set Cipher suite(s) for SAK derivation";
  }

  typedef confidentiality-offset {
    type enumeration {
      enum 0-bytes {
        description
          "No octets are sent unencrypted";
      }
      enum 30-bytes {
        description
          "30 octects are sent unencrypted";
      }
      enum 50-bytes {
        description
          "50 octects are sent unencrypted";
      }
    }
    description
      "The confidentiality offset specifies a number of octets in an Ethernet frame that are sent in unencrypted plaintext";
  }

  typedef tag-mode {
    type enumeration {
      enum no-tag {
        description
          "Do not put any tags into clear";
      }
      enum single-tag {
        description
          "Put 4 bytes after the MAC header into clear";
      }
      enum double-tag {
        description
          "Put 8 bytes after the MAC header into clear";
      }
    }
    description
      "By default macsec encrypts the 802.1q and q-in-q tags. Clear-tag-mode specifies if the user desires to put a single tag or double tag into clear";
  }

  typedef protocols {
    type enumeration {
      enum lacp {
        description
          "LACP protocol";
      }
      enum lldp {
        description
          "LLDP protocol";
      }
      enum cdp {
        description
          "Cisco discovery protocol";
      }
      enum eapol-start {
        description
          "EAP over LAN start packets";
      }
      enum efm-oam {
        description
          "Ethernet in first mile protocol";
      }
      enum eth-cfm {
        description
          "Connectivity fault management protocol";
      }
      enum ptp {
        description
          "Precision Time Protocol";
      }
      enum ubfd {
        description
          "Micro BFD protocol";
      }
    }
    description
      "Protocols that can be excluded from macsec";
  }

  typedef sci-hex-string {
    type srl_nokia-comm:hex-string {
      length "23";
    }
  }

  grouping macsec-mka-policy-config {
    description
      "MKA policy config grouping";
    leaf admin-state {
      type srl_nokia-comm:admin-state;
      default "disable";
      description
        "Enable mka policy

         While MKA policy is enabled no policy parameters can be configured or modified.";
    }
    leaf maximum-number-of-peers {
      if-feature "srl_nokia-feat:macsec-subinterface";
      type uint32 {
        range "1..512";
      }
      description
        "Max mka peers allowed";
    }
    leaf key-server-priority {
      type uint8;
      default "16";
      description
        "Specifies the key server priority used by the macsec

         Macsec Key Agreement (MKA) advertises and selects a key server. The node with the lower priority-number is selected as the key server.
         If the priority-number is identical on both sides of a point-to-point link, the MKA protocol selects the device with the lower MAC address as the key server";
    }
    leaf eapol-destination-address {
      type srl_nokia-comm:mac-address;
      description
        "This command can be used to set eap over lan destination mac to a unicast mac for L2 multiple hop networks";
    }
    leaf hello-interval {
      type uint32 {
        range "1000 | 2000 | 3000 | 4000 | 5000 | 6000";
      }
      default "2000";
      description
        "MKA hello interval, the intervals are 1000 ms up to 6000 ms";
    }
    leaf macsec-cipher-suite {
      must "((((. = 'gcm-aes-xpn-128') or (.= 'gcm-aes-xpn-256')) and (../confidentiality-offset = '0-bytes')) or ((. != 'gcm-aes-xpn-128') and (. != 'gcm-aes-xpn-256')))" {
        error-message "confidentiality-offset is only valid for non-xpn cipher-suite";
      }
      type macsec-cipher-suite;
      description
        "Set cipher suite(s) for security association key (SAK) derivation";
    }
    leaf confidentiality-offset {
      type confidentiality-offset;
      default "0-bytes";
      description
        "The confidentiality offset specifies a number of octets in an Ethernet frame that are sent in unencrypted and in plain-text";
    }
    leaf clear-tag-mode {
      type tag-mode;
      default "no-tag";
      description
        "Specifies the number of tags that will be in clear infront of the sectag";
    }
    leaf encrypt {
      type boolean;
      default "true";
      description
        "Enable or disable PDU encryption, if enabled the PDUs are encrypted and authenticated if disabled the PDU is only authenticated and not encrypted";
    }
    leaf sak-rekey-on-live-peer-loss {
      type boolean;
      default "false";
      description
        "Security association key, re-key on peer loss";
    }
  }

  grouping macsec-mka-error-counters {
    description
      "MKA error counters grouping";
    container out-mkpdu-errors {
      leaf pdu-too-small {
        srl_nokia-ext:show-importance "high";
        type srl_nokia-comm:zero-based-counter64;
        description
          "MKPDU TX error count";
      }
      leaf pdu-too-big {
        srl_nokia-ext:show-importance "high";
        type srl_nokia-comm:zero-based-counter64;
        description
          "MKPDU TX error count";
      }
      leaf pdu-not-quad-size {
        type srl_nokia-comm:zero-based-counter64;
        description
          "MKPDU TX error count";
      }
      leaf pdu-invalid-number {
        srl_nokia-ext:show-importance "high";
        type srl_nokia-comm:zero-based-counter64;
        description
          "MKPDU TX error count";
      }
      description
        "Enter the out-mkpdu-errors context";
    }
    container in-mkpdu-errors {
      leaf icv-verification-errors {
        srl_nokia-ext:show-importance "high";
        type srl_nokia-comm:zero-based-counter64;
        description
          "MKPDU RX ICV verification error count";
      }
      leaf validation-errors {
        srl_nokia-ext:show-importance "high";
        type srl_nokia-comm:zero-based-counter64;
        description
          "MKPDU RX validation error count";
      }
      leaf bad-peer-errors {
        type srl_nokia-comm:zero-based-counter64;
        description
          "MKPDU RX bad peer message number error count";
      }
      leaf peer-list-errors {
        type srl_nokia-comm:zero-based-counter64;
        description
          "MKPDU RX non-recent peer list Message Number error count";
      }
      description
        "Enter the in-mkpdu-errors context";
    }
    leaf sak-generation-errors {
      srl_nokia-ext:show-importance "high";
      type srl_nokia-comm:zero-based-counter64;
      description
        "MKA error SAK generation count";
    }
    leaf sak-hash-errors {
      type srl_nokia-comm:zero-based-counter64;
      description
        "MKA error Hash Key generation count";
    }
    leaf sak-encryption-errors {
      srl_nokia-ext:show-importance "high";
      type srl_nokia-comm:zero-based-counter64;
      description
        "MKA error SAK encryption/wrap count";
    }
    leaf sak-decryption-errors {
      srl_nokia-ext:show-importance "high";
      type srl_nokia-comm:zero-based-counter64;
      description
        "MKA error SAK decryption/unwrap count";
    }
    leaf sak-cipher-mismatch-errors {
      srl_nokia-ext:show-importance "high";
      type srl_nokia-comm:zero-based-counter64;
      description
        "MKA error SAK cipher mismatch count";
    }
    leaf sak-install-fail {
      srl_nokia-ext:show-importance "high";
      type srl_nokia-comm:zero-based-counter64;
      description
        "MKA error SAK cipher mismatch count";
    }
  }

  grouping macsec-mka-global-state {
    description
      "MKA global state grouping";
    uses macsec-mka-error-counters;
  }

  grouping macsec-mka-global-top {
    description
      "MKA global top level grouping";
    container statistics {
      config false;
      description
        "Enter the statistics context

         Operational state data for MKA";
      uses macsec-mka-global-state;
    }
  }

  grouping macsec-mka-interface-state {
    description
      "MKA interface specific states";
    leaf oper-state {
      srl_nokia-ext:show-importance "high";
      config false;
      description
        "The operational state of the mka instance";
      type srl_nokia-comm:oper-state;
    }
    leaf encryption-offset {
      config false;
      type confidentiality-offset;
      description
        "Indicates the operational encryption offset used for the datapath PDUs when all parties in the CA have the SAK. This value is specified by the key server";
    }
    leaf oper-cipher {
      config false;
      type macsec-cipher-suite;
      description
        "Indicates the operational encryption algorithm used for datapath PDUs when all parties in the CA have the SAK. This value is specified by the key server";
    }
    leaf outbound-sci {
      config false;
      type binary {
        length "8";
        srl_nokia-ext:output-flavor "hex";
      }
      description
        "Indicates the Secure Channel Identifier (SCI) information for transmitting MACsec frames";
    }
    leaf message-count {
      config false;
      type srl_nokia-comm:zero-based-counter32;
      description
        "Indicates the current count of MKA messages that is attached to MKA PDUs";
    }
    leaf key-number {
      config false;
      type uint32;
      description
        "Indicates the number of the currently assigned CAK

         When a new CAK is generated, this number is incremented.";
    }
    leaf key-server {
      config false;
      type boolean;
      description
        "Indicates whether this server is the highest priority server in the peer group";
    }
    leaf key-server-priority {
      config false;
      type uint8;
      description
        "Indicates the priority of local server";
    }
    leaf hello-interval {
      config false;
      type uint32;
      description
        "MKA hello interval, the intervals are 1000 ms up to 6000 ms";
    }
    leaf latest-sak-an {
      config false;
      type uint32;
      description
        "Indicates the Association Number (AN) of the latest Secure Association Key (SAK)

         This number is concatenated with an SCI to identify a Secure Association (SA).";
    }
    leaf previous-sak-an {
      config false;
      type uint32;
      description
        "Indicates the Association Number (AN) of the previous Security Association key (SAK)

         This number is concatenated with an SCI to identify an Secure Association SA.";
    }
    leaf latest-sak-ki {
      config false;
      type binary {
        length "16";
        srl_nokia-ext:output-flavor "hex";
      }
      description
        "Indicates the Key Identifier (KI) of the latest SAK

         This number is derived from the MI of the key server and the key number.";
    }
    leaf previous-sak-ki {
      config false;
      type binary {
        length "16";
        srl_nokia-ext:output-flavor "hex";
      }
      description
        "Indicates the Key Identifier (KI) of the previous SAK

         This number is derived from the Member Identifier (MI) of the key server and the key number.";
    }
    list mka-participant {
      config false;
      key "ca-key-name";
      description
        "List of MKA participants.";
      leaf member-id {
        type binary {
          length "12";
          srl_nokia-ext:output-flavor "hex";
        }
        description
          "Specifies the MI of the MKA participant";
      }
      leaf cak-name {
        config false;
        description
          "MACsec CKN, a hexadecimal name is only valid";
        type srl_nokia-comm:macsec-key-name {
          length "2..64";
        }
      }
      leaf ca-key-name {
        config false;
        description
          "MACsec CKN, a hexadecimal name is only valid";
        type srl_nokia-comm:macsec-key-name {
          length "2..64";
        }
      }
      leaf keychain-name {
        config false;
        description
          "Keychain name being used by this participant";
        type srl_nokia-comm:name;
      }
      leaf keychain-key-index {
        config false;
        type uint8;
        description
          "Active key's keychain key index number";
      }
      leaf message-count {
        config false;
        type srl_nokia-comm:zero-based-counter32;
        description
          "Indicates the current count of MKA messages that is attached to MKA PDUs";
      }
      leaf type {
        config false;
        type enumeration {
          enum primary {
            value 1;
            description
              "This MKA participant is using primary keychain";
          }
          enum fallback {
            value 2;
            description
              "This MKA participant is using fallback keychain";
          }
        }
        description
          "Indicates the type of the MKA participant based on keychain it is using";
      }
      leaf principal {
        config false;
        type boolean;
        description
          "Indicates whether this MKA participant is principal";
      }
      leaf latest-sak-lpn {
        config false;
        type srl_nokia-comm:counter64;
        description
          "Indicates Lowest Acceptable Packet Number of the latest Security Association Key (SAK)";
      }
      leaf previous-sak-lpn {
        config false;
        type srl_nokia-comm:counter64;
        description
          "Indicates Lowest Acceptable Packet Number of the previous Security Association Key (SAK)";
      }
      list mka-peer {
        config false;
        key "member-id";
        description
          "List of MKA peers.";
        leaf member-id {
          type binary {
            length "12";
            srl_nokia-ext:output-flavor "hex";
          }
          description
            "Specifies the MI of the peer entry";
        }
        leaf mka-peer-mid {
          config false;
          type binary {
            length "12";
            srl_nokia-ext:output-flavor "hex";
          }
          description
            "Specifies the MI of the peer entry";
        }
        leaf message-number {
          type srl_nokia-comm:counter64;
          description
            "Indicates the latest message Number of the peer entry";
        }
        leaf type {
          type enumeration {
            enum live-peer-list {
              value 1;
              description
                "These peer entry is in the Live Peer List";
            }
            enum potential-peer-list {
              value 2;
              description
                "These peer entry is in the Potential Peer List";
            }
          }
          description
            "Indicates the type of the peer entry";
        }
        leaf sci {
          type binary {
            length "8";
            srl_nokia-ext:output-flavor "hex";
          }
          description
            "Indicates the SCI information of this peer list entry";
        }
        leaf key-server-priority {
          type uint8;
          description
            "Indicates the priority of this MKA peer";
        }
        leaf lowest-acceptable-pn {
          type uint64;
          description
            "Indicates the lowest acceptable packet number of this MKA peer";
        }
      }
    }
    container statistics {
      config false;
      description
        "Enter the statistics context

         MKA interface counters";
      uses macsec-mka-interface-counters;
      uses macsec-mka-error-counters;
    }
  }

  grouping macsec-mka-interface-counters {
    description
      "MKA interface state grouping";
    leaf in-mkpdu {
      type srl_nokia-comm:zero-based-counter64;
      description
        "Validated MKPDU received count";
    }
    leaf sak-generated {
      type srl_nokia-comm:zero-based-counter64;
      description
        "Indicates the number of SAKs generated by this MKA instance";
    }
    leaf in-sak-mkpdu {
      type srl_nokia-comm:zero-based-counter64;
      description
        "Validated and installed MKPDU received SAK count";
    }
    leaf out-sak-mkpdu {
      type srl_nokia-comm:zero-based-counter64;
      description
        "Validated and installed MKPDU transmit SAK count";
    }
    leaf in-cak-mkpdu {
      type srl_nokia-comm:zero-based-counter64;
      description
        "Validated MKPDU received CAK count";
    }
    leaf out-mkpdu {
      type srl_nokia-comm:zero-based-counter64;
      description
        "MKPDU sent count";
    }
    leaf out-cak-mkpdu {
      type srl_nokia-comm:zero-based-counter64;
      description
        "MKPDU CAK sent count";
    }
    leaf peers-removed {
      type srl_nokia-comm:zero-based-counter64;
      description
        "Indicates the number of peers removed from the live/potential peer

         Peer removed due to not receiving an MKPDU within the MKA Live Time (6.0 sec).";
    }
    leaf ckn-not-found {
      type srl_nokia-comm:zero-based-counter64;
      description
        "Indicates the number of MKPDUs received with a CKN that does not match the CA configured for the port.";
    }
    leaf new-live-peer {
      type srl_nokia-comm:zero-based-counter64;
      description
        "Indicates the number of validated peers that have been added to the live peer list.";
    }
    leaf parameter-size-invalid {
      type srl_nokia-comm:zero-based-counter64;
      description
        "Indicates the number of MKPDUs received which contain a parameter set body length that exceeds the remaining length of the MKPDU.";
    }
    leaf liveness-check-fail {
      type srl_nokia-comm:zero-based-counter64;
      description
        "Indicates the number of MKPDUs received which contain an MN that is not acceptably recent.";
    }
    leaf parameter-not-quad-size {
      type srl_nokia-comm:zero-based-counter64;
      description
        "Indicates the number of MKPDUs received which contain a parameter set that is not a multiple of 4 octets.";
    }
    leaf unsupported-algorithm-agility {
      type srl_nokia-comm:zero-based-counter64;
      description
        "Indicates the number of MKPDUs received which contain an unsupported Algorithm Agility value.";
    }
    leaf invalid-ckn-length {
      type srl_nokia-comm:zero-based-counter64;
      description
        "Indicates the number of MKPDUs received which contain a CAK name that exceeds the maximum CAK name length.";
    }
    leaf peer-same-mi {
      type srl_nokia-comm:zero-based-counter64;
      description
        "Indicates the number of MKPDUs received which contain a peerlist with an MI entry which conflicts with the local MI.";
    }
    leaf sak-non-live-peer {
      type srl_nokia-comm:zero-based-counter64;
      description
        "Indicates the number of SAKs received from a peer that is not a member of the Live Peers List.";
    }
    leaf sak-no-key-server {
      type srl_nokia-comm:zero-based-counter64;
      description
        "Indicates the number of SAKs received from a none key server MKA participant";
    }
    leaf key-number-invalid {
      type srl_nokia-comm:zero-based-counter64;
      description
        "Indicates the number of SAKs received with an invalid Key Number";
    }
    leaf cak-info-missing {
      type srl_nokia-comm:zero-based-counter64;
      description
        "Indicates the number of times internal CAK data is not available for the generation of the SAK.";
    }
    leaf max-peers-set-zero {
      type srl_nokia-comm:zero-based-counter64;
      description
        "Indicates the number of SecY SAK installations that have failed

         Failed due to the max peer entry being set to 0.";
    }
  }

  grouping macsec-interface-config {
    description
      "Media Access Control Security (MACsec) config grouping";
    leaf admin-state {
      type srl_nokia-comm:admin-state;
      default "disable";
      description
        "Enable MACsec on an interface";
    }
    container replay-protection {
      leaf admin-state {
        type srl_nokia-comm:admin-state;
        default "disable";
        description
          "Enable MACsec on an interface";
      }
      leaf window-size {
        type uint16;
        default "0";
        description
          "MACsec window size, as defined by the number of out-of-order frames that are accepted.

           A value of 0 means that frames are accepted only in the correct order.";
      }
      description
        "Enter the replay-protection context";
    }
    leaf rx-must-be-macsec-enabled {
      type boolean;
      default "true";
      description
        "when true; only accept macsec with sectag packets,

         If false accept a mix of macsec and clear text packets";
    }
    list exclude-protocols {
      key "protocol";
      leaf protocol {
        type protocols;
        description
          "exclude this protocol";
      }
      description
        "protocols to be excluded from macsec";
    }
    list exclude-mac {
      key "destination-mac";
      leaf destination-mac {
        type srl_nokia-comm:mac-address;
        description
          "exclude this destination mac from encryption";
      }
      description
        "list of destination macs to be excluded from the macsec encryption";
    }
    leaf oper-state {
      type srl_nokia-comm:oper-state;
      config false;
      description
        "Indicates the operational state of macsec on this subinterface";
    }
  }

  grouping macsec-mka-policy-top {
    description
      "MKA policy top level grouping";
    list policy {
      key "name";
      description
        "List of MKA policies";
      leaf name {
        type srl_nokia-comm:name;
        description
          "Name of the MKA policy";
      }
      uses macsec-mka-policy-config;
    }
  }

  grouping macsec-mka-interface-config {
    description
      "MKA interface config grouping";
    leaf mka-policy {
      type leafref {
        path "../../../mka/policy/name";
      }
      description
        "Apply MKA policy on the interface";
    }
    leaf key-chain {
      type leafref {
        path "/srl_nokia-system:system/srl-keychain:authentication/srl-keychain:keychain/srl-keychain:name";
      }
      must '/srl_nokia-system:system/srl-keychain:authentication/srl-keychain:keychain[srl-keychain:name = current()]'
         + '/srl-keychain:type = "macsec"' {
        error-message "Only keychain of type macsec can be assigned";
      }
    }
    leaf fallback-key-chain {
      type leafref {
        path "/srl_nokia-system:system/srl-keychain:authentication/srl-keychain:keychain/srl-keychain:name";
      }
      if-feature "srl_nokia-feat:macsec-fallback-keychain";
      must '/srl_nokia-system:system/srl-keychain:authentication/srl-keychain:keychain[srl-keychain:name = current()]'
         + '/srl-keychain:type = "macsec-fallback"' {
        error-message "Only keychain of type macsec-fallback can be assigned";
      }
    }
  }

  grouping macsec-scsa-tx-interface-state {
    description
      "State leaves assigned with the TX Secure Channel and Secure
       Association";
    leaf sci-tx-identifier {
      type sci-hex-string;
      description
        "Secure Channel Identifier

         Every Transmit Channel is uniquely identified using this field.";
    }
  }

  grouping macsec-scsa-tx-interface-stats {
    description
      "TX Secure Channel and Secure Association Information";
    leaf sc-auth-only {
      type srl_nokia-comm:zero-based-counter64;
      description
        "Secure Channel Authenticated only TX Packets counter

         This counter reflects the number of authenticated only transmitted
         packets in a secure channel.";
    }
    leaf sc-encrypted {
      type srl_nokia-comm:zero-based-counter64;
      description
        "Secure Channel Encrypted TX Packets counter

         This counter reflects the number of encrypted and authenticated
         transmitted packets in a secure channel.";
    }
    leaf sc-octets-auth-only {
      type srl_nokia-comm:zero-based-counter64;
      description
        "Secure Channel Authenticated only TX octets counter

         This counter reflects the number of authenticated only transmitted
         octets in a secure channel.";
    }
    leaf sc-octets-encrypted {
      type srl_nokia-comm:zero-based-counter64;
      description
        "Secure Channel Encrypted TX octets counter

         This counter reflects the number of encrypted and authenticated
         transmitted octets in a secure channel.";
    }
    leaf sc-sak-installed-count {
      type srl_nokia-comm:zero-based-counter64;
      description
        "Secure Channel installed TX SAKs count

         This counter reflects the number of SAKs that are installed in TX security channel.";
    }
    list security-association {
      key "tx-sa-an";
      description
        "Enter the transmitting-sa list instance";
      leaf tx-sa-an {
        type uint32;
        description
          "Indicates the AN for identifying the transmitting SA";
      }
      leaf sa-auth-only {
        type srl_nokia-comm:zero-based-counter64;
        description
          "Secure Association Authenticated only TX Packets counter

           This counter reflects the number of authenticated only, transmitted
           packets in a secure association.";
      }
      leaf sa-encrypted {
        type srl_nokia-comm:zero-based-counter64;
        description
          "Secure Association (SA) encrypted Packets counter

           This counter reflects the number of encrypted and authenticated transmitted packets in a secure association.";
      }
      leaf sa-sak-installed {
        type boolean;
        description
          "Secure Association (SA) TX sak installed

           This counter reflects if the TX SAK is installed for this SA.";
      }
    }
  }

  grouping macsec-scsa-rx-interface-state {
    description
      "State associated with RX Secure Channel and Secure Association Information";
    leaf sci-rx-identifier {
      type sci-hex-string;
      description
        "Secure Channel Identifier

         Every Receive Channel is uniquely identified using this field.";
    }
  }

  grouping macsec-scsa-rx-interface-stats {
    description
      "RX Secure Channel and Secure Association Information";
    leaf sc-invalid {
      type srl_nokia-comm:zero-based-counter64;
      description
        "Invalid Secure Channel RX Packets counter

         This counter reflects the number of invalid received packets in a
         secure channel.
         Indicates the summation of counter /macsec/rx-sa/not-valid-packets
         information for all the SAs which belong to this SC.";
    }
    leaf sc-valid {
      type srl_nokia-comm:zero-based-counter64;
      description
        "Valid Secure Channel RX Packets counter

         This counter reflects the number of valid received packets in a
         secure channel.
         Indicates the summation of counter /macsec/rx-sa/ok-packets
         information for all the SAs which belong to this SC.";
    }
    leaf sc-octets-invalid {
      type srl_nokia-comm:zero-based-counter64;
      description
        "Invalid Secure Channel RX Packets counter

         This counter reflects the number of invalid received packets in a
         secure channel.";
    }
    leaf sc-octets-valid {
      type srl_nokia-comm:zero-based-counter64;
      description
        "Valid Secure Channel RX Packets counter

         This counter reflects the number of valid received packets in a
         secure channel.
         Indicates the number of octets of plain text recovered from
         received packets that were integrity protected and encrypted.";
    }
    leaf not-using-sa-packets {
      type srl_nokia-comm:zero-based-counter64;
      units "packets";
      description
        "Indicates the summation of counter /macsec/rx-sa/not-using-sa-packets

         Information for all the SAs which belong to this SC.";
    }
    leaf late-packets {
      type srl_nokia-comm:zero-based-counter64;
      units "packets";
      description
        "Indicates the number of received packets that have been discarded due to replay window protection on this SC";
    }
    leaf delayed-packets {
      type srl_nokia-comm:zero-based-counter64;
      units "packets";
      description
        "Indicates the number of received packets with the condition that the PN of the packets is lower than the lower bound of the replay protection PN";
    }
    leaf unchecked-packets {
      type srl_nokia-comm:zero-based-counter64;
      units "packets";
      description
        "Indicates the number of packets that have failed the integrity check on this SC";
    }
    leaf sc-sak-installed-count {
      type srl_nokia-comm:zero-based-counter64;
      description
        "Secure Channel installed RX SAKs count

         This counter reflects the number of SAKs that are installed in RX security channel.";
    }
    list security-association {
      key "rx-sa-an";
      description
        "Enter the receiving-sa list instance";
      leaf rx-sa-an {
        type uint32;
        description
          "Indicates the AN for identifying the receiving SA";
      }
      leaf sa-invalid {
        type srl_nokia-comm:zero-based-counter64;
        description
          "Invalid Secure Association RX Packets counter

           This counter reflects the number of integrity check fails for received packets in a secure association.";
      }
      leaf discarded-inactive {
        type srl_nokia-comm:zero-based-counter64;
        units "packets";
        description
          "Indicates the number of received packets that have been discarded on this SA which is not currently in use.";
      }
      leaf discarded-active {
        type srl_nokia-comm:zero-based-counter64;
        units "packets";
        description
          "Indicates the number of not valid packets that have been discarded on this active SA.";
      }
      leaf sa-valid {
        type srl_nokia-comm:zero-based-counter64;
        description
          "Secure Association Valid RX Packets counter

           This counter reflects the number of packets in a secure association that passed integrity check.";
      }
      leaf sa-sak-installed {
        type boolean;
        description
          "Secure Association (SA) RX sak installed

           This counter reflects if the RX SAK is installed for this SA.";
      }
    }
  }

  grouping macsec-interface-counters {
    description
      "MACsec interface state grouping";
    leaf tx-untagged-pkts {
      type srl_nokia-comm:zero-based-counter64;
      description
        "MACsec interface level Transmit untagged Packets counter

         This counter will increment if MACsec is enabled on interface and the outgoing packet is not tagged with MACsec header.";
    }
    leaf tx-too-long-packets {
      type srl_nokia-comm:zero-based-counter64;
      units "packets";
      description
        "Indicates the number of transmitted packets discarded because of long lenght

         The packet length is greater than the Maximum Transmission Unit (MTU) of the Ethernet physical interface.";
    }
    leaf rx-untagged-pkts {
      type srl_nokia-comm:zero-based-counter64;
      description
        "MACsec interface level Receive untagged Packets counter

         This counter will increment if MACsec is enabled on interface and the incoming packet does not have MACsec tag.";
    }
    leaf rx-badtag-pkts {
      type srl_nokia-comm:zero-based-counter64;
      description
        "MACsec interface level Receive Bad Tag Packets counter

         This counter will increment if MACsec is enabled on interface and incoming packet has incorrect MACsec tag.";
    }
    leaf rx-unknownsci-pkts {
      type srl_nokia-comm:zero-based-counter64;
      description
        "MACsec interface level Receive Unknown SCI Packets counter

         This counter will increment if MACsec is enabled on the interface and SCI present in the MACsec tag of the incoming packet does not match any SCI present in ingress SCI table.";
    }
    leaf rx-nosci-pkts {
      type srl_nokia-comm:zero-based-counter64;
      description
        "MACsec interface level Receive No SCI Packets counter

         This counter will increment if MACsec is enabled on interface and incoming packet does not have SCI field in MACsec tag.";
    }
    leaf rx-overrun-packets {
      type srl_nokia-comm:zero-based-counter64;
      units "packets";
      description
        "Indicates the number of packets discarded because the number of received packets exceeded the cryptographic performance capabilities";
    }
  }

  grouping macsec-scsa-interface-top {
    description
      "Secure channel and Secure Association Statistics";
    list scsa-tx {
      key "sci-tx";
      config false;
      description
        "TX Secure Channel and Secure Association Statistics";
      leaf sci-tx {
        type sci-hex-string;
        description
          "TX Secure Channel and Secure Association Statistics";
      }
      uses macsec-scsa-tx-interface-state;
      uses macsec-scsa-tx-interface-stats;
    }
    list scsa-rx {
      key "sci-rx";
      config false;
      description
        "RX Secure Channel and Secure Association Statistics";
      leaf sci-rx {
        type sci-hex-string;
        description
          "RX Secure Channel and Secure Association Statistics";
      }
      uses macsec-scsa-rx-interface-state;
      uses macsec-scsa-rx-interface-stats;
    }
  }

  grouping macsec-mka-interface-top {
    description
      "MKA interface top level grouping";
    container mka {
      description
        "Enter the mka context

         Enclosing container for the MKA interface";
      uses macsec-mka-interface-config;
      uses macsec-mka-interface-state;
    }
  }

  grouping macsec-interface-top {
    list interface {
      key "name";
      description
        "List of interfaces on which MACsec is enabled / available
         When interface is configured the entire interface is protected via macsec.";
      leaf name {
        type srl_nokia-comm:name;
        description
          "Name of the interface being created for the MACSec";
      }
      container interface-ref {
        leaf interface {
          mandatory true;
          type leafref {
            path "/srl_nokia-if:interface/srl_nokia-if:name";
          }
          must "starts-with(.,'eth')" {
            error-message "Ethernet interfaces only";
          }
          description
            "Reference to a base interface, for example a port";
        }
        leaf subinterface {
          if-feature "srl_nokia-feat:macsec-subinterface";
          type uint32 {
            range "0..9999";
          }
          must '(../aggregate-id and /srl_nokia-if:interface[srl_nokia-if:name=current()/../aggregate-id]/srl_nokia-if:subinterface[srl_nokia-if:index=current()]) or (not(../aggregate-id) and /srl_nokia-if:interface[srl_nokia-if:name=current()/../interface]/srl_nokia-if:subinterface[srl_nokia-if:index=current()])' {
            error-message "Subinterface must exist under the referenced interface or aggregate";
          }
          description
            "Reference to a subinterface

             This requires the base interface to be specified using the interface leaf in this container.";
        }
        leaf aggregate-id {
          if-feature "srl_nokia-feat:lag";
          if-feature "srl_nokia-feat:macsec-lag-subinterface";
          type leafref {
            path "/srl_nokia-if:interface[srl_nokia-if:name=current()/../interface]/srl_nokia-if:ethernet/srl_nokia-if:aggregate-id";
          }
          must '../subinterface' {
            error-message "aggregate-id can only be configured when subinterface is specified";
          }
          description
            "Reference to the aggregate-id configured on the interface";
        }
        description
          "Enter the interface-ref context";
      }
      uses macsec-interface-config;
      container statistics {
        config false;
        description
          "Enter the statistics context

           MACsec interface counters";
        uses macsec-interface-counters;
      }
      uses macsec-scsa-interface-top;
      uses macsec-mka-interface-top;
    }
  }

  grouping macsec-mka-top {
    description
      "MKA top level grouping";
    container mka {
      description
        "Enter the mka context

         The MKA";
      uses macsec-mka-policy-top;
      uses macsec-mka-global-top;
    }
  }

  grouping macsec-top {
    container macsec {
      if-feature "srl_nokia-feat:macsec";
      uses macsec-mka-top;
      uses macsec-interface-top;
      description
        "Enter the macsec context";
    }
  }

  augment "/srl_nokia-transport-security:transport-security" {
    uses macsec-top;
  }
}
