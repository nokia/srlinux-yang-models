module srl_nokia-transport-security {
  yang-version 1.1;
  namespace "urn:nokia.com:srlinux:macsec:transport-security";
  prefix srl_nokia-security;

  import srl_nokia-extensions {
    prefix srl-ext;
  }
  import srl_nokia-common {
    prefix srl-comm;
  }
  import srl_nokia-features {
    prefix srl_nokia-feat;
  }

  organization
    "Nokia";
  contact
    "Nokia SR Linux Support
     Web: <http://www.nokia.com>";
  description
    "This module defines configuration and operational state data related to security, including macsec and future transport encryption";

  revision 2026-07-31 {
    description
      "SRLinux 26.7.1";
  }
  revision 2023-03-31 {
    description
      "SRLinux 23.3.1";
  }

  grouping transport-security-top {
    description
      "Top-level configuration and state for transport-security.";
    container transport-security {
      if-feature "srl_nokia-feat:macsec";
      description
        "Enter the transport-security context

         Enclosing container for transport security";
    }
  }

  uses transport-security-top;
}
