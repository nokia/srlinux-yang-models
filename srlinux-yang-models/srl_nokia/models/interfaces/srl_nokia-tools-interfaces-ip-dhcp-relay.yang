module srl_nokia-tools-interfaces-ip-dhcp-relay {
  yang-version 1.1;
  namespace "urn:nokia.com:srlinux:dhcp-relay:tools-interfaces-ip-dhcp-relay";
  prefix srl_nokia-tools-interfaces-ip-dhcp-relay;

  import srl_nokia-tools-interfaces {
    prefix srl_nokia_tools-if;
  }

  organization
    "Nokia";
  contact
    "Nokia SR Linux Support
     Web: <http://www.nokia.com>";
  description
    "Model for interface ip dhcp relay operational commands";

  revision 2026-07-31 {
    description
      "SRLinux 26.7.1";
  }
  revision 2021-06-30 {
    description
      "SRLinux 21.6.1";
  }
  revision 2021-03-31 {
    description
      "SRLinux 21.3.1";
  }
  revision 2020-06-30 {
    description
      "SRLinux 20.6.1";
  }

  grouping tools-interface-ip-dhcp-relay-top {
    container dhcp-relay {
      presence "Dhcp relay is enabled";
      container statistics {
        leaf clear {
          type empty;
        }
        description
          "Enter the statistics context";
      }
    }
  }

  augment "/srl_nokia_tools-if:interface/srl_nokia_tools-if:subinterface/srl_nokia_tools-if:ipv4" {
    uses tools-interface-ip-dhcp-relay-top;
  }

  augment "/srl_nokia_tools-if:interface/srl_nokia_tools-if:subinterface/srl_nokia_tools-if:ipv6" {
    uses tools-interface-ip-dhcp-relay-top;
  }
}
