module srl_nokia-tools-interfaces {
  yang-version 1.1;
  namespace "urn:nokia.com:srlinux:chassis:tools-interfaces";
  prefix srl_nokia-tools-if;

  import srl_nokia-features {
    prefix srl_nokia-feat;
  }
  import srl_nokia-common {
    prefix srl_nokia-comm;
  }

  organization
    "Nokia";
  contact
    "Nokia SR Linux Support
     Web: <http://www.nokia.com>";
  description
    "Model for operational commands on network interfaces and subinterfaces.";

  revision 2026-07-31 {
    description
      "SRLinux 26.7.1";
  }
  revision 2022-11-30 {
    description
      "SRLinux 22.11.1";
  }
  revision 2021-06-30 {
    description
      "SRLinux 21.6.1";
  }
  revision 2021-03-31 {
    description
      "SRLinux 21.3.1";
  }
  revision 2020-06-30 {
    description
      "SRLinux 20.6.1";
  }
  revision 2019-11-30 {
    description
      "SRLinux 19.11.1";
  }

  grouping tools-subinterface-top {
    description
      "Subinterface data for logical interfaces associated with a given interface";
    list subinterface {
      key "index";
      description
        "The list of subinterfaces (logical interfaces) associated with a physical interface";
      leaf index {
        type uint32;
        description
          "The index of the subinterface, or logical interface number";
      }
      container statistics {
        leaf clear {
          type empty;
        }
        description
          "Enter the statistics context";
      }
      container ipv4 {
        list address {
          key "ip-prefix";
          leaf ip-prefix {
            type srl_nokia-comm:ipv4-prefix-with-host-bits;
          }
        }
        description
          "Enter the ipv4 context";
      }
      container ipv6 {
        list address {
          key "ip-prefix";
          leaf ip-prefix {
            type srl_nokia-comm:ipv6-prefix-with-host-bits;
          }
        }
        description
          "Enter the ipv6 context";
      }
      container bridge-table {
        description
          "Enter the bridge-table context";
      }
    }
  }

  grouping tools-interface-top {
    description
      "Top-level grouping for interface configuration and operational state data";
    list interface {
      key "name";
      description
        "The list of named interfaces on the device.";
      leaf name {
        type string;
        description
          "References the configured name of the interface";
      }
      container statistics {
        container clear {
          presence "Clear interface statistics";
          description
            "Clear interface statistics";
          leaf include-members {
            if-feature "srl_nokia-feat:lag";
            must "starts-with(../../../name,'lag')" {
              error-message "Must be used with a LAG interface";
            }
            type empty;
            description
              "Causes the member link statistics to also be cleared";
          }
        }
        description
          "Enter the statistics context";
      }
      container ethernet {
        container statistics {
          container clear {
            presence "Clear interface ethernet statistics";
            description
              "Clear interface ethernet statistics";
            leaf include-members {
              if-feature "srl_nokia-feat:lag";
              must "starts-with(../../../../name,'lag')" {
                error-message "Must be used with a LAG interface";
              }
              type empty;
              description
                "Causes the member link ethernet statistics to also be cleared";
            }
          }
          description
            "Enter the statistics context";
        }
        description
          "Enter the ethernet context";
      }
      container resource {
        presence "resource interface tools";
        if-feature "srl_nokia-feat:lag";
        must "starts-with(../name,'lag')" {
          error-message "Must be used with a LAG interface";
        }
        leaf retry {
          type empty;
          description
            "Causes the specified lag to be reevaluate for missing system resources";
        }
      }
      container transceiver {
        presence "tools interface transceiver";
        if-feature "srl_nokia-feat:transceiver-reset or srl_nokia-feat:transceiver-removal";
        description
          "Tools related to individual transceivers";
        container reset {
          if-feature "srl_nokia-feat:transceiver-reset";
          presence "Required due to mandatory statements";
          description
            "Reset the transceiver";
          must "starts-with(../../name, 'ethernet')" {
            error-message "reset not supported for this interface type";
          }
        }
        container simulate-removal {
          if-feature "srl_nokia-feat:transceiver-removal";
          presence "Required due to mandatory statements";
          description
            "Simulate the transceiver being physically removed

             When enabled, the system behaves as if the transceiver were not
             present in the cage. Useful for fault-injection and testing.";
          must "starts-with(../../name, 'ethernet')" {
            error-message "simulate-removal not supported for this interface type";
          }
          choice action {
            mandatory true;
            case enable {
              container enable {
                presence "Activate simulated removal of the transceiver";
                description
                  "Activate simulated removal of the transceiver";
              }
            }
            case disable {
              container disable {
                presence "Deactivate simulated removal of the transceiver";
                description
                  "Deactivate simulated removal of the transceiver";
              }
            }
          }
        }
      }
      uses tools-subinterface-top;
    }
  }

  uses tools-interface-top;
}
