module srl_nokia-tools-interfaces-nbr {
  yang-version 1.1;
  namespace "urn:nokia.com:srlinux:arp-nd:tools-interfaces-nbr";
  prefix srl_nokia-tools-if-nbr;

  import srl_nokia-tools-interfaces {
    prefix srl_nokia_tools-if;
  }
  import srl_nokia-common {
    prefix srl_nokia-comm;
  }

  organization
    "Nokia";
  contact
    "Nokia SR Linux Support
     Web: <http://www.nokia.com>";
  description
    "Model for operational commands on ARP and ND tables.";

  revision 2019-11-30 {
    description
      "SRLinux 19.11.1";
  }

  grouping arp-top {
    container arp {
      presence "IPv4 ARP protocol is enabled";
      must "not(starts-with(../../../srl_nokia_tools-if:name, 'lo') or starts-with(../../../srl_nokia_tools-if:name, 'system'))" {
        error-message "ARP is not supported on loopback or system interfaces";
      }
      list neighbor {
        key "ipv4-address";
        leaf ipv4-address {
          type srl_nokia-comm:ipv4-address;
          description
            "IPv4 address resolved by the ARP entry";
        }
        leaf delete-dynamic {
          type empty;
          description
            "Delete one specific dynamic ARP entry";
        }
      }
      leaf delete-dynamic {
        type empty;
        description
          "Delete all dynamic ARP entries";
      }
    }
  }

  grouping nd-top {
    container neighbor-discovery {
      presence "IPv6 ND protocol is enabled";
      must "not(starts-with(../../../srl_nokia_tools-if:name, 'lo') or starts-with(../../../srl_nokia_tools-if:name, 'system'))" {
        error-message "ND is not supported on loopback or system interfaces";
      }
      list neighbor {
        key "ipv6-address";
        leaf ipv6-address {
          type srl_nokia-comm:ipv6-address;
          description
            "IPv6 address resolved by the ND cache entry";
        }
        leaf delete-dynamic {
          type empty;
          description
            "Delete one specific dynamic neighbor cache entry";
        }
      }
      leaf delete-dynamic {
        type empty;
        description
          "Delete all dynamic neighbor cache entries";
      }
    }
  }

  augment "/srl_nokia_tools-if:interface/srl_nokia_tools-if:subinterface/srl_nokia_tools-if:ipv4" {
    uses arp-top;
  }

  augment "/srl_nokia_tools-if:interface/srl_nokia_tools-if:subinterface/srl_nokia_tools-if:ipv6" {
    uses nd-top;
  }
}
