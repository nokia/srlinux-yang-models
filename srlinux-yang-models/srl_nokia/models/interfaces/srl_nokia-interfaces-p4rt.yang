module srl_nokia-interfaces-p4rt {
  yang-version 1.1;

  // namespace

  namespace "urn:nokia.com:srlinux:chassis:interfaces-p4rt";
  prefix srl_nokia-if-p4rt;

  import srl_nokia-interfaces {
    prefix srl_nokia-if;
  }
  import srl_nokia-extensions {
    prefix srl_nokia-ext;
  }
  import srl_nokia-features {
    prefix srl_nokia-feat;
  }

  organization
    "Nokia";
  contact
    "Nokia SR Linux Support
     Web: <http://www.nokia.com>";
  description
    "Model for managing P4Runtime configuration and state underneath interfaces.";

  revision 2022-03-31 {
    description
      "SR Linux 22.3.1";
  }

  // identity statements
  // typedef statements

  grouping p4rt-interface {
    description
      "Interface configuration and state data relating to P4Runtime";
    container p4rt {
      presence "Enable P4Runtime";
      if-feature "srl_nokia-feat:p4rt";
      must "starts-with(../srl_nokia-if:name, 'ethernet') or starts-with(../srl_nokia-if:name, 'lag')" {
        error-message "not supported for this interface type";
      }
      must 'not(../breakout-mode)' {
        error-message "not supported when breakout-mode is enabled";
      }
      description
        "Top-level container for P4Runtime interface configuration and state";
      leaf id {
        srl_nokia-ext:show-importance "high";
        type uint32 {
          range "1..max";
        }
        description
          "The numeric identifier used by the controller to address the interface

           This ID is the interface ifIndex by default, or is assigned by an
           external-to-the-device entity (e.g., an SDN management system) to
           establish an externally deterministic numeric reference for the interface.

           The programming entity must ensure that the ID is unique within the
           required context.

           Note that this identifier is used only when a numeric reference to the
           interface is required, it does not replace the unique name assigned to
           the interface.";
      }
      leaf parent-id {
        srl_nokia-ext:show-importance "high";
        config false;
        type uint64;
        description
          "The numeric ID used by the controller to address the ASIC this interface resides on

           This is the ID configured at /platform/linecard/forwarding-complex/p4rt/id.

           This ID may be referred to as a 'device', 'node' or 'target' by the P4RT
           specification.

           Each switching ASIC (i.e., node) is addressed by the external entity
           based on its numeric identifier.";
      }
    }
  }

  augment "/srl_nokia-if:interface" {
    uses p4rt-interface;
  }
}
