module srl_nokia-if-ip-tags {
  yang-version 1.1;
  namespace "urn:nokia.com:srlinux:chassis:if-ip-tags";
  prefix srl_nokia-if-ip-tags;

  import srl_nokia-features {
    prefix srl_feat;
  }
  import srl_nokia-routing-policy {
    prefix srl_nokia-rpol;
  }
  import srl_nokia-interfaces {
    prefix srl_nokia-if;
  }

  organization
    "Nokia";
  contact
    "Nokia SR Linux Support
     Web: <http://www.nokia.com>";
  description
    "Model for assigninf tags to IP subnets of local subinterfaces";

  revision 2026-07-31 {
    description
      "SRLinux 26.7.1";
  }

  grouping internal-tags {
    description
      "Grouping containing the configuration of internal tags";
    container internal-tags {
      description
        "Enter the internal-tags context

         Configuration and state of internal tags";
      leaf-list set-tag-set {
        max-elements 1;
        type leafref {
          path "/srl_nokia-rpol:routing-policy/srl_nokia-rpol:tag-set/srl_nokia-rpol:name";
        }
        description
          "Reference to a tag-set defined under routing-policy";
      }
    }
  }

  augment "/srl_nokia-if:interface/srl_nokia-if:subinterface/srl_nokia-if:ipv4/srl_nokia-if:address" {
    uses internal-tags;
    if-feature "srl_feat:subif-ip-tags and srl_feat:internal-tags";
  }

  augment "/srl_nokia-if:interface/srl_nokia-if:subinterface/srl_nokia-if:ipv6/srl_nokia-if:address" {
    uses internal-tags;
    if-feature "srl_feat:subif-ip-tags and srl_feat:internal-tags";
  }
}
