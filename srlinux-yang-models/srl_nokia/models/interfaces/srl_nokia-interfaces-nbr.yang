module srl_nokia-interfaces-nbr {
  yang-version 1.1;
  namespace "urn:nokia.com:srlinux:arp-nd:interfaces-nbr";
  prefix srl_nokia-if-ip-nbr;

  import srl_nokia-interfaces {
    prefix srl_nokia-if;
  }
  import srl_nokia-common {
    prefix srl_nokia-comm;
  }
  import srl_nokia-extensions {
    prefix srl_nokia-ext;
  }
  import srl_nokia-routing-policy {
    prefix srl_nokia-routing-pol;
  }
  import srl_nokia-features {
    prefix srl-feat;
  }
  import srl_nokia-ip-route-tables {
    prefix srl_nokia-route-tbl;
  }

  organization
    "Nokia";
  contact
    "Nokia SR Linux Support
     Web: <http://www.nokia.com>";
  description
    "Model for managing ARP and IPv6 neighbor discovery on IP subinterfaces.";

  revision 2026-07-31 {
    description
      "SRLinux 26.7.1";
  }
  revision 2025-10-31 {
    description
      "SRLinux 25.10.1";
  }
  revision 2025-03-31 {
    description
      "SRLinux 25.3.1";
  }
  revision 2024-10-31 {
    description
      "SRLinux 24.10.1";
  }
  revision 2024-03-31 {
    description
      "SRLinux 24.3.1";
  }
  revision 2023-10-31 {
    description
      "SRLinux 23.10.1";
  }
  revision 2023-07-31 {
    description
      "SRLinux 23.7.1";
  }
  revision 2023-03-31 {
    description
      "SRLinux 23.3.1";
  }
  revision 2022-03-31 {
    description
      "SRLinux 22.3.1";
  }
  revision 2021-03-31 {
    description
      "SRLinux 21.3.1";
  }
  revision 2020-06-30 {
    description
      "SRLinux 20.6.1";
  }
  revision 2019-11-30 {
    description
      "SRLinux 19.11.1";
  }

  typedef neighbor-origin {
    type enumeration {
      enum other {
        value 1;
      }
      enum static {
        value 2;
      }
      enum dynamic {
        value 3;
      }
      enum evpn {
        value 4;
        if-feature "srl-feat:evpn";
      }
      enum submgmt {
        value 5;
        if-feature "srl-feat:subscriber-management";
      }
      enum evpn-local-es {
        value 6;
        if-feature "srl-feat:evpn-rt2-proxy-irb";
      }
    }
    description
      "The origin of the neighbor entry.";
  }

  grouping route-internal-tags {
    description
      "Grouping containing the configuration of internal tags";
    container internal-tags {
      if-feature "srl-feat:internal-tags";
      description
        "Enter the internal-tags context

         Configuration and state of internal tags";
      leaf-list set-tag-set {
        max-elements 1;
        type leafref {
          path "/srl_nokia-routing-pol:routing-policy/srl_nokia-routing-pol:tag-set/srl_nokia-routing-pol:name";
        }
        description
          "Reference to a tag-set defined under routing-policy";
      }
    }
  }

  grouping datapath-programming-status {
    container datapath-programming {
      description
        "Enter the datapath-programming context

         Container for state related to the datapath programming of the ARP or neighbor entry";
      config false;
      leaf status {
        description
          "The status of the ARP or neighbor entry with respect to datapath programming";
        type enumeration {
          enum success {
            description
              "All linecard complexes have reported that the entry was programmed successfully";
          }
          enum failed {
            description
              "At least one linecard complex reported that the entry was not programmed successfully or else this entry was not even provided to the datapath for programming because the system limit on the number of IPv4 ARP and IPv6 neighbor entries was exceeded";
          }
          enum pending {
            description
              "The ARP or neighbor entry was provided to the datapath for programming but at least one linecard complex has not provided a status yet.";
          }
        }
      }
      leaf-list last-failed-complexes {
        description
          "List of forwarding complexes that reported a failure for the last operation. They appear in the format (slot-number,complex-number).";
        type srl_nokia-route-tbl:failed-complex-list-including-control;
      }
    }
  }

  grouping common-neighbor-discovery {
    leaf route-type {
      description
        "Controls what type of ARP or ND entries generate a host route.";
      type enumeration {
        enum static {
          value 1;
        }
        enum dynamic {
          value 2;
        }
        enum evpn {
          value 3;
          if-feature "srl-feat:evpn";
        }
        enum evpn-local-es {
          value 4;
          if-feature "srl-feat:evpn-rt2-proxy-irb";
          description
            "Generate host route for evpn local ethernet segment entries";
        }
      }
    }
    leaf datapath-programming {
      if-feature "srl-feat:arp-nd-datapath-programming";
      type boolean;
      description
        "When set to true, the host route is programmed in the datapath";
    }
    uses route-internal-tags;
  }

  grouping host-route-top {
    container host-route {
      description
        "Enter the host-route context

         Configure which types of ARP or ND entries will be populated in the route-table.";
      list populate {
        must "boolean(../../../neighbor-discovery) or (../../../unnumbered/admin-state != 'enable')" {
          error-message "host-route config is not allowed on ipv4 unnumbered interfaces";
        }
        key "route-type";
        uses common-neighbor-discovery;
      }
    }
  }

  grouping nbr-limit-top {
    container limit {
      description
        "Enter the limit context

         Container for the configuration of Neighbor-Discovery limit";
      leaf max-entries {
        type uint32;
        description
          "The maximum number of neighbor entries allowed on the subinterface

           If not configured, the amount of neighbor entries on the subinterface
           is only limited by the total amount of entries supported by the router.";
      }
      leaf log-only {
        type boolean;
        default "false";
        description
          "Generate only a log message when limit is reached

           When set to true, neighbor entries are still being learned after
           exceeding the max-entries limit.";
      }
      leaf warning-threshold-pct {
        type uint32 {
          range "1..100";
        }
        units "percent";
        default "90";
        description
          "Threshold percentage of the configured maximum number of entries

           When exceeded, an event is triggered.";
      }
    }
  }

  grouping ipv4-nbr-top {
    container arp {
      description
        "Enter the arp context

         Container for the IPv4 ARP protocol";
      leaf duplicate-address-detection {
        type boolean;
        default "true";
        description
          "If set to true IPv4 Address Conflict Detection per RFC 5227 is performed on the IPv4 address assigned to the subinterface";
      }
      leaf timeout {
        type uint16 {
          range "60..65535";
        }
        units "seconds";
        default "14400";
        description
          "Duration of time that dynamic ARP entries remain in the ARP cache before they expire

           A change to this value does not affect existing entries until they are refreshed.";
      }
      leaf learn-unsolicited {
        type boolean;
        default "false";
        description
          "If set to true an ARP entry should be learned from any received ARP packets.";
      }
      list neighbor {
        srl_nokia-ext:show-importance "high";
        key "ipv4-address";
        description
          "List of static and dynamic ARP cache entries that map an IPv4 address to a MAC address

           To configure a static ARP entry a value must be written into this leaf and the link-layer-address leaf.";
        reference
          "RFC 826: An Ethernet Address Resolution Protocol";
        leaf ipv4-address {
          type srl_nokia-comm:ipv4-address;
          description
            "IPv4 address resolved by the ARP entry

             To configure a static neighbor entry a value must be written into this leaf and the link-layer-address leaf.";
        }
        leaf link-layer-address {
          type srl_nokia-comm:mac-address;
          mandatory true;
          description
            "The resolving MAC address of the ARP entry

             To configure a static ARP entry a value must be written into this leaf and the ipv4-address leaf.";
        }
        leaf origin {
          config false;
          type neighbor-origin;
          description
            "The origin of the ARP entry";
        }
        leaf expiration-time {
          config false;
          type srl_nokia-comm:date-and-time-delta;
          description
            "The date and time when the dynamic ARP entry is set to expire";
        }
        leaf group-based-policy-tag {
          config false;
          type uint16 {
            range "0..65535";
          }
          description
            "The group-based-policy tag value associated to this arp entry";
        }
        uses datapath-programming-status;
        action delete-dynamic {
          if-feature "srl-feat:tools-as-modeled-actions-same-output";
          description
            "Delete one specific dynamic ARP entry";
        }
      }
      uses host-route-top;
      leaf proxy-arp {
        if-feature "srl-feat:l3-proxy-arp";
        must "not (current() and starts-with(../../../../srl_nokia-if:name,'irb'))" {
          error-message "Not supported on IRB subinterfaces";
          srl_nokia-ext:if-feature "not srl_nokia-feat:l3-proxy-arp-irb";
        }
        type boolean;
        default "false";
        description
          "When set to true, the router replies with its own MAC to ARP Request destined to any host.";
      }
      leaf-list debug {
        type enumeration {
          enum messages {
            description
              "Capture all arp-request and reply-messages sent and received by the subinterface";
          }
        }
        description
          "List of events to debug";
      }
      action delete-dynamic {
        if-feature "srl-feat:tools-as-modeled-actions-same-output";
        description
          "Delete all dynamic ARP entries";
      }
    }
  }

  augment "/srl_nokia-if:interface/srl_nokia-if:subinterface/srl_nokia-if:ipv4" {
    description
      "IPv4 addr family configuration for interfaces";
    uses ipv4-nbr-top;
  }

  grouping ipv6-nbr-top {
    container neighbor-discovery {
      description
        "Enter the neighbor-discovery context

         Container for the IPv6 Neighbor Discovery protocol";
      leaf duplicate-address-detection {
        type boolean;
        default "true";
        description
          "Enables Duplicate Addres Detection on all tentative addresses

           This applies to link-local and global unicast addresses. Only one transmission is done; there are no retransmissions.

           Must be true on an IPv6 subinterface that has dhcp-client enabled.";
      }
      leaf reachable-time {
        type uint32 {
          range "30..3600";
        }
        units "seconds";
        default "30";
        description
          "The period of time that a dynamic IPv6 neighbor cache entry is considered reachable after a reachability confirmation event

           After this time expires the neighbor state moves to STALE.";
      }
      leaf stale-time {
        type uint32 {
          range "60..65535";
        }
        units "seconds";
        default "14400";
        description
          "The maximum time that a dynamic IPv6 neighbor cache entry can remain in the STALE state before it is removed

           This limit is reached only if no traffic is sent/queued towards the neighbor during the entire duration of the timer.";
      }
      leaf learn-unsolicited {
        type enumeration {
          enum none {
            value 0;
          }
          enum global {
            value 1;
          }
          enum link-local {
            value 2;
          }
          enum both {
            value 3;
          }
        }
        default "none";
        description
          "Sets if neighbors should be learned from unsolicited neighbor advertisements for global or link local addresses or both.";
      }
      list neighbor {
        srl_nokia-ext:show-importance "high";
        key "ipv6-address";
        description
          "List of static and dynamic ND cache entries that map an IPv6 address to a MAC address";
        reference
          "RFC 4861: Neighbor Discovery for IP version 6 (IPv6)";
        leaf ipv6-address {
          type srl_nokia-comm:ipv6-address;
          description
            "IPv6 address resolved by the ND cache entry

             To configure a static neighbor entry a value must be written into this leaf and the link-layer-address leaf.";
        }
        leaf link-layer-address {
          type srl_nokia-comm:mac-address;
          mandatory true;
          description
            "The resolving MAC address of the ND cache entry

             To configure a static neighbor entry a value must be written into this leaf and the ipv6-address leaf.";
        }
        leaf origin {
          config false;
          type neighbor-origin;
          description
            "The origin of the neighbor cache entry.";
        }
        leaf is-router {
          config false;
          type boolean;
          description
            "Indicates that the neighbor node claims to be a router (R bit in the Neighbor Advertisement message)";
        }
        leaf current-state {
          config false;
          description
            "The Neighbor Unreachability Detection state";
          type enumeration {
            enum incomplete {
              value 0;
            }
            enum reachable {
              value 1;
            }
            enum stale {
              value 2;
            }
            enum delay {
              value 3;
            }
            enum probe {
              value 4;
            }
          }
        }
        leaf next-state-time {
          config false;
          type srl_nokia-comm:date-and-time-delta;
          description
            "The date and time when the neighbor state is expected to transition to the next state";
        }
        leaf group-based-policy-tag {
          config false;
          type uint16 {
            range "0..65535";
          }
          description
            "The group-based-policy tag value associated to this neighbor entry";
        }
        uses datapath-programming-status;
        action delete-dynamic {
          description
            "Delete one specific dynamic neighbor cache entry";
        }
      }
      uses host-route-top;
      uses nbr-limit-top;
      leaf proxy-nd {
        if-feature "srl-feat:l3-proxy-nd";
        must "not (current() and starts-with(../../../../srl_nokia-if:name,'irb'))" {
          error-message "Not supported on IRB subinterfaces";
          srl_nokia-ext:if-feature "not srl_nokia-feat:l3-proxy-nd-irb";
        }
        type boolean;
        default "false";
        description
          "When set to true, the router replies with its own MAC to Neighbor Solicitations destined to any host.";
      }
      leaf-list debug {
        type enumeration {
          enum messages {
            description
              "Capture all neighbor-solicitation and neighbor-advertisement messages sent and received by the subinterface";
          }
        }
        description
          "List of events to debug";
      }
      action delete-dynamic {
        description
          "Delete all dynamic neighbor cache entries";
      }
    }
  }

  augment "/srl_nokia-if:interface/srl_nokia-if:subinterface/srl_nokia-if:ipv6" {
    description
      "IPv6 address family configuration for interfaces";
    uses ipv6-nbr-top;
  }
}
