module srl_nokia-tools-interfaces-ip-vrrp {
  yang-version 1.1;
  namespace "urn:nokia.com:srlinux:vrrp:tools-interfaces-ip-vrrp";
  prefix srl_nokia-tools-interfaces-ip-vrrp;

  import srl_nokia-tools-interfaces {
    prefix srl_nokia_tools-if;
  }
  import srl_nokia-features {
    prefix srl_nokia-feat;
  }

  organization
    "Nokia";
  contact
    "Nokia SR Linux Support
     Web: <http://www.nokia.com>";
  description
    "Model for interface ip VRRP operational commands";

  revision 2026-07-31 {
    description
      "SRLinux 26.7.1";
  }
  revision 2022-11-30 {
    description
      "SRLinux 22.11.1";
  }
  revision 2021-06-30 {
    description
      "SRLinux 21.6.1";
  }
  revision 2021-03-31 {
    description
      "SRLinux 21.3.1";
  }
  revision 2020-06-30 {
    description
      "SRLinux 20.6.1";
  }

  grouping tools-interface-ip-vrrp-top {
    list vrrp-group {
      if-feature "srl_nokia-feat:vrrp";
      key "virtual-router-id";
      description
        "VRRP Group Specific Configuration under IPv4 context";
      leaf virtual-router-id {
        description
          "VRRP Group Index";
        type uint8;
      }
      container statistics {
        leaf clear {
          type empty;
        }
        description
          "Enter the statistics context";
      }
    }
  }

  augment "/srl_nokia_tools-if:interface/srl_nokia_tools-if:subinterface/srl_nokia_tools-if:ipv4/srl_nokia_tools-if:address" {
    uses tools-interface-ip-vrrp-top;
  }

  augment "/srl_nokia_tools-if:interface/srl_nokia_tools-if:subinterface/srl_nokia_tools-if:ipv6/srl_nokia_tools-if:address" {
    uses tools-interface-ip-vrrp-top;
  }
}
