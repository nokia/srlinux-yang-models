module srl_nokia-interfaces-l2cp {
  yang-version 1.1;
  namespace "urn:nokia.com:srlinux:chassis:interfaces-l2cp";
  prefix srl_nokia-interfaces-l2cp;

  import srl_nokia-common {
    prefix srl_nokia-comm;
  }
  import srl_nokia-interfaces {
    prefix srl_nokia-if;
  }
  import srl_nokia-interfaces-lag {
    prefix srl_nokia-if-lag;
  }
  import srl_nokia-lacp {
    prefix srl_nokia-lacp;
  }
  import srl_nokia-lldp {
    prefix srl_nokia-lldp;
  }
  import srl_nokia-features {
    prefix srl_nokia-feat;
  }
  import srl_nokia-extensions {
    prefix srl_nokia-ext;
  }
  import srl_nokia-system {
    prefix srl_nokia-system;
  }

  organization
    "Nokia";
  contact
    "Nokia SR Linux Support
     Web: <http://www.nokia.com>";
  description
    "This module defines configuration and operational state related to the Layer-2 Control Protocols";

  revision 2026-07-31 {
    description
      "SRLinux 26.7.1";
  }
  revision 2025-03-31 {
    description
      "SRLinux 25.3.1";
  }
  revision 2024-10-31 {
    description
      "SRLinux 24.10.1";
  }
  revision 2022-03-31 {
    description
      "SRLinux 22.3.1";
  }

  grouping l2cp-statistics {
    description
      "Grouping containing statistics for Layer-2 Control Plane protocols.";
    container l2cp-statistics {
      if-feature "srl_nokia-feat:l2cp-transparency-stats";
      config false;
      description
        "Enter the l2cp-statistics context

         Container for Layer-2 Control Plane protocol statistics.";
      leaf total-in-packets {
        type srl_nokia-comm:zero-based-counter64;
        description
          "System level total incoming L2CP frames.

           Cumulative of all Ethernet interfaces including the tunneled, discarded and copy-to-cpu
           L2CP frames. L2CP frames are identified by a destination MAC value of 01:80:c2:00:00:0X
           or 01:80:c2:00:00:2X, being X any value in the 0..F range.";
      }
      leaf total-in-discarded-packets {
        type srl_nokia-comm:zero-based-counter64;
        description
          "System level incoming L2CP discarded frames.

           Cumulative of all Ethernet interfaces including all the discarded L2CP frames. L2CP
           frames are identified by a destination MAC value of 01:80:c2:00:00:0X or
           01:80:c2:00:00:2X, being X any value in the 0..F range.";
      }
      leaf total-in-tunneled-packets {
        type srl_nokia-comm:zero-based-counter64;
        description
          "System level incoming L2CP tunneled frames.

           Cumulative of all Ethernet interfaces including all the tunneled L2CP frames. L2CP
           frames are identified by a destination MAC value of 01:80:c2:00:00:0X or
           01:80:c2:00:00:2X, being X any value in the 0..F range.";
      }
      leaf total-in-trap-to-cpu-packets {
        type srl_nokia-comm:zero-based-counter64;
        description
          "System level incoming L2CP copy-to-cpu frames.

           Cumulative of all Ethernet interfaces including all the L2CP frames that are copied
           to CPU. L2CP frames are identified by a destination MAC value of 01:80:c2:00:00:0X or
           01:80:c2:00:00:2X, being X any value in the 0..F range.";
      }
      leaf last-clear {
        type srl_nokia-comm:date-and-time-delta;
        description
          "Timestamp of the last time the L2CP counters were cleared.";
      }
      container lldp {
        description
          "Enter the lldp context

           Container for LLDP.";
        leaf in-tunneled-packets {
          type srl_nokia-comm:zero-based-counter64;
          description
            "System level incoming Link Layer Discovery Protocol tunneled frames.

             Cumulative of all Ethernet interfaces including all the tunneled LLDP frames. LLDP
             frames are identified by a destination MAC value of 01:80:c2:00:00:0e and EtherType value
             of 0x88cc.";
        }
        leaf in-trap-to-cpu-packets {
          type srl_nokia-comm:zero-based-counter64;
          description
            "System level incoming Link Layer Discovery Protocol frames copied to CPU.

             Cumulative of all Ethernet interfaces including all the copy-to-cpu LLDP frames. LLDP
             frames are identified by a destination MAC value of 01:80:c2:00:00:0e and EtherType value
             of 0x88cc.";
        }
        leaf last-clear {
          type srl_nokia-comm:date-and-time-delta;
          description
            "Timestamp of the last time the LACP counters were cleared.";
        }
      }
      container lacp {
        description
          "Enter the lacp context

           Container for LACP.";
        leaf in-tunneled-packets {
          type srl_nokia-comm:zero-based-counter64;
          description
            "System level incoming Link Aggregation Control Protocol tunneled frames.

             Cumulative of all Ethernet interfaces including all the tunneled LACP frames. LACP
             frames are identified by a destination MAC value of 01:80:c2:00:00:02, EtherType value
             of 0x8809 and slow protocol subtype 0x1.";
        }
        leaf in-trap-to-cpu-packets {
          type srl_nokia-comm:zero-based-counter64;
          description
            "System level incoming Link Aggregation Control Protocol frames copied to CPU.

             Cumulative of all Ethernet interfaces including all the copy-to-cpu LACP frames. LACP
             frames are identified by a destination MAC value of 01:80:c2:00:00:02, EtherType value
             of 0x8809 and slow protocol subtype 0x1.";
        }
        leaf last-clear {
          type srl_nokia-comm:date-and-time-delta;
          description
            "Timestamp of the last time the LACP counters were cleared.";
        }
      }
      container xstp {
        if-feature "srl_nokia-feat:l2cp-transparency-xstp";
        description
          "Enter the xstp context

           Container for Spanning Tree Protocols.";
        leaf in-tunneled-packets {
          type srl_nokia-comm:zero-based-counter64;
          description
            "System level incoming Spanning Tree tunneled frames.

             Cumulative of all Ethernet interfaces including all the tunneled Spanning Tree frames.
             xSTP frames are identified by a destination MAC value of 01:80:c2:00:00:00 and LLC value
             0x42.";
        }
        leaf in-trap-to-cpu-packets {
          type srl_nokia-comm:zero-based-counter64;
          description
            "System level incoming Spanning Tree Protocol frames copied to CPU.

             Cumulative of all Ethernet interfaces including all the copy-to-cpu Spanning Tree frames.
             Spanning Tree frames are identified by a destination MAC value of 01:80:c2:00:00:00 and
             LLC value 0x42.";
        }
        leaf last-clear {
          type srl_nokia-comm:date-and-time-delta;
          description
            "Timestamp of the last time the xSTP counters were cleared.";
        }
      }
      container ptp {
        description
          "Enter the ptp context

           Container for Precision Time Protocol Peer-Delay protocol.";
        leaf in-tunneled-packets {
          type srl_nokia-comm:zero-based-counter64;
          description
            "System level incoming Precision Time Protocol Peer-Delay tunneled frames.

             Cumulative of all Ethernet interfaces including all the tunneled PTP frames. PTP
             frames are identified by a destination MAC value of 01:80:c2:00:00:0e and Ethertype
             value of 0x88F7.";
        }
        leaf in-trap-to-cpu-packets {
          type srl_nokia-comm:zero-based-counter64;
          description
            "System level incoming Precision Time Protocol Peer-Delay frames copied to CPU.

             Cumulative of all Ethernet interfaces including all the copy-to-cpu PTP frames. PTP
             frames are identified by a destination MAC value of 01:80:c2:00:00:0e and Ethertype
             value of 0x88F7.";
        }
        leaf last-clear {
          type srl_nokia-comm:date-and-time-delta;
          description
            "Timestamp of the last time the PTP counters were cleared.";
        }
      }
      container esmc {
        if-feature "srl_nokia-feat:l2cp-transparency-esmc";
        description
          "Enter the esmc context

           Container for Ethernet Synchronization Messaging Channel protocol

           ESMC frames are identified by a Ethertype 0x8809 and slow protocol subtype 0x0A.";
        leaf in-tunneled-packets {
          type srl_nokia-comm:zero-based-counter64;
          description
            "System level incoming ESMC tunneled frames

             Cumulative of all Ethernet interfaces including all the tunneled ESMC frames. ";
        }
        leaf in-trap-to-cpu-packets {
          type srl_nokia-comm:zero-based-counter64;
          description
            "System level incoming ESMC frames copied to CPU

             Cumulative of all Ethernet interfaces including all the copy-to-cpu ESMC frames.";
        }
        leaf last-clear {
          type srl_nokia-comm:date-and-time-delta;
          description
            "Timestamp of the last time the ESMC counters were cleared";
        }
      }
      container elmi {
        if-feature "srl_nokia-feat:l2cp-transparency-elmi";
        description
          "Enter the elmi context

           Container for Ethernet local management interface frames

           ELMI frames are identified by MAC DA 01-80-C2-00-00-07 and Ethertype 0x88ee.";
        leaf in-tunneled-packets {
          type srl_nokia-comm:zero-based-counter64;
          description
            "System level incoming ELMI tunneled frames

             Cumulative of all Ethernet interfaces including all the tunneled ELMI frames.";
        }
        leaf in-trap-to-cpu-packets {
          type srl_nokia-comm:zero-based-counter64;
          description
            "System level incoming ELMI frames copied to CPU

             Cumulative of all Ethernet interfaces including all the copy-to-cpu ELMI frames.";
        }
        leaf last-clear {
          type srl_nokia-comm:date-and-time-delta;
          description
            "Timestamp of the last time the ELMI counters were cleared";
        }
      }
      container efm-oam {
        if-feature "srl_nokia-feat:l2cp-transparency-efm-oam";
        description
          "Enter the efm-oam context

           Container for Ethernet in the First Mile OAM frames

           EFM-OAM frames are identified by a Ethertype value 0x8809 and slow protocol subtype 0x03.";
        leaf in-tunneled-packets {
          type srl_nokia-comm:zero-based-counter64;
          description
            "System level incoming EFM-OAM tunneled frames

             Cumulative of all Ethernet interfaces including all the tunneled EFM-OAM frames. ";
        }
        leaf in-trap-to-cpu-packets {
          type srl_nokia-comm:zero-based-counter64;
          description
            "System level incoming EFM-OAM frames copied to CPU

             Cumulative of all Ethernet interfaces including all the copy-to-cpu EFM-OAM frames.";
        }
        leaf last-clear {
          type srl_nokia-comm:date-and-time-delta;
          description
            "Timestamp of the last time the EFM-OAM counters were cleared.";
        }
      }
    }
  }

  grouping system-l2cp-transparency-top {
    description
      "Top level grouping for system level L2CP transparency.";
    container l2cp-transparency {
      config false;
      description
        "Enter the l2cp-transparency context

         Enclosing container for system level Layer-2 Control Protocol transparency.";
      uses l2cp-statistics;
    }
  }

  grouping l2cp-transparency-top {
    description
      "Top level grouping for L2CP transparency.";
    container l2cp-transparency {
      presence "Configures the l2cp transparency parameters";
      must "starts-with(../../srl_nokia-if:name, 'ethernet')" {
        error-message "l2cp-transparency not supported on this interface";
      }
      must 'not(../../srl_nokia-if:breakout-mode)' {
        error-message "l2cp-transparency not configurable when breakout-mode is enabled";
      }
      description
        "Configuration and state of the Layer-2 Control Protocol transparency";
      leaf tunnel-all-l2cp {
        must ". = false() or (/srl_nokia-system:system/srl_nokia-lldp:lldp/srl_nokia-lldp:interface[srl_nokia-lldp:name=current()/../../../srl_nokia-if:name]/srl_nokia-lldp:admin-state = 'disable') or (not(/srl_nokia-system:system/srl_nokia-lldp:lldp/srl_nokia-lldp:interface[srl_nokia-lldp:name=current()/../../../srl_nokia-if:name]/srl_nokia-lldp:admin-state = 'enable') and not(/srl_nokia-system:system/srl_nokia-lldp:lldp/srl_nokia-lldp:admin-state = 'enable'))" {
          error-message "this interface must not have lldp enabled";
        }
        must '. = false() or not (../../srl_nokia-if:aggregate-id) or not (/srl_nokia-if:interface[srl_nokia-if:name=current()/../../srl_nokia-if:aggregate-id]/srl_nokia-if-lag:lag/srl_nokia-lacp:lacp)' {
          error-message "this interface must not be part of an lacp enabled lag";
        }
        type boolean;
        default "false";
        description
          "Configures the tunneling of all the L2CP protocols.

           When set to true this command triggers the installation of an ingress TCAM rule with the highest
           priority (above all the individual L2CP tunnel rules) which allows the forwarding of any
           Layer-2 Control Protocol coming into the interface. All the L2CP frames identified by
           MAC DA = 01:80:c2:00:00:0x or MAC DA = 01:80:c2:00:00:2x, with 'x' being any hex value, are
           tunneled. When set to false, all L2CP frames without a specific L2CP tunnel rule are discarded.";
      }
      container lldp {
        description
          "Enter the lldp context

           Container for L2CP transparency of the Link Layer Discovery Protocol";
        leaf tunnel {
          must ". = false() or (/srl_nokia-system:system/srl_nokia-lldp:lldp/srl_nokia-lldp:interface[srl_nokia-lldp:name=current()/../../../../srl_nokia-if:name]/srl_nokia-lldp:admin-state = 'disable') or (not(/srl_nokia-system:system/srl_nokia-lldp:lldp/srl_nokia-lldp:interface[srl_nokia-lldp:name=current()/../../../../srl_nokia-if:name]/srl_nokia-lldp:admin-state = 'enable') and not(/srl_nokia-system:system/srl_nokia-lldp:lldp/srl_nokia-lldp:admin-state = 'enable'))" {
            error-message "this interface must not have lldp enabled";
          }
          type boolean;
          default "false";
          description
            "Configures if incoming LLDP frames are tunneled.

             LLDP frames are identified by MAC DA 01-80-c2-00-00-00 and Ethertype 0x88cc.";
        }
        leaf oper-rule {
          config false;
          srl_nokia-ext:show-importance "high";
          type srl_nokia-comm:l2cp-oper-rule-state;
          description
            "The operational state of the TCAM rule applied to ingress LLDP frames.";
        }
      }
      container lacp {
        description
          "Enter the lacp context

           Container for L2CP transparency of the Link Aggregation Control Protocol";
        leaf tunnel {
          must '. = false() or not (../../../srl_nokia-if:aggregate-id) or not (/srl_nokia-if:interface[srl_nokia-if:name=current()/../../../srl_nokia-if:aggregate-id]/srl_nokia-if-lag:lag/srl_nokia-lacp:lacp)' {
            error-message "this interface must not be part of an lacp enabled lag";
          }
          type boolean;
          default "false";
          description
            "Configures if incoming LACP frames are tunneled.

             LACP frames are identified by MAC DA 01-80-c2-00-00-02, Ethertype 0x8809 and slow-protocol
             sub-type 0x01.";
        }
        leaf oper-rule {
          config false;
          srl_nokia-ext:show-importance "high";
          type srl_nokia-comm:l2cp-oper-rule-state;
          description
            "The operational state of the TCAM rule applied to ingress LACP frames.";
        }
      }
      container xstp {
        if-feature "srl_nokia-feat:l2cp-transparency-xstp";
        description
          "Enter the xstp context

           Container for the configuration of all the Spanning Tree Protocols.

           It includes Spanning Tree Protocol (STP), Rapid RSTP (RSTP) and Multiple STP (MSTP)";
        leaf tunnel {
          type boolean;
          default "false";
          description
            "Configures if incoming xSTP frames are tunneled.

             xSTP frames are identified by MAC DA 01-80-c2-00-00-00 and any Ethertype.";
        }
        leaf oper-rule {
          config false;
          srl_nokia-ext:show-importance "high";
          type srl_nokia-comm:l2cp-oper-rule-state;
          description
            "The operational state of the TCAM rule applied to ingress xSTP frames.";
        }
      }
      container ptp {
        description
          "Enter the ptp context

           Container for the configuration of Precision Time Protocol Peer-Delay frames.";
        leaf tunnel {
          type boolean;
          default "false";
          description
            "Configures if incoming ptp frames are tunneled.

             ptp frames are identified by MAC DA 01-80-c2-00-00-0e and Ethertype 0x88f7.";
        }
        leaf oper-rule {
          config false;
          srl_nokia-ext:show-importance "high";
          type srl_nokia-comm:l2cp-oper-rule-state;
          description
            "The operational state of the TCAM rule applied to ingress ptp frames.";
        }
      }
      container esmc {
        if-feature "srl_nokia-feat:l2cp-transparency-esmc";
        description
          "Enter the esmc context

           Container for the configuration of Ethernet synchronization messaging channel frames";
        leaf tunnel {
          must ". = false() or (not (../../../srl_nokia-if:synce/srl_nokia-if:ssm/srl_nokia-if:admin-state = 'enable'))" {
            error-message "this interface must not be configured for esmc messaging";
          }
          type boolean;
          default "false";
          description
            "Configures if incoming esmc frames are tunneled

             ESMC frames are identified by Ethertype 0x8809 and slow protocol subtype 0x0A.";
        }
        leaf oper-rule {
          config false;
          srl_nokia-ext:show-importance "high";
          type srl_nokia-comm:l2cp-oper-rule-state;
          description
            "The operational state of the TCAM rule applied to ingress ESMC frames";
        }
      }
      container elmi {
        if-feature "srl_nokia-feat:l2cp-transparency-elmi";
        description
          "Enter the elmi context

           Container for the configuration of Ethernet local management interface frames";
        leaf tunnel {
          type boolean;
          default "false";
          description
            "Configures if incoming ELMI frames are tunneled

             ELMI frames are identified by MAC DA 01-80-C2-00-00-07 and Ethertype 0x88ee.";
        }
        leaf oper-rule {
          config false;
          srl_nokia-ext:show-importance "high";
          type srl_nokia-comm:l2cp-oper-rule-state;
          description
            "The operational state of the TCAM rule applied to ingress ELMI frames";
        }
      }
      container efm-oam {
        if-feature "srl_nokia-feat:l2cp-transparency-efm-oam";
        description
          "Enter the efm-oam context

           Container for the configuration of Ethernet in the First Mile OAM frames";
        leaf tunnel {
          type boolean;
          default "false";
          description
            "Configures if incoming EFM-OAM frames are tunneled

             EFM-OAM frames are identified by Ethertype 0x8809 and slow protocol subtype 0x03.";
        }
        leaf oper-rule {
          config false;
          srl_nokia-ext:show-importance "high";
          type srl_nokia-comm:l2cp-oper-rule-state;
          description
            "The operational state of the TCAM rule applied to ingress EFM-OAM frames.";
        }
      }
    }
  }

  augment "/srl_nokia-if:interface/srl_nokia-if:ethernet" {
    if-feature "srl_nokia-feat:l2cp-transparency";
    uses l2cp-transparency-top;
  }

  augment "/srl_nokia-system:system" {
    if-feature "srl_nokia-feat:l2cp-transparency";
    uses system-l2cp-transparency-top;
  }
}
