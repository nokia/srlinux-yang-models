module srl_nokia-if-ip {
  yang-version 1.1;
  namespace "urn:nokia.com:srlinux:chassis:if-ip";
  prefix srl_nokia-if-ip;

  import srl_nokia-common {
    prefix srl_nokia-comm;
  }
  import srl_nokia-features {
    prefix srl_feat;
  }
  import srl_nokia-extensions {
    prefix srl_nokia-ext;
  }

  organization
    "Nokia";
  contact
    "Nokia SR Linux Support
     Web: <http://www.nokia.com>";
  description
    "Model for managing IP subinterfaces";

  revision 2026-07-31 {
    description
      "SRLinux 26.7.1";
  }
  revision 2026-03-31 {
    description
      "SRLinux 26.3.1";
  }
  revision 2025-10-31 {
    description
      "SRLinux 25.10.1";
  }
  revision 2025-07-31 {
    description
      "SRLinux 25.7.1";
  }
  revision 2025-03-31 {
    description
      "SRLinux 25.3.1";
  }
  revision 2024-10-31 {
    description
      "SRLinux 24.10.1";
  }
  revision 2024-07-31 {
    description
      "SRLinux 24.7.1";
  }
  revision 2024-03-31 {
    description
      "SRLinux 24.3.1";
  }
  revision 2023-07-31 {
    description
      "SRLinux 23.7.1";
  }
  revision 2023-03-31 {
    description
      "SRLinux 23.3.1";
  }
  revision 2021-11-30 {
    description
      "SRLinux 21.11.1";
  }
  revision 2021-06-30 {
    description
      "SRLinux 21.6.1";
  }
  revision 2021-03-31 {
    description
      "SRLinux 21.3.1";
  }
  revision 2020-06-30 {
    description
      "SRLinux 20.6.1";
  }
  revision 2019-11-30 {
    description
      "SRLinux 19.11.1";
  }

  typedef address-origin {
    type enumeration {
      enum other {
        value 1;
      }
      enum static {
        value 2;
      }
      enum dhcp {
        value 3;
      }
      enum link-layer {
        value 4;
      }
      enum random {
        value 5;
      }
    }
    description
      "The origin of the IP address";
  }

  typedef ipv6-address-status {
    type enumeration {
      enum preferred {
        value 1;
      }
      enum deprecated {
        value 2;
      }
      enum invalid {
        value 3;
      }
      enum inaccessible {
        value 4;
      }
      enum unknown {
        value 5;
      }
      enum tentative {
        value 6;
      }
      enum duplicate {
        value 7;
      }
      enum optimistic {
        value 8;
      }
    }
    description
      "The IPv6 address status";
  }

  typedef ipv4-address-status {
    type enumeration {
      enum preferred {
        value 1;
      }
      enum inaccessible {
        value 2;
      }
      enum tentative {
        value 3;
      }
      enum duplicate {
        value 4;
      }
    }
    description
      "The IPv4 address status";
  }

  typedef anycast-gw-mac-origin {
    type enumeration {
      enum configured {
        value 1;
      }
      enum vrid-auto-derived {
        value 2;
      }
    }
    description
      "The origin of the anycast-gw MAC address.";
  }

  grouping ipv4-top {
    description
      "Top-level configuration and state for IPv4 interfaces";
    container ipv4 {
      description
        "Enter the ipv4 context

         IPv4 configuration and state for the subinterface";
      leaf admin-state {
        description
          "Enable/disable IPv4 on the subinterface

           When set to enable, and even before an IPv4 address is configured, the subinterface starts to accept incoming packets with dest-ip 255.255.255.255, which is necessary to support dhcp-client functionality.";
        type srl_nokia-comm:admin-state;
        default "disable";
        must "(. = 'disable' or (../../type != 'bridged' and ../../type != 'local-mirror-dest'))" {
          error-message "ipv4 configuration not allowed on bridged or local-mirror-dest subinterfaces";
        }
      }
      list address {
        max-elements 64;
        key "ip-prefix";
        description
          "The list of  IPv4 addresses assigned to the subinterface.";
        must 'not (../../evpn-interface-ful-unnumbered)' {
          error-message "evpn-interface-ful-unnumbered not supported on subinterfaces with ipv4 or ipv6 addresses";
        }
        leaf ip-prefix {
          type srl_nokia-comm:ipv4-prefix-with-host-bits;
          description
            "The IPv4 address and prefix length in CIDR notation

             Subnets on the same subinterface are allowed to overlap as long as the host bits are different. When a locally originated unicast packet is destined to a host covered by multiple subnets associated with a subinterface, the source address is chosen to be the numerically lowest IP address among all these subnets. For example, if the addresses 172.16.1.1/12, 172.16.1.2/12, and 172.16.1.3/12 are configured on the same interface, 172.16.1.1 would be used as a local address when you issue a ping 172.16.1.5 command";
          must "not(starts-with(.,'0.') or starts-with(.,'127.') or re-match(.,'22[4-9]\\..*') or re-match(.,'2[3-5][0-9]\\..*'))" {
            error-message "Not a valid IPv4 unicast address prefix";
          }
          must "(../../unnumbered/admin-state != 'enable')" {
            error-message "Assignment of IPv4 addresses is prohibited when the subinterface is unnumbered";
          }
        }
        leaf anycast-gw {
          if-feature "srl_feat:anycast-gw";
          srl_nokia-ext:first-released "20.12.1";
          must "starts-with(../../../../name,'irb')" {
            error-message "Only supported on IRB subinterfaces";
          }
          must ". = false() or (. = true() and ../../../anycast-gw) or not(starts-with(../../../../name,'irb'))" {
            error-message "Only supported if anycast-gw container is configured";
          }
          type boolean;
          description
            "This designates the associated IPv4 address as an anycast-gateway IPv4 address of the subinterface.

             When this parameter is set to true:
             - The IPv4 address is associated with the anycast-gw MAC address in the same subinterface. ARP Requests received for the anycast-gw IPv4 address
               will be replied using this anycast-gw MAC address.
             - The IPv4 address can have duplicate IPv4 addresses in other IRB subinterfaces of routers attached to the same broadcast domain.
               Because of that ARP duplicate-address-detection procedures do not apply to anycast-gw IP addresses.";
        }
        leaf origin {
          config false;
          type address-origin;
          description
            "The origin of the IPv4 address.";
        }
        leaf primary {
          srl_nokia-ext:first-released "20.12.1";
          type empty;
          must "not (starts-with(../../../../name, 'mgmt') or (starts-with(../../../../name, 'system')) or (starts-with(../../../../name, 'sync')))" {
            error-message "primary not supported on mgmt or system or sync subinterfaces";
          }
          description
            "One of the IPv4 prefixes assigned to the subinterface can be explicitly configured as primary by setting this leaf to true. This designates the associated IPv4 address as a primary IPv4 address of the subinterface. By default, the numerically lowest value IPv4 address is selected as the primary address.

             The primary address is used as the source address for locally originated broadcast and multicast packets sent out the subinterface.";
        }
        leaf status {
          config false;
          type ipv4-address-status;
          description
            "The status of an IPv4 address";
        }
      }
      leaf allow-directed-broadcast {
        type boolean;
        default "false";
        description
          "When this is set to true the software is allowed to re-broadcast targeted broadcast IPv4 packets on this subinterface

           Detailed handling of subnet broadcast is as follows:

           If a targeted broadcast packet is received on subinterface X that has the matching subnet then it is delivered to the CPM and CPM will reply to an ICMP echo.

           If a targeted broadcast packet is received on subinterface X but the matching subnet is associated with subinterface Y, and subinterface Y is configured with allow-directed-broadcasts=false then it is delivered to the CPM and CPM replies to an ICMP echo per above, but it does not re-broadcast the packet on subinterface Y.

           If a targeted broadcast packet is received on subinterface X but the matching subnet is associated with subinterface Y, and subinterface Y is configured with allow-directed-broadcasts=true then it is delivered to the CPM and CPM replies to an ICMP echo per above, and CPM also re-broadcasts the packet on subinterface Y.";
      }
      container unnumbered {
        if-feature "srl_feat:ipv4-unnumbered";
        description
          "Enter the unnumbered context

           Top-level container for configuring unnumbered interfaces";
        leaf admin-state {
          type srl_nokia-comm:admin-state;
          default "disable";
          description
            "When enabled, the subinterface should operate in unnumbered mode for IPv4";
          must "(. = 'disable') or (starts-with(../../../../name, 'ethernet')) or (starts-with(../../../../name, 'lif')) or (starts-with(../../../../name, 'lag'))" {
            error-message "Unnumbered interfaces must be ethernet or LAG";
          }
          must "(. = 'disable') or not(boolean(../../dhcp-client))" {
            error-message "Assignment of dhcp-client prohibited when the subinterface is unnumbered";
          }
          must "(. = 'disable') or boolean(../interface)" {
            error-message "interface is mandatory when unnumbered admin-state is enable";
          }
        }
        leaf interface {
          type srl_nokia-comm:subinterface-all;
          description
            "Reference to the subinterface with the IPv4 address to be borrowed";
          must "not(starts-with(.,'mgmt'))" {
            error-message "Cannot borrow IPv4 address from management interfaces";
          }
          must "../../../../../interface[name=substring-before(current(), '.')]/subinterface[index=substring-after(current(), '.')]" {
            error-message "Cannot borrow IPv4 address from non-existing subinterface";
          }
          must "(substring-before(current(), '.') != ../../../../name) or (substring-after(current(), '.') != string(../../../index))" {
            error-message "Cannot borrow IPv4 address from same interface/subinterface";
          }
        }
        leaf address {
          config false;
          type srl_nokia-comm:ipv4-address;
          description
            "The operational IPv4 address borrowed from the referenced subinterface";
        }
        leaf unavailable-address-reason {
          config false;
          description
            "The reason why there is no operational IPv4 address to use for this subinterface";
          type enumeration {
            enum not-same-network-instance {
              description
                "The referenced subinterface does not belong to the same network instance as the borrowing subinterface";
            }
            enum referenced-interface-is-down {
              description
                "The referenced subinterface is operationally down";
            }
            enum referenced-interface-ipv4-is-down {
              description
                "The referenced subinterface is not enabled for IPv4";
            }
            enum referenced-interface-has-no-ipv4-addresses {
              description
                "The referenced subinterface has no IPv4 addresses assigned to it";
            }
          }
        }
      }
      uses subinterface-statistics {
        if-feature "srl_feat:subif-stats-per-ipv4-ipv6-container";
      }
    }
  }

  grouping ipv6-top {
    description
      "Top-level configuration and state for IPv6 interfaces";
    container ipv6 {
      description
        "Enter the ipv6 context

         IPv6 configuration and state for the subinterface";
      leaf admin-state {
        description
          "Enable/disable IPv6 on the subinterface

           When set to enable, and even before a global unicast IPv6 address is configured, chassis manager assigns an IPv6 link-local address to the subinterface, which will appear as a read-only entry in the address list. At this stage, the subinterface can receive IPv6 packets with any of the following destinations:
           -\tIPv6 link-local address
           -\tsolicited-node multicast address for the link-local address
           -\tff02::1 (all IPv6 devices)
           -\tff02::2 (all IPv6 routers)";
        type srl_nokia-comm:admin-state;
        default "disable";
        must "(. = 'disable' or (../../type != 'bridged' and ../../type != 'local-mirror-dest'))" {
          error-message "ipv6 configuration not allowed on bridged or local-mirror-dest subinterfaces";
        }
      }
      list address {
        max-elements 18;
        key "ip-prefix";
        description
          "The list of IPv6 addresses assigned to the subinterface.";
        must 'not (../../evpn-interface-ful-unnumbered)' {
          error-message "evpn-interface-ful-unnumbered not supported on subinterfaces with ipv4 or ipv6 addresses";
        }
        leaf ip-prefix {
          type srl_nokia-comm:ipv6-prefix-with-host-bits;
          description
            "The IPv6 address and prefix-length in CIDR notation

             Up to 16 global unicast IPv6 addresses can be assigned to each subinterface. Global unicast IPv6 address subnets on the same subinterface are allowed to overlap as long as the host bits are different. When a locally originated unicast packet is destined to a host covered by multiple subnets associated with a subinterface, the source address is chosen to be the numerically lowest IP address among all these subnets.";
          must "not(.='::/128' or .='::1/128' or starts-with(.,'ff'))" {
            error-message "Not a unicast IPv6 address prefix";
          }
        }
        leaf type {
          type srl_nokia-comm:ipv6-address-type;
          default "global-unicast";
          description
            "Specifies the explicit type of the IPv6 address being assigned to the subinterface

             By default, addresses are assumed to be global unicast.  Where a link-local address is to be explicitly configured, this leaf should be set to link-local.";
          must "not(. = 'global-unicast' and starts-with(../ip-prefix,'fe80'))" {
            error-message "Type is global but address prefix implies link-local";
          }
          must "not(. = 'link-local-unicast' and not(starts-with(../ip-prefix,'fe80')))" {
            error-message "Type is link-local-unicast but address prefix is not link-local";
          }
        }
        leaf anycast-gw {
          if-feature "srl_feat:anycast-gw";
          must "starts-with(../../../../name,'irb')" {
            error-message "Only supported on IRB subinterfaces";
          }
          must ". = false() or (. = true() and ../../../anycast-gw) or not(starts-with(../../../../name,'irb'))" {
            error-message "Only supported if anycast-gw container is configured";
          }
          must "not(starts-with(../ip-prefix,'fe80'))" {
            error-message "not supported on link local address";
          }
          type boolean;
          description
            "This designates the associated IPv6 address as an anycast-gateway IPv6 address of the subinterface.

             When this parameter is set to true:
             - The IPv6 address is associated with the anycast-gw MAC address in the same subinterface. Neighbor Solicitations received for the anycast-gw IPv6 address
               will be replied using this anycast-gw MAC address.
             - The IPv6 address can have duplicate IPv6 addresses in other IRB subinterfaces of routers attached to the same broadcast domain.
               Because of that, ND duplicate-address-detection procedures do not apply to anycast-gw IP addresses.";
        }
        leaf origin {
          config false;
          type address-origin;
          description
            "The origin of the IPv6 address";
        }
        leaf primary {
          srl_nokia-ext:first-released "20.12.1";
          type empty;
          must "not (starts-with(../../../../name, 'mgmt') or (starts-with(../../../../name, 'system')) or (starts-with(../../../../name, 'sync')))" {
            error-message "primary not supported on mgmt or system or sync subinterfaces";
          }
          description
            "One of the IPv6 prefixes assigned to the subinterface can be explicitly configured as primary by setting this leaf to true. This designates the associated IPv6 address as a primary IPv6 address of the subinterface. By default, the numerically lowest value IPv6 address is selected as the primary address.

             The primary address is used as the source address for locally originated broadcast and multicast packets sent out the subinterface.";
        }
        leaf status {
          config false;
          type ipv6-address-status;
          description
            "The status of an IPv6 address";
        }
      }
      uses subinterface-statistics {
        if-feature "srl_feat:subif-stats-per-ipv4-ipv6-container";
      }
    }
  }

  grouping anycast-gw-top {
    description
      "Top-level configuration and state for the anycast-gw context";
    container anycast-gw {
      if-feature "srl_feat:anycast-gw";
      must "starts-with(../../name,'irb')" {
        error-message "Only supported on IRB subinterfaces";
      }
      presence "Enable the anycast-gw functionality in the subinterface.";
      leaf virtual-router-id {
        type uint8 {
          range "1..255";
        }
        default "1";
        description
          "The Virtual Router Identifier (VRID) value used to auto-derive the anycast-gw-mac in the format 00:00:5E:00:01:VRID.";
        reference
          "draft-ietf-bess-evpn-inter-subnet-forwarding";
      }
      leaf anycast-gw-mac {
        type srl_nokia-comm:mac-address;
        description
          "The MAC address of associated to the anycast-gw IP address.

           If the anycast-gw MAC address is not configured, it will be auto-derived from the virtual-router-id value
           as per draft-ietf-bess-evpn-inter-subnet-forwarding following the format 00:00:5E:00:01:VRID.";
      }
      leaf anycast-gw-mac-origin {
        config false;
        type anycast-gw-mac-origin;
        description
          "Origin of the active anycast-gateway MAC address.

           If not configured, the anycast-gateway-mac will be auto-derived out of 00:00:5E:00:01:VRID, where VRID is the
           Virtual Router Identifier of the subinterface anycast-gw.";
      }
    }
  }

  grouping subinterface-statistics {
    container statistics {
      config false;
      description
        "Enter the statistics context

         Container for subinterface statistics, including all IPv4, IPv6 and MPLS packets belonging to a routed subinterface, or including just one of these protocols on a routed subinterface, or for all frames on a bridged subinterface";
      leaf in-packets {
        type srl_nokia-comm:zero-based-counter64;
        description
          "The total number of input packets received, counting transit and terminating traffic

           This equals the sum of:
           in-error-packets
           in-discarded-packets
           in-terminated-packets
           in-forwarded-packets";
      }
      leaf in-octets {
        type srl_nokia-comm:zero-based-counter64;
        description
          "The total number of octets received in input packets, counting transit and terminating traffic";
      }
      leaf in-error-packets {
        if-feature "srl_feat:ixr-dnx or srl_feat:fpcx";
        type srl_nokia-comm:zero-based-counter64;
        description
          "The total number of input packets discarded due to errors, counting transit and terminating traffic

           In an IP context, the sum of the following RFC 4293 counters:
           ipIfStatsInHdrErrors
           ipIfStatsInNoRoutes
           ipIfStatsInAddrErrors
           ipIfStatsInUnknownProtos
           ipIfStatsInTruncatedPkts

           In an MPLS context, the total number of MPLS packets that were dropped because:
           - forwarded top label had an MPLS TTL value of 0
           - terminating top label had an MPLS TTL value of 0
           - the top label was unknown (no matching forwarding entry)";
      }
      leaf in-discarded-packets {
        type srl_nokia-comm:zero-based-counter64;
        description
          "The total number of input packets that were dropped due to explicit programming

           The discards can be due to any of the following reasons
           - ingress interface ACL drop action
           - CPM filter drop action
           - VOQ congestion discards (7250 IXR only)
           - unicast destination MAC address is not the MAC address of the subinterface
           - packet matched a route with a blackhole next-hop
           - packet was non-terminating and its TTL expired
           - packet matched a route with a next-hop via another subinterface but the next-hop address was not resolvable by ARP/ND
           - packet is a host address on another subinterface but the host address was not resolvable by ARP/ND

           In an MPLS context, this includes the total number of MPLS packets that were dropped because they were received with forwarded top label having an MPLS TTL value of 1";
      }
      leaf in-terminated-packets {
        if-feature "srl_feat:ixr-dnx or srl_feat:vsrl or srl_feat:fpcx";
        type srl_nokia-comm:zero-based-counter64;
        description
          "The total number of input packets that were received on this subinterface that were extracted to the control plane

           The count includes packets eventually discarded by the CPM. Such discards include:
           - packets with unsupported IP protocol numbers
           - packets destined to TCP/UDP ports that are not open/listening
           - IPv4 packets with any IP options
           - IPv6 packets with any extension headers";
      }
      leaf in-terminated-octets {
        if-feature "srl_feat:ixr-dnx or srl_feat:vsrl or srl_feat:fpcx";
        type srl_nokia-comm:zero-based-counter64;
        description
          "The total number of octets in packets that were received on this subinterface and counted in in-terminated-packets";
      }
      leaf in-forwarded-packets {
        type srl_nokia-comm:zero-based-counter64;
        description
          "The number of packets received on this subinterface for which the router was not the final destination and for which the router attempted to find a route to forward them to that final destination.

           Note that non-terminating IPv4 packets with options and non-terminating IPv6 packets with extension headers are included in this count as are packets that trigger ICMP/ICMPv6 redirect messages.";
      }
      leaf in-forwarded-octets {
        type srl_nokia-comm:zero-based-counter64;
        description
          "The number of octets in packets received on this subinterface counted in in-forwarded-packets";
      }
      leaf in-matched-ra-packets {
        type srl_nokia-comm:zero-based-counter64;
        description
          "The total number of IPv6 packets matched with applied RA-Guard policy";
      }
      leaf out-forwarded-packets {
        type srl_nokia-comm:zero-based-counter64;
        description
          "The number of transit packets which the router attempted to forward out this subinterface";
      }
      leaf out-forwarded-octets {
        type srl_nokia-comm:zero-based-counter64;
        description
          "The number of octets in transit packets which the router attempted to forward out this subinterface";
      }
      leaf out-originated-packets {
        type srl_nokia-comm:zero-based-counter64;
        description
          "The number of packets which originated on the CPM and which the router attempted to forward out this subinterface";
      }
      leaf out-originated-octets {
        type srl_nokia-comm:zero-based-counter64;
        description
          "The number of octets in packets which originated on the CPM and which the router attempted to forward out this subinterface";
      }
      leaf out-error-packets {
        if-feature "srl_feat:ixr-dnx or srl_feat:fpcx";
        type srl_nokia-comm:zero-based-counter64;
        description
          "The number of packets, originating and transit, for which this router was successful in finding a path to their final destination through this subinterface but an error prevented their transmission

           On 7250 IXR systems this is incremented when the IPv4 packet size exceeds the IP MTU and fragmentation was not allowed or not supported. It is also incremented when the MPLS packet size exceeds the MPLS MTU of the subinterface.";
      }
      leaf out-discarded-packets {
        type srl_nokia-comm:zero-based-counter64;
        description
          "The total number of packets, originating and transit, that should have been sent out this subinterface but were dropped

           This includes IP packets dropped by egress interface ACL drop action.";
      }
      leaf out-packets {
        type srl_nokia-comm:zero-based-counter64;
        description
          "The total number of packets that this router supplied to the lower layers for transmission

           This equals the sum of:
           out-error-packets
           out-discarded-packets
           out-originated-packets
           out-forwarded-packets";
      }
      leaf out-octets {
        type srl_nokia-comm:zero-based-counter64;
        description
          "The total number of octets in packets delivered to the lower layers for transmission";
      }
      leaf last-clear {
        type srl_nokia-comm:date-and-time-delta;
        description
          "Timestamp of the last time the subinterface counters were cleared";
      }
    }
  }
}
