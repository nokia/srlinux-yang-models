module srl_nokia-interfaces-ip-dhcp-relay {
  yang-version 1.1;
  namespace "urn:nokia.com:srlinux:dhcp-relay:interfaces-ip-dhcp-relay";
  prefix srl_nokia-if-ip-dhcp-relay;

  import srl_nokia-interfaces {
    prefix srl_nokia-if;
  }
  import srl_nokia-common {
    prefix srl_nokia-comm;
  }
  import srl_nokia-network-instance {
    prefix srl-netinst;
  }
  import srl_nokia-features {
    prefix srl_nokia-feat;
  }

  organization
    "Nokia";
  contact
    "Nokia SR Linux Support
     Web: <http://www.nokia.com>";
  description
    "Model for managing DHCP relay and DHCPv6 relay on IP and IRB subinterfaces";

  revision 2026-07-31 {
    description
      "SRLinux 26.7.1";
  }
  revision 2026-03-31 {
    description
      "SRLinux 26.3.1";
  }
  revision 2024-03-31 {
    description
      "SRLinux 24.3.1";
  }
  revision 2023-03-31 {
    description
      "SRLinux 23.3.1";
  }
  revision 2022-03-31 {
    description
      "SRLinux 22.3.1";
  }
  revision 2021-11-30 {
    description
      "SRLinux 21.11.1";
  }
  revision 2021-03-31 {
    description
      "SRLinux 21.3.1";
  }
  revision 2020-06-30 {
    description
      "SRLinux 20.6.1";
  }

  typedef hostv4 {
    type union {
      type srl_nokia-comm:ipv4-address;
      type srl_nokia-comm:domain-name;
    }
    description
      "The hostv4 type represents either an IPv4 address or a DNS domain name.";
  }

  typedef hostv6 {
    type union {
      type srl_nokia-comm:ipv6-address;
      type srl_nokia-comm:domain-name;
    }
    description
      "The hostv6 type represents either an IPv6 address or a DNS domain name.";
  }

  typedef dhcp-relay-v4-agent-oper-down-reason {
    type enumeration {
      enum dhcp-relay-admin-down;
      enum sub-interface-oper-down;
      enum all-dhcp-servers-unreachable-within-net-instance;
      enum gi-address-not-matching-relay-sub-interface-ipv4-addresses;
      enum no-valid-ipv4-address-on-sub-interface;
    }
    description
      "The dhcp-relay-v4-agent-oper-down-reason represents the possible reasons causing DHCPv4 relay agent to go into operational down state";
  }

  typedef dhcp-relay-v6-agent-oper-down-reason {
    type enumeration {
      enum dhcp-relay-admin-down;
      enum sub-interface-oper-down;
      enum all-dhcpv6-servers-unreachable-within-net-instance;
      enum source-address-not-matching-relay-sub-interface-ipv6-addresses;
      enum no-valid-ipv6-address-on-sub-interface;
    }
    description
      "The dhcp-relay-v6-agent-oper-down-reason represents the possible reasons causing DHCPv6 relay agent to go into operational down state";
  }

  grouping dhcp-relay-dns-resolution {
    list server {
      key "domain";
      config false;
      description
        "Reports the resolved IP address for server entries using domain names";
      leaf domain {
        type srl_nokia-comm:domain-name;
        description
          "The server domain name";
      }
      leaf resolved-ip-address {
        type srl_nokia-comm:ip-address;
        description
          "The resolved IP address of the server domain name.

           An entry of 0.0.0.0 indicates the server IP cannot be resolved.";
      }
      leaf last-update {
        type srl_nokia-comm:date-and-time-delta;
        description
          "The date and time of the last update of the server IP address";
      }
    }
  }

  grouping subinterface-dhcpv4-relay {
    container dhcp-relay {
      presence "Performs DHCPv4 relay function";
      description
        "Container for options related to DHCPv4 relay";
      must "not(starts-with(../../../srl_nokia-if:name, 'mgmt') or starts-with(../../../srl_nokia-if:name, 'lo') or starts-with(../../../srl_nokia-if:name, 'system')  or starts-with(../../../srl_nokia-if:name, 'sync'))" {
        error-message "dhcp relay is not supported on mgmt, lo, system or sync interfaces";
      }
      leaf admin-state {
        type srl_nokia-comm:admin-state;
        default "enable";
        description
          "The configurable state of the dhcp relay agent";
      }
      leaf oper-state {
        config false;
        type srl_nokia-comm:oper-state;
        description
          "The operational state of the dhcp relay agent";
      }
      leaf oper-down-reason {
        config false;
        type dhcp-relay-v4-agent-oper-down-reason;
        description
          "The reason causing the dhcp relay agent to go into operational down state";
      }
      leaf-list option {
        type enumeration {
          enum circuit-id {
            description
              "Enable option 82 suboption 1 circuit-id into relayed packet towards DHCPv4 server, format=system_name/VRF_instance/sub-interface_id:vlan_id";
          }
          enum remote-id {
            description
              "Enable option 82 suboption 2 remote-id into relayed packet towards DHCPv4 server, format=client MAC address";
          }
          enum link-selection {
            description
              "Enable option 82 suboption 5 link-selection into relayed packet towards DHCPv4 server, format=IP address of incoming interface";
          }
        }
        description
          "List of option82 suboptions to insert into relayed packet towards DHCPv4 server";
      }
      leaf circuit-id-l2-interface {
        if-feature "srl_nokia-feat:dhcp-relay-irb-l2-circuit-id";
        type boolean;
        default "false";
        description
          "When this is set, the format of the option 82 suboption 1 circuit-id will be changed to indicate the L2 interface the packet came from, format=system_name/MAC_VRF_instance_name/L2_interface_name/sub_interface_id:vlan_id";
      }
      leaf-list server {
        type hostv4;
        description
          "List of the DHCPv4 servers that the DHCPv4 relay function will relay DHCPv4 packets to/from";
        min-elements 1;
        max-elements 8;
      }
      leaf gi-address {
        type srl_nokia-comm:ipv4-address;
        description
          "IPv4 address to be used as giaddr of the relayed packets towards DHCPv4 servers.
            This address can be any IPv4 address configured within the network-instance towards the DHCPv4 server";
      }
      leaf use-gi-addr-as-src-ip-addr {
        type boolean;
        default "false";
        description
          "When this is set, the configured giaddress will be used as source ip address.";
      }
      leaf trusted-mode {
        type boolean;
        default "false";
        description
          "When this is set, trusted mode will be enabled for incoming DHCPv4 messages

           If option 82 is set and giaddr is zero, do not add second relay-agent option and set giaddr as configured and forward
           If a non-zero giaddr packet is received without matching the configured giaddr, forward without additional options
           If a non-zero giaddr packet is received and matching the configured giaddr, drop";
      }
      leaf network-instance {
        description
          "network instance to relay dhcp packets to";
        type leafref {
          path "/srl-netinst:network-instance/srl-netinst:name";
        }
        must '(/srl-netinst:network-instance[srl-netinst:name=current()]/srl-netinst:type = "srl-netinst:ip-vrf" or "srl-netinst:default") and not(starts-with(.,"mgmt"))' {
          error-message "dhcp relay is only supported in an existing network-instance of type 'ip-vrf' or 'default' and not on 'mgmt' network-instance";
        }
      }
      container trace-options {
        description
          "Enter the trace-options context

           Container for tracing DHCPv4 relay operations on the subinterface";
        leaf-list trace {
          type enumeration {
            enum messages {
              description
                "Capture all DHCPv4 messages sent and received by the subinterface";
            }
          }
          description
            "List of events to trace";
        }
      }
      container dns-resolution {
        config false;
        uses dhcp-relay-dns-resolution;
        description
          "Enter the dns-resolution context";
      }
      container statistics {
        config false;
        leaf client-packets-received {
          type srl_nokia-comm:zero-based-counter64;
          description
            "Total received dhcp packets from dhcp client(s) for DHCP Relay";
        }
        leaf client-packets-relayed {
          type srl_nokia-comm:zero-based-counter64;
          description
            "Total relayed dhcp packets from dhcp client(s) towards DHCP server(s)";
        }
        leaf client-packets-discarded {
          type srl_nokia-comm:zero-based-counter64;
          description
            "Total discarded dhcp packets from dhcp client(s) towards DHCP server(s)";
        }
        leaf server-packets-received {
          type srl_nokia-comm:zero-based-counter64;
          description
            "Total received dhcp packets from DHCP server(s) for DHCP Relay";
        }
        leaf server-packets-relayed {
          type srl_nokia-comm:zero-based-counter64;
          description
            "Total relayed dhcp packets from DHCP server(s) towards dhcp client(s)";
        }
        leaf server-packets-discarded {
          type srl_nokia-comm:zero-based-counter64;
          description
            "Total discarded dhcp packets from DHCP server(s) towards dhcp client(s)";
        }
        description
          "Enter the statistics context";
      }
    }
  }

  grouping subinterface-dhcpv6-relay {
    container dhcp-relay {
      presence "Performs DHCPv6 relay function";
      description
        "Container for options related to DHCPv6 relay";
      must "not(starts-with(../../../srl_nokia-if:name, 'mgmt') or starts-with(../../../srl_nokia-if:name, 'lo') or starts-with(../../../srl_nokia-if:name, 'system')  or starts-with(../../../srl_nokia-if:name, 'sync'))" {
        error-message "dhcp relay is not supported on mgmt, lo, system, or sync interfaces";
      }
      leaf admin-state {
        type srl_nokia-comm:admin-state;
        default "enable";
        description
          "The configurable state of the dhcp relay agent";
      }
      leaf oper-state {
        config false;
        type srl_nokia-comm:oper-state;
        description
          "The operational state of the dhcp relay agent";
      }
      leaf oper-down-reason {
        config false;
        type dhcp-relay-v6-agent-oper-down-reason;
        description
          "The reason causing the dhcp relay agent to go into operational down state";
      }
      leaf-list option {
        type enumeration {
          enum interface-id {
            description
              "Enable option 18 Interface-Id into relayed packet towards DHCPv6 server, format=system_name/VRF_instance/sub-interface_id:vlan_id";
          }
          enum remote-id {
            description
              "Enable option 37 Remote Identifier into relayed packet towards DHCPv6 server, format=client MAC address";
          }
          enum client-link-layer-address {
            description
              "Enable option 79 Client Link-Layer Address into relayed packet towards DHCPv6 server, format based on rfc-6939";
          }
        }
        description
          "List of options to insert into relayed packet towards DHCPv6 server";
      }
      leaf interface-id-l2-interface {
        if-feature "srl_nokia-feat:dhcp-relay-irb-l2-circuit-id";
        type boolean;
        default "false";
        description
          "When this is set, the format of the option 18 interface-id will be changed to indicate the L2 interface the packet came from, format=system_name/MAC_VRF_instance_name/L2_interface_name/sub_interface_id:vlan_id";
      }
      leaf-list server {
        type hostv6;
        description
          "List of the DHCPv6 servers that the DHCPv6 relay function will relay DHCPv6 packets to/from";
        min-elements 1;
        max-elements 8;
      }
      leaf source-address {
        type srl_nokia-comm:ipv6-address;
        description
          "Source IPv6 address of the relayed packets towards DHCPv6 servers
            this address can be any IPv6 address configured within the network-instance towards the DHCPv6 server";
      }
      leaf network-instance {
        description
          "network instance to relay dhcp packets to";
        type leafref {
          path "/srl-netinst:network-instance/srl-netinst:name";
        }
        must '(/srl-netinst:network-instance[srl-netinst:name=current()]/srl-netinst:type = "srl-netinst:ip-vrf" or "srl-netinst:default") and not(starts-with(.,"mgmt"))' {
          error-message "dhcp relay is only supported in an existing network-instance of type 'ip-vrf' or 'default' and not on 'mgmt' network-instance";
        }
      }
      container trace-options {
        description
          "Enter the trace-options context

           Container for tracing DHCPv6 relay operations on the subinterface";
        leaf-list trace {
          type enumeration {
            enum messages {
              description
                "Capture all DHCPv6 messages sent and received by the subinterface";
            }
          }
          description
            "List of events to trace";
        }
      }
      container dns-resolution {
        config false;
        uses dhcp-relay-dns-resolution;
        description
          "Enter the dns-resolution context";
      }
      container statistics {
        config false;
        leaf client-packets-received {
          type srl_nokia-comm:zero-based-counter64;
          description
            "Total received dhcp packets from dhcp client(s) for DHCP Relay";
        }
        leaf client-packets-relayed {
          type srl_nokia-comm:zero-based-counter64;
          description
            "Total relayed dhcp packets from dhcp client(s) towards DHCP server(s)";
        }
        leaf client-packets-discarded {
          type srl_nokia-comm:zero-based-counter64;
          description
            "Total discarded dhcp packets from dhcp client(s) towards DHCP server(s)";
        }
        leaf server-packets-received {
          type srl_nokia-comm:zero-based-counter64;
          description
            "Total received dhcp packets from DHCP server(s) for DHCP Relay";
        }
        leaf server-packets-relayed {
          type srl_nokia-comm:zero-based-counter64;
          description
            "Total relayed dhcp packets from DHCP server(s) towards dhcp client(s)";
        }
        leaf server-packets-discarded {
          type srl_nokia-comm:zero-based-counter64;
          description
            "Total discarded dhcp packets from DHCP server(s) towards dhcp client(s)";
        }
        description
          "Enter the statistics context";
      }
    }
  }

  augment "/srl_nokia-if:interface/srl_nokia-if:subinterface/srl_nokia-if:ipv4" {
    if-feature "srl_nokia-feat:dhcp-relay";
    uses subinterface-dhcpv4-relay;
  }

  augment "/srl_nokia-if:interface/srl_nokia-if:subinterface/srl_nokia-if:ipv6" {
    if-feature "srl_nokia-feat:dhcp-relay";
    uses subinterface-dhcpv6-relay;
  }
}
