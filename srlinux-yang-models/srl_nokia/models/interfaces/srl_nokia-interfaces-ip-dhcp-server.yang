module srl_nokia-interfaces-ip-dhcp-server {
  yang-version 1.1;
  namespace "urn:nokia.com:srlinux:dhcp:interfaces-ip-dhcp-server";
  prefix srl_nokia-if-ip-dhcp-server;

  import srl_nokia-interfaces {
    prefix srl_nokia-if;
  }
  import srl_nokia-common {
    prefix srl-comm;
  }
  import srl_nokia-extensions {
    prefix srl-ext;
  }
  import srl_nokia-interfaces-ip-dhcp-relay {
    prefix srl_nokia-dhcp-relay;
  }
  import srl_nokia-features {
    prefix srl_nokia-feat;
  }

  organization
    "Nokia";
  contact
    "Nokia SR Linux Support
     Web: <http://www.nokia.com>";
  description
    "Model to enable DHCP server on IP and IRB subinterfaces";

  revision 2026-03-31 {
    description
      "SRLinux 26.3.1";
  }
  revision 2022-03-31 {
    description
      "SRLinux 22.3.1";
  }
  revision 2021-11-30 {
    description
      "SRLinux 21.11.1";
  }
  revision 2021-06-30 {
    description
      "SRLinux 21.6.1";
  }

  grouping dhcp-common {
    leaf oper-state {
      config false;
      type srl-comm:oper-state;
      srl-ext:show-importance "high";
      description
        "Details if the dhcp server is operationally available";
    }
  }

  grouping subinterface-dhcpv4-server {
    container dhcp-server {
      presence "perform dhcp server related functions under subinterface";
      leaf admin-state {
        type srl-comm:admin-state;
        srl-ext:show-importance "high";
        default "disable";
        must "not(((../../srl_nokia-dhcp-relay:dhcp-relay/srl_nokia-dhcp-relay:admin-state = 'enable') and (. = 'enable')) or starts-with(../../../../srl_nokia-if:name, 'mgmt'))" {
          error-message "can't enable both dhcp server and dhcp relay on the same subinterface or enable dhcp server on the mgmt interface";
        }
        description
          "Enables/Disables DHCP server function on subinterface";
      }
      uses dhcp-common;
    }
  }

  grouping subinterface-dhcpv6-server {
    container dhcpv6-server {
      presence "perform dhcpv6 server related functions under subinterface";
      leaf admin-state {
        type srl-comm:admin-state;
        srl-ext:show-importance "high";
        default "disable";
        must "not(((../../srl_nokia-dhcp-relay:dhcp-relay/srl_nokia-dhcp-relay:admin-state = 'enable') and (. = 'enable')) or starts-with(../../../../srl_nokia-if:name, 'mgmt'))" {
          error-message "can't enable both dhcp server and dhcp relay on the same subinterface or enable dhcp server on the mgmt interface";
        }
        description
          "Enables/Disables DHCPv6 server function on subinterface";
      }
      uses dhcp-common;
    }
  }

  augment "/srl_nokia-if:interface/srl_nokia-if:subinterface/srl_nokia-if:ipv4" {
    if-feature "srl_nokia-feat:dhcp-server";
    uses subinterface-dhcpv4-server;
  }

  augment "/srl_nokia-if:interface/srl_nokia-if:subinterface/srl_nokia-if:ipv6" {
    if-feature "srl_nokia-feat:dhcp-server";
    uses subinterface-dhcpv6-server;
  }
}
